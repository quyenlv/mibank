-- $Id: it-bridge-mib.mib,v 1.2 2001/06/25 19:28:47 sse Exp $
       ITOUCH-BRIDGE-MIB DEFINITIONS ::= BEGIN

               IMPORTS
                       Counter
                               FROM RFC1155-SMI
                       DisplayString, ifIndex
                               FROM RFC1213-MIB
                       dot1dTpFdbAddress, MacAddress
                               FROM BRIDGE-MIB
                       OBJECT-TYPE
                               FROM RFC-1212
                       iTouch
                               FROM ITOUCH-MIB;

       bridgeDep       OBJECT IDENTIFIER ::= { iTouch 5 }
       xBridge         OBJECT IDENTIFIER ::= { iTouch 19 }

       -- ITouch Bridge subgroups

       xBridgeSystem   OBJECT IDENTIFIER ::= { xBridge 1 }
       --              2 is reserved for IF
       xBridgeProtocol OBJECT IDENTIFIER ::= { xBridge 3 }
       xBridgeFilter   OBJECT IDENTIFIER ::= { xBridge 4 }

       -- This is a MIB module for all iTouch systems that
       -- implement Ethernet bridging.

            -- Copyright 2000 iTouch Communications, Inc. All Rights Reserved.
            -- Reproduction of this document is authorized on
            -- condition that this copyright notice is included.
            -- This MIB document embodies iTouch Communications, Inc.'s 
            -- proprietary intellectual property.  iTouch Communications, Inc.
            -- retains all title and ownership in this MIB, including any
            -- revisions.
            --
            -- It is iTouch Communications, Inc.'s intent to encourage the
            -- widespread use of this MIB in connection with the management of
            -- iTouch Communications, Inc. products. iTouch Communications,
            -- Inc. grants vendors,end-users, and other interested parties a
            -- non-exclusive license to use this MIB in connection with the
            -- management of iTouch Communications, Inc. products.
            --
            -- This MIB document is supplied "AS IS," and iTouch 
            -- Communications, Inc. makes no warranty, either express or
            -- implied, as to the use operation, condition, or performance of
            -- the MIB.


       -- the Bridge System group

       -- Implementation of this group is mandatory for all iTouch
       -- bridges

       bridgeState OBJECT-TYPE
           SYNTAX INTEGER { disabled(1), enabled(2) }
           ACCESS read-write
           STATUS mandatory
           DESCRIPTION
               "Controls whether the bridge will perform 
               bridging."
           DEFVAL { enabled }
           ::= { xBridgeSystem 1 }

       bridgeEarlyLoopState OBJECT-TYPE
           SYNTAX INTEGER { disabled(1), enabled(2) }
           ACCESS read-write
           STATUS mandatory
           DESCRIPTION
               "Controls whether the bridge will implement the 
               early loop detection algorithm of restarting the 
               Spanning Tree Protocol when a packet is received 
               from a source on one interface when the source was 
               learned on a different interface."
           DEFVAL { disabled }
           ::= { xBridgeSystem 2 }

       bridgeEarlyLoopCount OBJECT-TYPE
           SYNTAX Counter
           ACCESS read-only
           STATUS mandatory
           DESCRIPTION
               "The number of times that an early loop was detected 
               while the early loop state was enabled."
           ::= { xBridgeSystem 3 }

       bridgeEarlyLoopAddress OBJECT-TYPE
           SYNTAX MacAddress
           ACCESS read-only
           STATUS mandatory
           DESCRIPTION
               "The last address to cause an early loop to be 
               detected while the early loop state was enabled."
           ::= { xBridgeSystem 4 }

       bridgeSpanningTreeState OBJECT-TYPE
           SYNTAX INTEGER { disabled(1), enabled(2) }
           ACCESS read-write
           STATUS mandatory
           DESCRIPTION
               "Controls whether the bridge will run the Spanning 
               Tree Protocol."
           DEFVAL { enabled }
           ::= { xBridgeSystem 5 }

       bridgeFilterDiscardTimeout OBJECT-TYPE
           SYNTAX INTEGER (0..65535)
           ACCESS read-write
           STATUS mandatory
           DESCRIPTION
               "The number of seconds before an inactive filter is 
               deleted. Learned filters become inactive when the 
               use timeout (dot1dTpAgingTime) has been exceeded."
           DEFVAL { 43200 }
           ::= { xBridgeSystem 6 }

       bridgeTopologyState OBJECT-TYPE
           SYNTAX INTEGER { stable(1), changing(2) }
           ACCESS read-only
           STATUS mandatory
           DESCRIPTION
               "Indicates whether the Spanning Tree Protocol's 
               topology is stable or changing."
           ::= { xBridgeSystem 7 }

       bridgeTopologyChangeAddr OBJECT-TYPE
           SYNTAX MacAddress
           ACCESS read-only
           STATUS mandatory
           DESCRIPTION
               "The ethernet address of the last bridge from which 
               a Topology Change Notification packet was 
               received."
           ::= { xBridgeSystem 8 }

       -- Bridge Protocol Filter Group

       bridgeProtocolFilterState OBJECT-TYPE
           SYNTAX INTEGER { disabled(1), enabled(2) }
           ACCESS read-write
           STATUS mandatory
           DESCRIPTION
               "Controls whether protocol filtering is active."
           DEFVAL { enabled }
           ::= { xBridgeProtocol 1 }

       bridgeProtocolDefaultPriority OBJECT-TYPE
           SYNTAX INTEGER { low(1), medium(3), high(5),
                            discard(101) }
           ACCESS read-write
           STATUS mandatory
           DESCRIPTION
               "Controls the default priority if no entry exists 
               for the protocol."
           DEFVAL { medium }
           ::= { xBridgeProtocol 2 }

       bridgeProtocolTable OBJECT-TYPE
           SYNTAX SEQUENCE OF BridgeProtocolEntry
           ACCESS not-accessible
           STATUS mandatory
           DESCRIPTION
               "A list of bridge protocol filters."
           ::= { xBridgeProtocol 3 }

       bridgeProtocolEntry OBJECT-TYPE
           SYNTAX BridgeProtocolEntry
           ACCESS not-accessible
           STATUS mandatory
           DESCRIPTION
               "Bridge protocol filter entry."
           INDEX { bridgeProtocolProtocol }
           ::= { bridgeProtocolTable 1 }

       BridgeProtocolEntry ::=
           SEQUENCE {
               bridgeProtocolProtocol
                   OCTET STRING,
               bridgeProtocolName
                   DisplayString,
               bridgeProtocolPriority
                   INTEGER,
               bridgeProtocolUses
                   Counter,
               bridgeProtocolStatus
                   INTEGER
           }

       bridgeProtocolProtocol OBJECT-TYPE
           SYNTAX OCTET STRING (SIZE (2)) 
           ACCESS read-only
           STATUS mandatory
           DESCRIPTION
               "The protocol type associated with the entry. The 
               value 65536 is for all 802.3 MAC frames."
           ::= { bridgeProtocolEntry 1 }

       bridgeProtocolName OBJECT-TYPE
           SYNTAX DisplayString (SIZE(0..24))
           ACCESS read-write
           STATUS mandatory
           DESCRIPTION
               "The name associated with the protocol."
           DEFVAL { "" }
           ::= { bridgeProtocolEntry 2 }

       bridgeProtocolPriority OBJECT-TYPE
           SYNTAX INTEGER { low(1), medium(3), high(5),
                            discard(101) }
           ACCESS read-write
           STATUS mandatory
           DESCRIPTION
               "The priority or action to take with the protocol."
           DEFVAL { medium }
           ::= { bridgeProtocolEntry 3 }

       bridgeProtocolUses OBJECT-TYPE
           SYNTAX Counter
           ACCESS read-only
           STATUS mandatory
           DESCRIPTION
               "The number of times the filter has been used."
           ::= { bridgeProtocolEntry 4 }

       bridgeProtocolStatus OBJECT-TYPE
           SYNTAX INTEGER { invalid(1), valid(2) }
           ACCESS read-write
           STATUS mandatory
           DESCRIPTION
               "The status of the protocol entry.  Set to 'invalid' 
               to remove the entry."
           DEFVAL { valid }
           ::= { bridgeProtocolEntry 5 }

       -- Bridge Filter Group

       bridgeFilterTable OBJECT-TYPE
           SYNTAX SEQUENCE OF BridgeFilterEntry
           ACCESS not-accessible
           STATUS mandatory
           DESCRIPTION
               "A list of bridge filters."
           ::= { xBridgeFilter 1 }

       bridgeFilterEntry OBJECT-TYPE
           SYNTAX BridgeFilterEntry
           ACCESS not-accessible
           STATUS mandatory
           DESCRIPTION
               "Bridge filter entry."
           INDEX { dot1dTpFdbAddress }
           ::= { bridgeFilterTable 1 }

       BridgeFilterEntry ::=
           SEQUENCE {
               bridgeFilterForwardSubPort
                   INTEGER,
               bridgeFilterUses
                   Counter,
               bridgeFilterAge
                   INTEGER
           }

       bridgeFilterForwardSubPort OBJECT-TYPE
           SYNTAX INTEGER
           ACCESS read-write
           STATUS mandatory
           DESCRIPTION
               "The unique identifier from which the address has 
               been seen within the port.  It is the DLCI for frame 
               relay or VC for X25."
           DEFVAL { 0 }
           ::= { bridgeFilterEntry 1 }

       bridgeFilterUses OBJECT-TYPE
           SYNTAX Counter
           ACCESS read-only
           STATUS mandatory
           DESCRIPTION
               "The number of times the filter has been used for 
               forwarding packets."
           ::= { bridgeFilterEntry 2 }

       bridgeFilterAge OBJECT-TYPE
           SYNTAX INTEGER
           ACCESS read-only
           STATUS mandatory
           DESCRIPTION
               "The number of seconds that a learned filter has 
               been active or inactive.  This value has no meaning 
               for non-learned filters."
           ::= { bridgeFilterEntry 3 }


       -- Bridge Filter Link table
       
       bridgeFilterLinkTable OBJECT-TYPE
           SYNTAX SEQUENCE OF BridgeFilterLinkEntry
           ACCESS not-accessible
           STATUS mandatory
           DESCRIPTION
               "Bridge filtering characteristics of all links."
           ::= { xBridgeFilter 2 }
       
       bridgeFilterLinkEntry OBJECT-TYPE
           SYNTAX BridgeFilterLinkEntry
           ACCESS not-accessible
           STATUS mandatory
           DESCRIPTION
               "Bridge filtering characteristics of a specific 
               link."
           INDEX { ifIndex }
           ::= { bridgeFilterLinkTable 1 }
       
       BridgeFilterLinkEntry ::=
           SEQUENCE {
               bridgeFilterLinkOverflowCam
                   INTEGER
           }

       bridgeFilterLinkOverflowCam OBJECT-TYPE
           SYNTAX INTEGER
           ACCESS read-write
           STATUS mandatory
           DESCRIPTION
               "Identifies the number of extra entries in a 
               hardware assist filter CAM that the user wants to 
               have available to cover CAM entry overflow 
               conditions.  If filtering hardware is present, this 
               field defaults to 400.  Otherwise, it is zero."
           ::= { bridgeFilterLinkEntry 1 }
       
END
²
