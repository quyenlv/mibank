-- *****************************************************************
-- CISCO-QOS-PIB-CAPABILITY.my:
-- Cisco CISCO-QOS-PIB-MIB AGENT-CAPABILITIES
--
-- August 2003, Lilian Jiang 
--
-- Copyright (c) 2003 by Cisco Systesms, Inc.
-- All rights reserved.
-- *****************************************************************

CISCO-QOS-PIB-CAPABILITY DEFINITIONS ::= BEGIN

IMPORTS
        MODULE-IDENTITY
                FROM SNMPv2-SMI
        AGENT-CAPABILITIES
                FROM SNMPv2-CONF
        ciscoAgentCapability
                FROM CISCO-SMI;

ciscoQosPibCapability MODULE-IDENTITY
        LAST-UPDATED    "200308140000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of 
                CISCO-QOS-PIB-MIB."

        REVISION        "200308140000Z"
        DESCRIPTION
                "Initial version of this MIB module."
        ::= { ciscoAgentCapability 390 }

ciscoQosPibCapCatOSV08R0101Cat6K AGENT-CAPABILITIES
    PRODUCT-RELEASE     "Cisco CatOS 8.1(1) on Catalyst 6000/6500
                        and Cisco 7600 series devices."
    STATUS              current
    DESCRIPTION         "CISCO-QOS-PIB-MIB capabilities."

    SUPPORTS            CISCO-QOS-PIB-MIB
        INCLUDES        { 
                          qosDevicePibIncarnationTableGroup,
                          qosDeviceAttributeTableGroup,
                          qosInterfaceTypeTableGroup,
                          qosDiffServMappingTableGroup,
                          qosCosToDscpTableGroup,
                          qosUnmatchedPolicyTableGroup,
                          qosPolicerTableGroup,
                          qosAggregateTableGroup,
                          qosMacClassificationTableGroup,
                          qosIpAceTableGroup,
                          qosIpAclDefinitionTableGroup,
                          qosIpAclActionTableGroup,
                          qosIfSchedulingPreferencesTableGroup,
                          qosIfDropPreferenceTableGroup,
                          qosIfDscpAssignmentTableGroup,
                          qosIfRedTableGroup,
                          qosIfTailDropTableGroup,
                          qosIfWeightsTableGroup     
                        }
    ::= { ciscoQosPibCapability 1 }

END
