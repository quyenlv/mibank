-- *****************************************************************
-- ciscoWanParMIB: MIB For Portable AutoRoute(PAR) Controller
--  in MGX82xx products.
--
-- September 2002, Subra Hegde
--
-- Copyright (c) 2002 by cisco Systems, Inc.
-- All rights reserved.
-- *****************************************************************

CISCO-WAN-PAR-MIB DEFINITIONS ::= BEGIN
IMPORTS
        MODULE-IDENTITY,
        OBJECT-TYPE, 
        IpAddress,
        Integer32       FROM    SNMPv2-SMI
        MODULE-COMPLIANCE,
        OBJECT-GROUP    FROM    SNMPv2-CONF
        TruthValue,
        DisplayString   FROM    SNMPv2-TC
        par             FROM    BASIS-MIB
        ciscoWan        FROM    CISCOWAN-SMI;

ciscoWanParMIB MODULE-IDENTITY
        LAST-UPDATED    "200209100000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "The MIB module for configuring AutoRoute controller.
        The Portable AutoRoute(PAR) is a Controller providing
        routing capabilities in Network of Cisco MGX and
        BPX Switches.
        PAR controller performs following functions:
         - Connection Provisioning. Adding/Deleting/modifying
           connections
         - Connection Alarm Management. On receipt of a failure
           event, PAR sends messages to condition the connection.
         - Annex G functionality. Manages the LMI communication
           between feeder and routing node.
         - Clocking Control. PAR handles the clocking selection
           for the switch."

    REVISION    "200209100000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been 
        modified."
    ::= { ciscoWan 63 }

parSelfNode	OBJECT IDENTIFIER ::= { par 1 }
parInterfaces	OBJECT IDENTIFIER ::= { par 2 }
parConnection	OBJECT IDENTIFIER ::= { par 3 }
parNetworkClock	OBJECT IDENTIFIER ::= { par 4 }
parConfigParms	OBJECT IDENTIFIER ::= { par 5 }

parVsiConfigParms	OBJECT	IDENTIFIER	::= { parConfigParms 1 }
parCmParms		OBJECT	IDENTIFIER	::= { parConfigParms 2 }
parMnUpdt		OBJECT	IDENTIFIER	::= { parConfigParms 3 }
parSwFunc		OBJECT	IDENTIFIER	::= { parConfigParms 4 }
parOnOff		OBJECT	IDENTIFIER	::= { parConfigParms 5 }
parSysParms		OBJECT	IDENTIFIER	::= { parConfigParms 6 }
parNetworkingParms	OBJECT	IDENTIFIER	::= { parConfigParms 7 }


parSnNodeId	OBJECT-TYPE
	SYNTAX	   Integer32(1..223)
	MAX-ACCESS read-write
	STATUS	   current
	DESCRIPTION
	    " This object specifies the node number of the node.
            When the network manager tries to modify the value of 
            this object, a message is sent node state machine which 
            propagates this information and the value gets modified 
            only if the new node number is successfully propagated. 
            The node number uniquely identifies a routing node 
            in a network."
	DEFVAL  { 1 }
	::= { parSelfNode 1}

parSnNodeIP	OBJECT-TYPE
	SYNTAX	   IpAddress
	MAX-ACCESS read-write
	STATUS	   current
	DESCRIPTION
	    "This object specifies the IP address for 
            routing node and is used for communication with 
            SNMP manager(for example Cisco Wan Manager:CWM)."
	::= { parSelfNode 2}

parSnNodeName	OBJECT-TYPE
	SYNTAX	   DisplayString (SIZE (0..8))
	MAX-ACCESS read-write
	STATUS	   current
	DESCRIPTION
	    "This object specifies the name of the node 
            and is unique among all the nodes in the network. 
            Whenever the name of the node is changed, AutoRoute 
            has to propagate the information to the other nodes 
            in the network. It also specifies the name of a PAR 
            Feeder node."
	::= { parSelfNode 3}

parSnRevision	OBJECT-TYPE
	SYNTAX     DisplayString	
	MAX-ACCESS read-only
	STATUS	   current
	DESCRIPTION
	    "This object specifies the primary revision of 
            the PAR running on the node.
	    Format: cc.c.cc 
	      Where: c = one ascii character"
	::= { parSelfNode 4}

parSnNodeAlarmStatus	OBJECT-TYPE
	SYNTAX	INTEGER {
	            clear   (1),
	            minor   (2),
	            major   (3),
	            unreach (4)
	         }
	MAX-ACCESS read-only
	STATUS	   current
	DESCRIPTION
	    "This object specifies the type of alarm on the node.

             clear(1)   : No Alarm
             minor(2)   : Minor Alarm
             major(3)   : Major Alarm
             unreach(4) : Node is unreachable."
	::= { parSelfNode 5}

parSnNumberOfTrunks	OBJECT-TYPE
	SYNTAX	   Integer32 (0..255)
	MAX-ACCESS read-only
	STATUS	   current
	DESCRIPTION
	    "This object specifies the number of trunks 
            attached to the node."
	::= { parSelfNode 6}

-- parInterfaces

parIfTable	OBJECT-TYPE
	SYNTAX	   SEQUENCE OF ParIfEntry
	MAX-ACCESS not-accessible
	STATUS     current
	DESCRIPTION
	    "Table of all logical interfaces supported by PAR"
	::= { parInterfaces 1}

parIfEntry	OBJECT-TYPE
	SYNTAX	   ParIfEntry
	MAX-ACCESS not-accessible
	STATUS	   current
	DESCRIPTION	
	    "Entries for logical interfaces."
	INDEX	{ parIfLogicalInterface }
	::=	{ parIfTable 1}

ParIfEntry ::=
	SEQUENCE {
		parIfLogicalInterface	Integer32,
		parIfType		INTEGER,
		parIfOperStatus		INTEGER,
		parIfTxBw		Integer32,
		parIfRxBw		Integer32,
		parIfMaxConn		Integer32,
		parIfHiAddrMin		Integer32,
		parIfHiAddrMax		Integer32,
		parIfLoAddrMin		Integer32,
		parIfLoAddrMax		Integer32
}

parIfLogicalInterface	OBJECT-TYPE
	SYNTAX	   Integer32 (1..2147483647)
	MAX-ACCESS read-only
        STATUS	   current
	DESCRIPTION
	    "This object specifies the logical interface number."
	::= { parIfEntry 1}

parIfType	OBJECT-TYPE
	SYNTAX	INTEGER {
		userport     (1),
		routingtrunk (2),
		feedertrunk  (3),
                clkport      (4),
                virtualtrunk (5)
		}
	MAX-ACCESS read-write
	STATUS	   current
	DESCRIPTION
	    "This object specifies the type of interface.
             User ports need to be UNI interface. The trunks
             can be either UNI or NNI.

              userport(1) : UNI interface. This is for user ports.
              routingtrunk(2) : NNI interface. This value can be 
                                set provided there are no connections
                                on the interface.
              feedertrunk(3) : It is feeder trunk.
              clkport(4)     : Clock port.
              virtualtrunk(5): Virtual Trunk.
	
            Type of interface can be changed from nni(2) to uni(1) 
            if the trunk is not added."
	DEFVAL {userport }
	::= { parIfEntry 2}

parIfOperStatus OBJECT-TYPE
	SYNTAX	INTEGER {
		up           (1),
		added        (2),
		failed       (3),
		added-failed (4)
	}
	MAX-ACCESS read-only
	STATUS	   current
	DESCRIPTION
	    "This object specifies the operation status of 
            the interface.

            up(1)     : Interface is up.
                        This value is applicable for UNI as well as NNI
                        interfaces.

            added(2)  : Interface is added.
                        This value is applicable for NNI interfaces.

            failed(3) : Interface is failed.
                        This value is applicable for UNI as well as NNI
                        interfaces.
	    added-failed (4) : Interface is failed.
                        This value is applicable for NNI interfaces.
                        interfaces."
	::= { parIfEntry 3}

parIfTxBw	OBJECT-TYPE
	SYNTAX	   Integer32
        UNITS      "cells-per-second"
	MAX-ACCESS read-only
	STATUS	   current
	DESCRIPTION
	    "This object specifies the transmit bandwidth 
            for the interface."
	::= { parIfEntry 4}

parIfRxBw	OBJECT-TYPE
	SYNTAX	   Integer32
        UNITS      "cells-per-second"
	MAX-ACCESS read-only
	STATUS	   current
	DESCRIPTION
	    "This object specifies the receive bandwidth for 
             the interface."
	::= { parIfEntry 5}

parIfMaxConn	OBJECT-TYPE
	SYNTAX	   Integer32
	MAX-ACCESS read-only
	STATUS	   current
	DESCRIPTION
	    "This object specifies the maximum number
            of connections that can be configured over 
            the interface."
	::= { parIfEntry 6}

parIfHiAddrMin	OBJECT-TYPE
	SYNTAX	   Integer32
	MAX-ACCESS read-only
	STATUS	   current
	DESCRIPTION
	    "This object specifies the minimum VPI that 
            PAR can use for configuring connection in 
            the interface."
	::= { parIfEntry 7}

parIfHiAddrMax	OBJECT-TYPE
	SYNTAX	   Integer32
	MAX-ACCESS read-only
	STATUS	   current
	DESCRIPTION
	"This object specifies the maximum VPI that
        PAR can use for configuring connection in 
        the interface."
	::= { parIfEntry 8}

parIfLoAddrMin	OBJECT-TYPE
	SYNTAX	   Integer32
	MAX-ACCESS read-only
	STATUS	   current
	DESCRIPTION
	    "This object specifies the minimum VCI that 
            PAR can use for configuring connection in 
            the interface."
	::= { parIfEntry 9}

parIfLoAddrMax	OBJECT-TYPE
	SYNTAX	   Integer32
	MAX-ACCESS read-only
	STATUS	   current
	DESCRIPTION
	    "This object specifies the maximum VCI that 
            PAR can use for configuring connection in 
            the interface."
	::= { parIfEntry 10}

parTrkTable	OBJECT-TYPE
	SYNTAX	   SEQUENCE OF ParTrkEntry
	MAX-ACCESS not-accessible
	STATUS	   current
	DESCRIPTION
	    "The table containing trunk parameters."
	::= { parInterfaces 2}

parTrkEntry	OBJECT-TYPE
	SYNTAX	   ParTrkEntry
	MAX-ACCESS not-accessible
	STATUS	   current
	DESCRIPTION
	    "Entries for logical interfaces configured 
            as trunks (parIfType nni)."
	INDEX { parIfLogicalInterface }
	::= { parTrkTable 1}

ParTrkEntry ::=

	SEQUENCE {
	parTrkId                     Integer32,
	parTrkStatReserve            Integer32,
	parTrkCnfgCcRestrict         TruthValue,
	parTrkCnfgLineType           INTEGER,
	parTrkCnfgPassSync           TruthValue,
	parTrkCnfgDerouteDelay       Integer32,
	parTrkCnfgTrafficClassFst    TruthValue,
	parTrkCnfgTrafficClassFr     TruthValue,
	parTrkCnfgTrafficClassNts    TruthValue,
	parTrkCnfgTrafficClassTs     TruthValue,
	parTrkCnfgTrafficClassVoice  TruthValue,
	parTrkCnfgTrafficClassCbr    TruthValue,
	parTrkCnfgTrafficClassVbr    TruthValue,
	parTrkCnfgTrafficClassAbr    TruthValue,
	parTrkCnfgAdminStatus        INTEGER,
	parTrkCnfgRoutingCost        Integer32,
	parTrkCnfgVpcConids          Integer32,
	parTrkCnfgVccConids          Integer32,
	parTrkLocalSlotNumber        Integer32,
	parTrkLocalPortNumber        Integer32,
	parTrkLocalVTrunkId          Integer32,
	parTrkRemoteNodeId           Integer32,
	parTrkRemoteTrunkId          Integer32,
	parTrkRemoteSlotNumber       Integer32,
	parTrkRemotePortNumber       Integer32,
	parTrkRemoteVTrunkId         Integer32,
	parTrkRemoteNodeIP           IpAddress,
	parTrkRemoteNodeType         INTEGER,
	parTrkRemoteNodeName         DisplayString,
	parTrkAlarmStatus            INTEGER,
	parTrkAlarmType              INTEGER,
	parTrkLineLoad               Integer32,
	parTrkBwCapacity             Integer32
}

parTrkId	OBJECT-TYPE
	SYNTAX	   Integer32
	MAX-ACCESS read-only
	STATUS	   current
	DESCRIPTION
	    "This object specifies the logical trunk number 
            associated with the trunk at the local node."
	::= { parTrkEntry 1}

parTrkStatReserve	OBJECT-TYPE
	SYNTAX	   Integer32
        UNITS      "cells-per-second"
	MAX-ACCESS read-write
	STATUS     current
	DESCRIPTION
	    "Specifies the bandwidth reserved as Statistical 
            Reserve on the trunk in units of cells per second.
	    This object cannot take a value beyond the bandwidth 
            capacity of the trunk."
	DEFVAL  { 1000}  
	::= { parTrkEntry 2}

parTrkCnfgCcRestrict	OBJECT-TYPE
	SYNTAX	   TruthValue
	MAX-ACCESS read-write
	STATUS     current
	DESCRIPTION
	    "This object specifies the operators preference for
            routing control plane traffic on the interface.
	    If the object is set to False, then the interface may 
            be chosen for control plane traffic. If it is True, then 
            the interface is not chosen, unless there is no other 
            trunk with parIfOperStatus added(2), in which case it is 
            chosen regardless of the value of this object."
	DEFVAL	{ false }
	::= { parTrkEntry 3}

parTrkCnfgLineType	OBJECT-TYPE
	SYNTAX	INTEGER {
		terrestrial (1),
		satellite   (2)
	}
	MAX-ACCESS read-write
	STATUS	   current
	DESCRIPTION
	    "This object specifies the type of interface terrestrial 
	    or satellite. The interfaces configured as terrestrial(1) 
	    are preferred over those configured as satellite(2) for 
	    routing control plane traffic.
	    This information is also used for connections for which 
	    routing restrictions are specified."
	DEFVAL  { terrestrial }
	::= { parTrkEntry 4}

parTrkCnfgPassSync	OBJECT-TYPE
	SYNTAX	   TruthValue
	MAX-ACCESS read-write
	STATUS	   current
	DESCRIPTION
	    "This object specifies whether the trunk can be 
            used to pass clock sync.
	    If the value of this object is True, clock can be
            synchronized through the trunk; otherwise not."
	DEFVAL  { true}
	::= { parTrkEntry 5}

parTrkCnfgDerouteDelay OBJECT-TYPE
	SYNTAX     Integer32
        UNITS      "seconds"
	MAX-ACCESS read-write
	STATUS     current
	DESCRIPTION
	    "This object specifies the value of deroute delay 
            timer in seconds."
	DEFVAL { 0 }
	::= { parTrkEntry 6}

parTrkCnfgTrafficClassFst OBJECT-TYPE
	SYNTAX     TruthValue
	MAX-ACCESS read-write
	STATUS     current
	DESCRIPTION
	    "This object indicates whether Foresight traffic
            can be routed over the trunk. If the value is true(1),
            it can be rerouted otherwise not."
	DEFVAL { true }
	::= { parTrkEntry 7}

parTrkCnfgTrafficClassFr OBJECT-TYPE
	SYNTAX     TruthValue
	MAX-ACCESS read-write
	STATUS     current
	DESCRIPTION
	    "This object indicates whether Frame Relay traffic 
            can be routed over the trunk. If the value is true(1),
            it can be rerouted otherwise not."
	DEFVAL { true }
	::= { parTrkEntry 8}

parTrkCnfgTrafficClassNts OBJECT-TYPE
	SYNTAX     TruthValue
	MAX-ACCESS read-write
	STATUS     current
	DESCRIPTION
	    "This object indicates whether Non-Time Stamped 
            traffic can be routed over the trunk. If the value 
            is true(1) it can be rerouted otherwise not."
	DEFVAL { true }
	::= { parTrkEntry 9}

parTrkCnfgTrafficClassTs OBJECT-TYPE
	SYNTAX     TruthValue
	MAX-ACCESS read-write
	STATUS     current
	DESCRIPTION
	    "This object indicates whether Time Stamped 
            traffic can be routed over the trunk. If the value 
            is true(1) it can be rerouted otherwise not."
	DEFVAL { true }
	::= { parTrkEntry 10}

parTrkCnfgTrafficClassVoice OBJECT-TYPE
	SYNTAX     TruthValue
	MAX-ACCESS read-write
	STATUS     current
	DESCRIPTION
	    "This object indicates whether Voice traffic 
            can be routed over the trunk. If the value is 
            true(1), it can be rerouted otherwise not."
	DEFVAL { true }
	::= { parTrkEntry 11}

parTrkCnfgTrafficClassCbr OBJECT-TYPE
	SYNTAX     TruthValue
	MAX-ACCESS read-write
	STATUS     current
	DESCRIPTION
	    "This object indicates whether Constant Bit Rate 
            traffic can be routed over the trunk. If the value 
            is true(1), it can be rerouted otherwise not."
	DEFVAL { true }
	::= { parTrkEntry 12}

parTrkCnfgTrafficClassVbr OBJECT-TYPE
	SYNTAX     TruthValue
	MAX-ACCESS read-write
	STATUS     current
	DESCRIPTION
	    "This object indicates whether Variable Bit Rate 
            traffic can be routed over the trunk. If the value 
            is true(1), it can be rerouted otherwise not."
	DEFVAL { true }
	::= { parTrkEntry 13}
 
parTrkCnfgTrafficClassAbr OBJECT-TYPE
	SYNTAX     TruthValue
	MAX-ACCESS read-write
	STATUS     current
	DESCRIPTION
	    "This object indicates whether Available Bit Rate 
            traffic can be routed over the trunk. If the value 
            is true(1), it can be rerouted otherwise not."
	DEFVAL { true }
	::= { parTrkEntry 14}

parTrkCnfgAdminStatus OBJECT-TYPE
	SYNTAX INTEGER {
		add (1),
		delete (2)
	}
	MAX-ACCESS read-write
	STATUS     current
	DESCRIPTION
	    "This object can be used to add or delete the trunk. 
            The value of this object can be set to add(1) only 
            if the parIfOperStatus is up(1). The value can be 
            set to delete if parIfOperStatus is added or 
            added-failed"
	DEFVAL { delete }
	::= { parTrkEntry 15}

parTrkCnfgRoutingCost OBJECT-TYPE
	SYNTAX     Integer32 (1..15)
	MAX-ACCESS read-write
	STATUS     current
	DESCRIPTION
	    "This object specifies the cost associated with 
            the trunk for the purpose of routing the connections.
            This object has significance if cost based routing 
            feature is enabled(parCmParmsCostBased)"
	DEFVAL { 7 }
	::= { parTrkEntry 16}

parTrkCnfgVccConids OBJECT-TYPE
	SYNTAX     Integer32
	MAX-ACCESS read-write
	STATUS     current
	DESCRIPTION 
	    "The maximum number of routing resource available 
            on the trunk for VCC connections."
	::= { parTrkEntry 17}

parTrkCnfgVpcConids OBJECT-TYPE
	SYNTAX     Integer32
	MAX-ACCESS read-write
	STATUS     current
	DESCRIPTION
	    "The maximum number of routing resource available 
            on the trunk for VPC connections"
	::= { parTrkEntry 18}

parTrkLocalSlotNumber OBJECT-TYPE
	SYNTAX     Integer32 (1..32)
	MAX-ACCESS read-only
	STATUS     current
	DESCRIPTION 
	    "This object specifies the slot number of the 
            interface card associated with the trunk at the 
            local node."
	::= { parTrkEntry 19}

parTrkLocalPortNumber OBJECT-TYPE
	SYNTAX     Integer32 (1..2147483647)
	MAX-ACCESS read-only
	STATUS     current
	DESCRIPTION
	"This object specifies the port number of the interface card 
	associated with the trunk at the local node."
	::= { parTrkEntry 20}

parTrkLocalVTrunkId OBJECT-TYPE
	SYNTAX     Integer32 (1..255)
	MAX-ACCESS read-only
	STATUS     current
	DESCRIPTION
	    "This object specifies the Virtual trunk of the 
            interface card associated with the trunk at the 
            local node. The value of this object is between 
            1 and 254, inclusive for a virtual trunk and 
	    255 for a physical trunk."
	::= { parTrkEntry 21}

parTrkRemoteNodeId OBJECT-TYPE
	SYNTAX     Integer32 (1..223)
	MAX-ACCESS read-only
	STATUS     current
	DESCRIPTION 
	    "This object specifies the node number of the 
            node attached to the remote end of the trunk."
	::= { parTrkEntry 22}

parTrkRemoteTrunkId OBJECT-TYPE
	SYNTAX     Integer32 (1..255)
	MAX-ACCESS read-only
	STATUS     current
	DESCRIPTION 
	    "This object specifies the logical trunk number 
            at the node on the remote end of the trunk."
	::= { parTrkEntry 23}

parTrkRemoteSlotNumber OBJECT-TYPE
	SYNTAX     Integer32 (1..32)
	MAX-ACCESS read-only
	STATUS     current
	DESCRIPTION
	    "This object specifies the slot number of the 
            interface card to which the trunk is attached 
            on the remote node."
	::= { parTrkEntry 24}

parTrkRemotePortNumber OBJECT-TYPE
	SYNTAX     Integer32 (1..2147483647)
	MAX-ACCESS read-only
	STATUS     current
	DESCRIPTION
	    "This object specifies the port number of the
            interface card to which the trunk is attached 
            on the remote node."
	::= { parTrkEntry 25}

parTrkRemoteVTrunkId OBJECT-TYPE
	SYNTAX     Integer32 (1..255)
	MAX-ACCESS read-only
	STATUS     current
	DESCRIPTION 
	    "This object specifies the Virtual trunk of the 
            interface card associated with the trunk at the 
            remote node. The value of this object is between 
            1 and 254, inclusive for a virtual trunk and 255
            for a physical trunk."
	::= { parTrkEntry 26}

parTrkRemoteNodeIP OBJECT-TYPE
	SYNTAX     IpAddress
	MAX-ACCESS read-only
	STATUS     current
	DESCRIPTION
            "This object specifies the IP address for the 
	    Remote node, used for communication with NMS"
	::= { parTrkEntry 27}

parTrkRemoteNodeType OBJECT-TYPE
	SYNTAX INTEGER{
		ipx (1),
		igx (2),
		bpx (3),
		par (4),
		unknown (5)
		}
	MAX-ACCESS read-only
	STATUS     current
	DESCRIPTION
	    "Specifies the type of the node."
	::= { parTrkEntry 28}

parTrkRemoteNodeName OBJECT-TYPE
	SYNTAX     DisplayString
	MAX-ACCESS read-only
	STATUS     current
	DESCRIPTION
	   "This object specifies the name of the remote 
           node and is unique among all the nodes in the network."
	::= { parTrkEntry 29}

parTrkAlarmStatus OBJECT-TYPE
	SYNTAX INTEGER {
	           clear (1),
	           minor (2),
	           major (3)
	       }
	MAX-ACCESS read-only
	STATUS     current
	DESCRIPTION
	    "This object specifies the severity of the alarm 
            on the trunk.

             clear(1)   : No Alarm
             minor(2)   : Minor Alarm
             major(3)   : Major Alarm."
	::= { parTrkEntry 30}

parTrkAlarmType OBJECT-TYPE
	SYNTAX INTEGER{
	           rsrcunavail (1),
	           commfail (2),
	           unknown (3),
                   failed (4),
                   looped (5)
               }
	MAX-ACCESS read-only
	STATUS     current
	DESCRIPTION 
	    "This object specifies the type of alarm on 
            the trunk. The value of this object has no 
            significance if parTrunkAlarmStatus indicates no alarm.

	    rsrcunavail(1) : resources unavailable indicates that 
                             the platform has not provided the resources 
                             required to make this interface into a trunk.
	    commfail(2)    : communication failure indicates that message 
                             exchanged between neighboring nodes on this 
                             trunk has failed.
	    unknown (3)    : indicates that the alarm type is unknown to PAR, 
	                     for example if the platform has declared the 
                             interface in alarm due to some physical problem 
                             with the interface."
	::= { parTrkEntry 31}

parTrkBwCapacity OBJECT-TYPE
	SYNTAX     Integer32
	MAX-ACCESS read-only
	STATUS     current
	DESCRIPTION
	    "Specifies the bandwidth capacity of the trunk."
	::= { parTrkEntry 32}

parTrkLineLoad OBJECT-TYPE
	SYNTAX     Integer32
	MAX-ACCESS read-only
	STATUS     current
	DESCRIPTION
	    "Specifies the bandwidth used by the connections 
            routed over the trunk."
	::= { parTrkEntry 33}

parTrkLoadTable OBJECT-TYPE
	SYNTAX     SEQUENCE OF ParTrkLoadEntry
	MAX-ACCESS not-accessible
	STATUS     current
	DESCRIPTION 
	    "Trunk Load Information"
	::= { parInterfaces 3}

parTrkLoadEntry OBJECT-TYPE
	SYNTAX     ParTrkLoadEntry
	MAX-ACCESS not-accessible
	STATUS     current
	DESCRIPTION
	    "Load info for logical interfaces configured as 
            trunks (parIfType nni)."
	INDEX { parIfLogicalInterface }
	::= { parTrkLoadTable 1}

ParTrkLoadEntry ::=
	SEQUENCE {
		parTrkLoadXmtUsedCbr	Integer32,
		parTrkLoadRcvUsedCbr	Integer32,
		parTrkLoadXmtUsedVbr	Integer32,
		parTrkLoadRcvUsedVbr	Integer32,
		parTrkLoadXmtUsedAbr	Integer32,
		parTrkLoadRcvUsedAbr	Integer32,
		parTrkLoadXmtUsedNts	Integer32,
		parTrkLoadRcvUsedNts	Integer32,
		parTrkLoadXmtUsedTs	Integer32,
		parTrkLoadRcvUsedTs	Integer32,
		parTrkLoadXmtUsedVoice	Integer32,
		parTrkLoadRcvUsedVoice	Integer32,
		parTrkLoadXmtUsedBdataA	Integer32,
		parTrkLoadRcvUsedBdataA	Integer32,
		parTrkLoadXmtUsedBdataB	Integer32,
		parTrkLoadRcvUsedBdataB	Integer32,
		parTrkLoadVccConidsUsed	Integer32,
		parTrkLoadVpcConidsUsed	Integer32
	}

parTrkLoadXmtUsedCbr OBJECT-TYPE
	SYNTAX     Integer32
	MAX-ACCESS read-only
	STATUS     current
	DESCRIPTION
	    "This object specifies the used bandwidth in the 
            transmit direction for CBR traffic."
	::= { parTrkLoadEntry 1}

parTrkLoadRcvUsedCbr OBJECT-TYPE
	SYNTAX     Integer32
	MAX-ACCESS read-only
	STATUS     current
	DESCRIPTION
	    "This object specifies the used bandwidth in the 
            receive direction for CBR traffic"
	::= { parTrkLoadEntry 2}

parTrkLoadXmtUsedVbr OBJECT-TYPE
	SYNTAX     Integer32
	MAX-ACCESS read-only
	STATUS     current
	DESCRIPTION
	    "This object specifies the used bandwidth in the 
            transmit direction for VBR traffic."
	::= { parTrkLoadEntry 3}

parTrkLoadRcvUsedVbr OBJECT-TYPE
	SYNTAX     Integer32
	MAX-ACCESS read-only
	STATUS     current
	DESCRIPTION
	    "This object specifies the used bandwidth in the 
            receive direction for VBR traffic."
	::= { parTrkLoadEntry 4}

parTrkLoadXmtUsedAbr OBJECT-TYPE
	SYNTAX     Integer32
	MAX-ACCESS read-only
	STATUS     current
	DESCRIPTION
	    "This object specifies the used bandwidth in the 
            transmit direction for ABR."
	::= { parTrkLoadEntry 5}

parTrkLoadRcvUsedAbr OBJECT-TYPE
	SYNTAX     Integer32
	MAX-ACCESS read-only
	STATUS     current
	DESCRIPTION 
	    "This object specifies the used bandwidth in the 
            receive direction for ABR."
	::= { parTrkLoadEntry 6}

parTrkLoadXmtUsedNts OBJECT-TYPE
	SYNTAX     Integer32
	MAX-ACCESS read-only
	STATUS     current
	DESCRIPTION
	    "This object specifies the used bandwidth in the 
            transmit direction for Non-Time Stamped."
	::= { parTrkLoadEntry 7}

parTrkLoadRcvUsedNts OBJECT-TYPE
	SYNTAX     Integer32
	MAX-ACCESS read-only
	STATUS     current
	DESCRIPTION
	    "This object specifies the used bandwidth in the
            receive direction for Non-Time Stamped."
	::= { parTrkLoadEntry 8}

parTrkLoadXmtUsedTs OBJECT-TYPE
	SYNTAX     Integer32
	MAX-ACCESS read-only
	STATUS     current
	DESCRIPTION
	    "This object specifies the used bandwidth in the
            transmit direction for Time-Stamped."
	::= { parTrkLoadEntry 9}
	
parTrkLoadRcvUsedTs OBJECT-TYPE
	SYNTAX     Integer32
	MAX-ACCESS read-only
	STATUS     current
	DESCRIPTION
	    "This object specifies the used bandwidth in the
            receive direction for Time-Stamped."
	::= { parTrkLoadEntry 10}

parTrkLoadXmtUsedVoice OBJECT-TYPE
	SYNTAX     Integer32
	MAX-ACCESS read-only
	STATUS     current
	DESCRIPTION
	    "This object specifies the used bandwidth in the 
            transmit direction for Voice."
	::= { parTrkLoadEntry 11}

parTrkLoadRcvUsedVoice OBJECT-TYPE
	SYNTAX     Integer32
	MAX-ACCESS read-only
	STATUS     current
	DESCRIPTION
	    "This object specifies the used bandwidth in the
            receive direction for Voice."
	::= { parTrkLoadEntry 12}
	
parTrkLoadXmtUsedBdataA OBJECT-TYPE
	SYNTAX     Integer32
	MAX-ACCESS read-only
	STATUS     current
	DESCRIPTION
            "This object specifies the used bandwidth in the 
	    transmit direction for Busty Data A."
	::= { parTrkLoadEntry 13}

parTrkLoadRcvUsedBdataA OBJECT-TYPE
	SYNTAX     Integer32
	MAX-ACCESS read-only
	STATUS     current
	DESCRIPTION
            "This object specifies the used bandwidth in the 
	    receive direction for Bursty Data A."
	::= { parTrkLoadEntry 14}

parTrkLoadXmtUsedBdataB OBJECT-TYPE
	SYNTAX     Integer32
	MAX-ACCESS read-only
	STATUS     current
	DESCRIPTION
	    "This object specifies the used bandwidth in the 
            transmit direction for Bursty Data B."
	::= { parTrkLoadEntry 15}

parTrkLoadRcvUsedBdataB OBJECT-TYPE
	SYNTAX     Integer32
	MAX-ACCESS read-only
	STATUS     current
	DESCRIPTION
	    "This object specifies the used bandwidth in the 
            receive direction for Bursty Data B."
	::= { parTrkLoadEntry 16}
	
parTrkLoadVccConidsUsed	OBJECT-TYPE
	SYNTAX     Integer32
	MAX-ACCESS read-only
	STATUS     current
	DESCRIPTION
	    "This object specifies the number of conids used 
            for VCCs (not used) on the trunk."
	::= { parTrkLoadEntry 17}

parTrkLoadVpcConidsUsed	OBJECT-TYPE
	SYNTAX     Integer32
	MAX-ACCESS read-only
	STATUS     current
	DESCRIPTION
	    "This object specifies the number of conids 
            Used for VPCs (not used) on the trunk."
	::= { parTrkLoadEntry 19}

-- parConnection

parConnectionTable OBJECT-TYPE
	SYNTAX     SEQUENCE OF ParConnectionEntry
	MAX-ACCESS not-accessible
	STATUS     current
	DESCRIPTION
	   "This table contains connections Mastered or slaved 
           by the node."
	::= { parConnection 1}

parConnectionEntry OBJECT-TYPE
	SYNTAX     ParConnectionEntry
	MAX-ACCESS not-accessible
	STATUS     current
	DESCRIPTION
	    "Entries for connections mastered or slaved 
            by the node. Each entry contains Local and
            remote end information."
	INDEX { parConnLocalSlot, 
                parConnLocalPort, 
                parConnLocalVpi, 
                parConnLocalVci 
              }
	::= { parConnectionTable 1}

ParConnectionEntry ::=
SEQUENCE {
	parConnLocalSlot	Integer32,
	parConnLocalPort	Integer32,
	parConnLocalVpi		Integer32,
	parConnLocalVci		Integer32,
        parConnMasterShip       TruthValue,
	parConnLocalVcIndx	Integer32,
        parConnLocalEndpt       DisplayString,
	parConnRemoteNodeName	DisplayString,
	parConnRemoteSlot	Integer32,
	parConnRemotePort	Integer32,
	parConnRemoteVpi	Integer32,
	parConnRemoteVci	Integer32,
	parConnRemoteVcIndx	Integer32,
        parConnRemoteEndpt      DisplayString,
	parConnOperStatus	INTEGER,
	parConnAdminStatus	INTEGER,
	parConnRoute		DisplayString,
        parPrefRoute            DisplayString,
        parConnFailRsn          INTEGER,
        parRrtFailRsn           DisplayString,
	parConnRstrTyp		INTEGER,
	parConnRstrZcs		TruthValue,
        parConnCos              Integer32
}

parConnLocalSlot OBJECT-TYPE
	SYNTAX     Integer32(1..32)
	MAX-ACCESS read-only
	STATUS     current
	DESCRIPTION
	    "This object specifies the slot number part of the 
            local endpoint connection address."
	::= { parConnectionEntry 1}

parConnLocalPort OBJECT-TYPE
	SYNTAX     Integer32 (1..2147483647)
	MAX-ACCESS read-only
	STATUS     current
	DESCRIPTION
	    "This object specifies the port number part of the
            local endpoint connection address."
	::= { parConnectionEntry 2}

parConnLocalVpi OBJECT-TYPE
	SYNTAX     Integer32 (0..4095)
	MAX-ACCESS read-only
	STATUS     current
	DESCRIPTION 
	    "This object specifies the Virtual Path Identifier 
            part of the local endpoint connection address."
	::= { parConnectionEntry 3}

parConnLocalVci OBJECT-TYPE
	SYNTAX     Integer32 (0..65535)
	MAX-ACCESS read-only
	STATUS     current
	DESCRIPTION
	    "This object specifies the Virtual Channel Identifier 
            part of the local endpoint connection address."
	::= { parConnectionEntry 4}

parConnMasterShip OBJECT-TYPE
	SYNTAX     TruthValue
	MAX-ACCESS read-only
	STATUS     current
	DESCRIPTION
            "This object specifies whether this end of the 
            connection is the master or the slave of the 
            connection. The value true(1) signifies the
            master end and false(2) signifies slave end."
	::= { parConnectionEntry 5}

parConnLocalVcIndx OBJECT-TYPE
	SYNTAX     Integer32
	MAX-ACCESS read-only
	STATUS     current
	DESCRIPTION 
	    "This object specifies the Virtual Connection Index 
            at this node. It is used by Network Management to 
            correlate this end of the connection with the remote end."
	::= { parConnectionEntry 6}

parConnLocalEndpt OBJECT-TYPE
        SYNTAX     DisplayString
        MAX-ACCESS read-only
        STATUS     current
        DESCRIPTION
            "This object specifies the actual physical connection 
            endpoint at the local node."
        ::= { parConnectionEntry 7}

parConnRemoteNodeName OBJECT-TYPE
	SYNTAX     DisplayString
	MAX-ACCESS read-only
	STATUS     current
	DESCRIPTION
	    "This object specifies the node name of the 
            remote endpoint. For a intra-switch connection 
            or feeder connection this object would specify 
            the self node name."
	::= { parConnectionEntry 8}

parConnRemoteSlot OBJECT-TYPE
	SYNTAX     Integer32 (1..32)
	MAX-ACCESS read-only
	STATUS     current
	DESCRIPTION
	    "This object specifies the slot number part of 
            the remote endpoint connection address."
	::= { parConnectionEntry 9}

parConnRemotePort OBJECT-TYPE
	SYNTAX     Integer32 (1..2147483647)
	MAX-ACCESS read-only
	STATUS     current
	DESCRIPTION
	    "This object specifies the port number part of
            the remote endpoint connection address."
	::= { parConnectionEntry 10}

parConnRemoteVpi OBJECT-TYPE
	SYNTAX     Integer32
	MAX-ACCESS read-only
	STATUS     current
	DESCRIPTION
	    "This object specifies the VPI part of the 
            remote endpoint connection address."
	::= { parConnectionEntry 11}

parConnRemoteVci OBJECT-TYPE
	SYNTAX     Integer32 
	MAX-ACCESS read-only
	STATUS     current
	DESCRIPTION
	    "This object specifies the VCI part of the 
            remote endpoint connection address."
	::= { parConnectionEntry 12}

parConnRemoteVcIndx OBJECT-TYPE
	SYNTAX     Integer32
	MAX-ACCESS read-only
	STATUS     current
	DESCRIPTION
	    "This object specifies the Virtual Connection Index 
            at the remote node. It is used by Network Management 
            to correlate this end of the connection with the 
            remote end.."
	::= { parConnectionEntry 13}

parConnOperStatus OBJECT-TYPE
        SYNTAX INTEGER {
	           routed   (1),
           	   unrouted (2),
                   lmifail  (3),
           	   unknown  (4)
	       }
	MAX-ACCESS read-only
	STATUS     current
	DESCRIPTION
	    "This object specifies the status of connection 
           as known and determined by PAR. The status shall be 
           OK if there is an A-bit alarm on the connection."
	::= { parConnectionEntry 14}

parConnAdminStatus OBJECT-TYPE
	SYNTAX INTEGER {
	           down    (1),
                   up      (2),
                   reroute (3)
	}
	MAX-ACCESS read-write
	STATUS     current
	DESCRIPTION
	    "This object is used by the operator to reroute
            or down/up a connection. The value of this object 
            is up(1) when the connection is created. 

            If the value of the object is set to down(1) 
            the connection is derouted (if it is routed) and 
	    parConnOperStatus object is set to not routed.

	    If the value of the object is up (2) and it is set 
            to reroute(3) the connection is derouted and attempt 
            is made to reroute the connection. If the value of the 
            object is down (1) and the it is set to reroute (3), 
            no action is performed and the object's value does not 
            changes. 

            If the value of object is down(1) and is set to up(2),
            an attempt is made to reroute the connection."
	DEFVAL { up }
	::= { parConnectionEntry 15}

parConnRoute OBJECT-TYPE
	SYNTAX     DisplayString
	MAX-ACCESS read-only
	STATUS     current
	DESCRIPTION
	    "This object specifies the current path on which 
            the connection is routed. A value of this object is 
            valid only if parConnOperStatus is routed. 
            The Null string specifies that the connection is not 
            routed.

	    Format: Nodename {Trk--Trk Nodename}
	        Where: Nodename = up to 8 characters,
                       Trk = slot.port.vtrk, 
	                 slot = 1 or 2 characters, 
                         port = 1 or two characters, and 
	                 vtrk = 1 or two characters and is optional. 
                The portion of the format shown in braces {like this}
                can be repeated up to 10 times."
	::= { parConnectionEntry 16}

parConnRemoteEndpt OBJECT-TYPE
        SYNTAX     DisplayString
        MAX-ACCESS read-only
        STATUS     current
        DESCRIPTION
            "This object specifies the actual physical connection 
            endpoint at the remote end of the connection. It shall 
            be known only if the connection is a local(DAX) connection."
        ::= { parConnectionEntry 17}

parPrefRoute OBJECT-TYPE
	SYNTAX     DisplayString
	MAX-ACCESS read-write
	STATUS     current
	DESCRIPTION
	    "This object specifies the preferred path for 
            the connection. The Null string specifies that 
            the connection does not have a preferred route.

	    Format: Nodename {Trk--Trk Nodename}
	        Where: Nodename = up to 8 characters, 
                       Trk = slot.port.vtrk, 
	                  slot = 1 or 2 characters,
                          port = 1 or two characters, and 
	                  vtrk = 1 or two characters and is optional. 
                 The portion of the format shown in braces {like this} 
                 can be repeated up to 10 times."
	::= { parConnectionEntry 18}

parConnFailRsn OBJECT-TYPE
        SYNTAX INTEGER {
            down(1),
            hwalm(2),
            abitalm(3),
            lmifail(4),
            rrtfail(5),
            incomplete(6)
        }
        MAX-ACCESS read-only
	STATUS     current 
        DESCRIPTION
            "This object specifies a reason code for the 
            failure of the connection."
        ::= {parConnectionEntry 19}

parRrtFailRsn OBJECT-TYPE
	SYNTAX     DisplayString
	MAX-ACCESS read-only
	STATUS     current
	DESCRIPTION
	    "This object specifies the Reason of failure of 
            a connection to route."
	::= {parConnectionEntry 20}

parConnRstrTyp OBJECT-TYPE
	SYNTAX INTEGER {
	           norestrict    (1),
           	   terrestrict   (2),
           	   satrestrict   (3),
           	   undefrestrict (4)
	        }
	MAX-ACCESS read-only
	STATUS     current
	DESCRIPTION
	    "This object specifies the Route restriction 
            of a connection." 
	::= {parConnectionEntry 21}
	
parConnRstrZcs OBJECT-TYPE
	SYNTAX     TruthValue
	MAX-ACCESS read-only
	STATUS     current
	DESCRIPTION
	    "This object specifies whether ZCS lines should 
            be avoided or not."
	::= {parConnectionEntry 22}

parConnCos OBJECT-TYPE
	SYNTAX     Integer32 (0..15)
	MAX-ACCESS read-only
	STATUS     current
	DESCRIPTION
	    "This object specifies the COS for the connection."
	::= {parConnectionEntry 23}

-- parNetworkClock

parClockTable OBJECT-TYPE
	SYNTAX     SEQUENCE OF ParClockEntry
	MAX-ACCESS not-accessible
	STATUS     current
	DESCRIPTION
	    "Table of clock sources available to PAR"
	::= { parNetworkClock 1}

parClockEntry OBJECT-TYPE
	SYNTAX     ParClockEntry
	MAX-ACCESS not-accessible
	STATUS     current
	DESCRIPTION
            "Each entry represent a clock source available to 
            PAR"
	INDEX { parClockIndex }
	::= { parClockTable 1}

ParClockEntry ::= SEQUENCE {
	parClockIndex       Integer32,
	parClockType        INTEGER,
        parClockCurSource   TruthValue,
	parClockSource      INTEGER,
	parClockSourceId    Integer32,
        parClockPath        DisplayString
       }
	
parClockIndex OBJECT-TYPE
	SYNTAX     Integer32 (1..2147483647)
	MAX-ACCESS read-only
	STATUS     current
	DESCRIPTION
	    "This clock index is assigned by PAR."
	::= { parClockEntry 1}

parClockType OBJECT-TYPE
	SYNTAX INTEGER{
		primary   (1),
		secondary (2),
		tertiary  (3),
                null      (4)
	}
	MAX-ACCESS read-write
	STATUS     current
	DESCRIPTION
	    "Specifies the type of clock."
	::= { parClockEntry 2}
	
parClockSource OBJECT-TYPE
	SYNTAX INTEGER{
	           internal  (1),
                   interface (2),
                   external  (3)
               }
	MAX-ACCESS read-only
	STATUS     current
	DESCRIPTION
	    "Specifies source of the clock."
	DEFVAL { internal }
	::= { parClockEntry 3}

parClockCurSource OBJECT-TYPE
        SYNTAX     TruthValue
        MAX-ACCESS read-only
        STATUS     current
        DESCRIPTION
        "Specifies whether clock source is a current clock source or not. The 
         value is true if the cloock source is current and false otherwise"
        DEFVAL {false}
        ::= { parClockEntry 4}

parClockSourceId OBJECT-TYPE
	SYNTAX     Integer32 
	MAX-ACCESS read-write
	STATUS     current
	DESCRIPTION
	    "Specifies identification of the clock - for example 
            - if clock source is `Interface' then this field will
            carry logical interface number"
	::= { parClockEntry 5}

parClockPath OBJECT-TYPE
        SYNTAX     DisplayString
        MAX-ACCESS read-only
        STATUS     current
        DESCRIPTION
            "Describes the path used for clock synchronization"
        ::= { parClockEntry 6}

parCmParmsMaxRoutingBundle OBJECT-TYPE
	SYNTAX     Integer32
	MAX-ACCESS read-write
	STATUS     current
	DESCRIPTION
	    "This object specifies the maximum number of 
            connections that can be routed in one routing cycle."
	DEFVAL { 24 }
	::= { parCmParms 1}

parCmParmsRerouteTimer OBJECT-TYPE
	SYNTAX     Integer32
	MAX-ACCESS read-write
	STATUS     current
	DESCRIPTION
	    "This object specifies the minimum time after 
            which a connection is routed once it has been 
            successfully routed."
	DEFVAL { 0 }
	::= { parCmParms 2}

parCmParmsResetTimer OBJECT-TYPE
	SYNTAX     TruthValue
	MAX-ACCESS read-write
	STATUS     current
	DESCRIPTION
	    "This object specifies whether the reroute timer 
            should be reset if the path for routed connection 
            failed.  If the value of the object is true(1), the 
            timer is reset on detecting path fail."
	DEFVAL { true }
	::= { parCmParms 3}

parCmParmsDnUpPerPass OBJECT-TYPE
	SYNTAX     Integer32
	MAX-ACCESS read-write
	STATUS     current
	DESCRIPTION
	    "This object specifies the maximum number of 
            connections that are upped or down in one schedule 
            of down connection state machine."
	DEFVAL { 50 }
	::= { parCmParms 4}

parCmParmsDnUpTimer OBJECT-TYPE
	SYNTAX     Integer32
        UNITS      "milliseconds"
	MAX-ACCESS read-write
	STATUS     current
	DESCRIPTION
	    "This object specifies the minimum time interval 
           (in milliseconds) between two schedules of the down 
           connection state machine."
	DEFVAL { 30000 }
	::= { parCmParms 5}

parCmParmsRrtErrsPerCycle OBJECT-TYPE
	SYNTAX     Integer32
	MAX-ACCESS read-write
	STATUS     current
	DESCRIPTION
	    "This object specifies the threshold for number 
            of failures to route a connection before it is 
            moved into the wait group. If the value of this 
            object is zero, the feature is disabled."
	DEFVAL { 50 }
	::= { parCmParms 6}

parCmParmsRrtCycleInterval OBJECT-TYPE
	SYNTAX     Integer32
        UNITS      "minutes"
	MAX-ACCESS read-write
	STATUS     current
	DESCRIPTION
	    "This object specifies the time (in minutes) for 
            which no attempt is made to route a connection in 
            the wait group."
	DEFVAL { 5 }
	::= { parCmParms 7}

parCmParmsMaxRrtCycles OBJECT-TYPE
	SYNTAX     Integer32
	MAX-ACCESS read-write
	STATUS     current
	DESCRIPTION
	    "This object specifies the number of times a 
            connection is added to the wait group before 
            declaring it unroutable."
	DEFVAL { 10 }
	::= { parCmParms 8}

parCmParmsRrtPauseTime OBJECT-TYPE
	SYNTAX     Integer32
        UNITS      "milliseconds"
	MAX-ACCESS read-write
	STATUS     current
	DESCRIPTION
	    "This object specifies the time interval 
            (in milliseconds) between two routing cycles."
	DEFVAL { 0 }
	::= { parCmParms 9}

parCmParmsMaxUpdates OBJECT-TYPE
	SYNTAX     Integer32
	MAX-ACCESS read-write
	STATUS     current
	DESCRIPTION
	    "This object specifies the maximum number of 
            connection management updates that are sent by 
            the node in schedule.."
	DEFVAL { 10 }
	::= { parCmParms 10}

parCmParmsRerouteGroups OBJECT-TYPE
	SYNTAX     Integer32
	MAX-ACCESS read-write
	STATUS     current
	DESCRIPTION
	    "This object specifies the total number of 
            reroute groups."
	DEFVAL { 50 }
	::= { parCmParms 11}

parCmParmsMinRrGroupSize OBJECT-TYPE
	SYNTAX     Integer32
	MAX-ACCESS read-write
	STATUS     current
	DESCRIPTION
	    "This object specifies the minimum size of 
            reroute group in Cell Load Units."
	DEFVAL { 0 }
	::= { parCmParms 12}

parCmParmsRrGroupInc OBJECT-TYPE
	SYNTAX     Integer32
	MAX-ACCESS read-write
	STATUS     current
	DESCRIPTION
	    "This object specifies the increment of 
            reroute group size (in Cell Load Units) 
            between adjacent groups."
	DEFVAL { 100 }
	::= { parCmParms 13}

parCmParmsCostBased OBJECT-TYPE
	SYNTAX     TruthValue
	MAX-ACCESS read-write
	STATUS     current
	DESCRIPTION
	    "This object can be configured to enable 
            or disable cost based routing feature. 
           If the value of this object is true(1),
           the feature is enabled else it is disabled."
	DEFVAL { false }
	::= { parCmParms 14}

parCmParmsUseCache OBJECT-TYPE
	SYNTAX     TruthValue
	MAX-ACCESS read-write
	STATUS     current
	DESCRIPTION
	    "This object can be configured to enable or disable 
            hop based route selection from using cache of 
            precomputed routes. 
	    If the value of this object is true(1), the feature is 
            enabled else it is disabled."
	DEFVAL { false }
	::= { parCmParms 15}
	
parCmParmsUseDelay OBJECT-TYPE
	SYNTAX     TruthValue
	MAX-ACCESS read-write
	STATUS     current
	DESCRIPTION
	    "This object can be configured to enable 
            or disable cost based route selection from 
            considering end-to-end delay associated with 
            the routes. If the value of this object is true(1),
            the delay would be considered otherwise daley would 
	    not be considered during routing of connection."
	DEFVAL { false }
	::= { parCmParms 16}

parCmParmMaxViaCons OBJECT-TYPE
	SYNTAX     Integer32 (1..80000)
	MAX-ACCESS read-write
	STATUS     current
	DESCRIPTION
	    "This object specifies the maximum number of
           via user connections that can be routed through 
           the node."
	DEFVAL { 50000 }
	::= { parCmParms 17}

parMnUpdtInterval OBJECT-TYPE
	SYNTAX     Integer32
        UNITS      "seconds"
	MAX-ACCESS read-write
	STATUS     current
	DESCRIPTION
	    "This object specifies the timer interval 
           (in seconds) for the current update state machine."
	DEFVAL { 15 }
	::= { parMnUpdt 1}

parMnUpdtNodesPerInt OBJECT-TYPE
	SYNTAX     Integer32
	MAX-ACCESS read-write
	STATUS     current
	DESCRIPTION
	    "This object specifies the maximum number of 
            nodes to which current updates can be sent per
            interval."
	DEFVAL { 20 }
	::= { parMnUpdt 2}

parMnUpdtBatchSend OBJECT-TYPE
	SYNTAX     TruthValue
	MAX-ACCESS read-write
	STATUS     current
	DESCRIPTION 
	    "This object specifies whether current updates 
            to any node are sent one at a time or all in one go.
            If the value of this object is true(1), all current 
            updates are sent to the node simultaneously. 
            If the value of this object is False, current updates 
            are sent one at a time."
	DEFVAL { true }
	::= { parMnUpdt 3}

parSwFuncAbrVsvd OBJECT-TYPE
	SYNTAX     TruthValue
	MAX-ACCESS read-write
	STATUS     current
	DESCRIPTION
	    "This object enables/disables the ABR standard 
            with VSVD. The feature is enabled if the value 
           of the object is true(1)."
	DEFVAL { false }
	::= { parSwFunc 1}

parSwFuncNodeType OBJECT-TYPE
	SYNTAX INTEGER {
	           routing (1),
                   feeder  (2)
	}
	MAX-ACCESS read-write
	STATUS     current
	DESCRIPTION
	    "This object specifies whether the node is a 
            routing node or a feeder node. To configure the 
            node from a routing(1) node to feeder(2) node 
            the node should be part of a single node network.
	    To configure the node from feeder node to routing
            node, there should be no feeder trunk attached to 
            the node."
	DEFVAL { routing }
	::= { parSwFunc 2}

parOnOffBackgroundUpdt OBJECT-TYPE
	SYNTAX     TruthValue
	MAX-ACCESS read-write
	STATUS     current
	DESCRIPTION 
	    "This object can be used to enable or disable 
            Background updates. If the value of the object 
            is true(1), background updates are enabled; 
            otherwise they are disabled."
	DEFVAL { false }
	::= { parOnOff 1}

parOnOffDynamicBwAlloc OBJECT-TYPE
	SYNTAX     TruthValue
	MAX-ACCESS read-write
	STATUS     current
	DESCRIPTION 
	    "This object can be used to enable or disable 
            Bandwidth state machine. If the value of the 
            object is true(1), bandwidth state machine is 
            enabled; otherwise it is disabled."
	DEFVAL { true }
	::= { parOnOff 2}

parOnOffCmUpdts OBJECT-TYPE
	SYNTAX     TruthValue
	MAX-ACCESS read-write
	STATUS     current
	DESCRIPTION
	    "This object can be used to enable or disable 
            connection management updates. If the value of 
            the object is true(1), connection management 
            updates are enabled; otherwise they are disabled."
	DEFVAL { true }
	::= { parOnOff 3}

parOnOffRouting OBJECT-TYPE
	SYNTAX     TruthValue
	MAX-ACCESS read-write
	STATUS     current
	DESCRIPTION 
	    "This object can be used to enable or disable 
            connection routing. If the value of the object 
            is true(1), routing is enabled; otherwise it 
            is disabled."
	DEFVAL { true }
	::= { parOnOff 4}

parOnOffCommFailTest OBJECT-TYPE
	SYNTAX     TruthValue
	MAX-ACCESS read-write
	STATUS     current
	DESCRIPTION
	    "This object can be used to enable or disable 
            Comm Fail Test. If the value of the object is 
            true(1), Comm Fail test is enabled; otherwise it 
            is disabled."
	DEFVAL { true }
	::= { parOnOff 5}

parOnOffDrtDelay OBJECT-TYPE
	SYNTAX     TruthValue
	MAX-ACCESS read-write
	STATUS     current
	DESCRIPTION
	    "This object can be used to enable or disable 
            Deroute Delay feature. If the value of the object 
            is true(1) Derote delay feature is enabled; 
            otherwise it is disabled."
	DEFVAL { true }
	::= { parOnOff 6}

parOnOffRenumRec OBJECT-TYPE
	SYNTAX     TruthValue
	MAX-ACCESS read-write
	STATUS     current
	DESCRIPTION
	    "This object can be used to enable or disable 
            Renumber recovery feature. If the value of the 
            object is true(1), renumber recovery feature is 
            enabled; otherwise it is disabled."
	DEFVAL { false }
	::= { parOnOff 7}

parOnOffCommBreak OBJECT-TYPE
	SYNTAX     TruthValue
	MAX-ACCESS read-write
	STATUS     current
	DESCRIPTION
	    "This object can be used to enable or disable 
            Comm Break Test. If the value of the object is 
            true(1), Comm Break Test feature is enabled; 
            otherwise it is disabled."
	DEFVAL { false }
	::= { parOnOff 8}

parSysParmsTsPacketAge OBJECT-TYPE
	SYNTAX     Integer32(1..64) 
        UNITS      "milliseconds"
	MAX-ACCESS read-write
	STATUS     current
	DESCRIPTION
	    "Time Stamped packets older than this value 
            (in milliseconds)are discarded.
            This is a network wide parameter."
	DEFVAL { 64 }
	::= { parSysParms 1}

parSysParmsConnFail OBJECT-TYPE
	SYNTAX     TruthValue
	MAX-ACCESS read-write
	STATUS     current
	DESCRIPTION
	    "This object specifies whether the connections to 
            a node should be failed when comm fail is declared 
            with the node. If the value of this object is true(1),
            the connection will be failed. 
            This is a network wide parameter."
	DEFVAL {false}
	::= { parSysParms 2}

parSysParmsVcPollRate OBJECT-TYPE
	SYNTAX     Integer32
	MAX-ACCESS read-only
	STATUS     current
	DESCRIPTION 
	    "This object specifies the rate at which 
            VC statistics are to be polled. This is a 
            network wide parameter. For Portable AutoRoute 
            statistic collections would be done by platform 
            software."
	::= { parSysParms 3}

parSysParmsMaxVDelay OBJECT-TYPE
	SYNTAX     Integer32
        UNITS      "milliseconds"
	MAX-ACCESS read-only
	STATUS     current
	DESCRIPTION
            "This object specifies the maximum delay for 
	    voice connection with VAD enabled in milli-seconds.
            This is a network wide parameter."
	::= { parSysParms 4}

parSysParmsMaxCDelay OBJECT-TYPE
	SYNTAX     Integer32
        UNITS      "milliseconds"
	MAX-ACCESS read-only
	STATUS     current
	DESCRIPTION 
	    "This object specifies the maximum delay for 
            ADPCM compressed voice connection with VAD 
            enabled in milli-seconds.
            This is a network wide parameter."
	::= { parSysParms 5}

parSysParmsMaxDDelay OBJECT-TYPE
	SYNTAX Integer32
        UNITS      "milliseconds"
	MAX-ACCESS read-only
	STATUS current
	DESCRIPTION
	    "This object specifies the maximum delay for 
            data connection in milli-seconds. 
            This is a network wide parameter."
	::= { parSysParms 6}

parSysParmsMaxADelay OBJECT-TYPE
	SYNTAX     Integer32
        UNITS      "milliseconds"
	MAX-ACCESS read-only
	STATUS     current
	DESCRIPTION 
	    "This object specifies the maximum delay for 
            ADPCM compressed voice connection in 
            milli-seconds.
            This is a network wide parameter."
	::= { parSysParms 7}

parSysParmsMaxHsdDelay OBJECT-TYPE
	SYNTAX     Integer32
        UNITS      "milliseconds"
	MAX-ACCESS read-only
	STATUS     current
	DESCRIPTION 
	    "This object specifies the maximum delay for 
            High Speed data connection in milli-seconds.
            This is a network wide parameter."
	::= { parSysParms 8}

parSysParmsDeEnable OBJECT-TYPE
	SYNTAX     TruthValue
	MAX-ACCESS read-only
	STATUS 	   current
	DESCRIPTION
	    "This object specifies whether DE bit of 
            Frame Relay frames can be modified. 
            DE bit can be modified if the value of this 
	    object is true(1).
            This is a network wide parameter."
	::= { parSysParms 9}

parSysParmsFrStandard OBJECT-TYPE
	SYNTAX     TruthValue
	MAX-ACCESS read-only
	STATUS     current
	DESCRIPTION
	    "This object specifies whether standard
            Frame Relay parameters,Be and Bc, are to be used.
            If the value of this object is true(1), 
	    standard parameters are used.
            This is a network wide parameter."
	::= { parSysParms 10}

parSysParmsDrtDelay OBJECT-TYPE
	SYNTAX     TruthValue
	MAX-ACCESS read-write
	STATUS     current
	DESCRIPTION
	    "This object specifies whether Deroute Delay 
            feature is enabled. If the value of this object 
            is true(1), the feature is enabled. 
	    This is a network wide parameter."
	DEFVAL { true }
	::= { parSysParms 11}

parSysParmsInvLogAlarmThres OBJECT-TYPE
	SYNTAX     Integer32 
	MAX-ACCESS read-only
	STATUS     current
	DESCRIPTION
	    "This object specifies the threshold for invalid 
            login attempts before triggering an alarm. 
            If the value of this object is zero, this feature 
            is disabled. 
            This is a network wide parameter."
        DEFVAL { 0 }
	::= { parSysParms 12}
	
parSysParmsMaxCdpVDelay OBJECT-TYPE
	SYNTAX     Integer32
        UNITS      "milliseconds"
	MAX-ACCESS read-only
	STATUS     current
	DESCRIPTION
	    "This object specifies the maximum network delay 
            for CDP to CDP voice connection with VAD enabled 
            in milli-seconds.
            This is a network wide parameter."
	::= { parSysParms 13}

parSysParmsMaxCdpCDelay OBJECT-TYPE
	SYNTAX     Integer32
        UNITS      "milliseconds"
	MAX-ACCESS read-only
	STATUS     current
	DESCRIPTION
	    "This object specifies the maximum network delay 
            for CDP to CDP ADPCM compressed voice connection 
            with VAD enabled.
	    This is a network wide parameter."
	::= { parSysParms 14}

parSysParmsMaxCdpDDelay OBJECT-TYPE
	SYNTAX     Integer32
        UNITS      "milliseconds"
	MAX-ACCESS read-only
	STATUS     current
	DESCRIPTION 
	    "This object specifies the maximum network delay 
            for CDP to CDP data connection.
            This is a network wide parameter."
	::= { parSysParms 15}

parSysParmsMaxCdpADelay OBJECT-TYPE
	SYNTAX     Integer32
        UNITS      "milliseconds"
	MAX-ACCESS read-only
	STATUS     current
	DESCRIPTION
	    "This object specifies the maximum network delay 
            for CDP to CDP ADPCM compressed voice connection.
            This is a network wide parameter."
	::= { parSysParms 16}

parSysParmsMaxCdpHsdDelay OBJECT-TYPE
	SYNTAX     Integer32
        UNITS      "milliseconds"
	MAX-ACCESS read-only
	STATUS     current
	DESCRIPTION
	    "This object specifies the maximum network delay 
            for CDP to CDP High Speed data connection. 
            This is a network wide parameter."
	::= { parSysParms 17}

parSysParmsMaxIpcdpVDelay OBJECT-TYPE
	SYNTAX     Integer32
        UNITS      "milliseconds"
	MAX-ACCESS read-only
	STATUS     current
	DESCRIPTION
	    "This object specifies the maximum local delay 
            for CDP to CDP voice connection with VAD enabled.
            This is a network wide parameter."
	::= { parSysParms 18}

parSysParmsMaxIpcdpCDelay OBJECT-TYPE
	SYNTAX     Integer32
        UNITS      "milliseconds"
	MAX-ACCESS read-only
	STATUS     current
	DESCRIPTION
	    "This object specifies the maximum local delay 
            for CDP to CDP ADPCM compressed voice connection
            with VAD enabled.
            This is a network wide parameter."
	::= { parSysParms 19}

parSysParmsMaxIpcdpDDelay OBJECT-TYPE
	SYNTAX     Integer32
        UNITS      "milliseconds"
	MAX-ACCESS read-only
	STATUS     current
	DESCRIPTION
	    "This object specifies the maximum local delay 
            for CDP to CDP data connection.
            This is a network wide parameter."
	::= { parSysParms 20}

parSysParmsMaxIpcdpADelay OBJECT-TYPE
	SYNTAX     Integer32
	MAX-ACCESS read-only
	STATUS     current
	DESCRIPTION
	    "This object specifies the maximum local delay 
            for CDP to CDP ADPCM compressed voice connection.
            This is a network wide parameter."
	::= { parSysParms 21}

parSysParmsMaxIpcdpHsdDelay OBJECT-TYPE
	SYNTAX     Integer32
	MAX-ACCESS read-only
	STATUS     current
	DESCRIPTION
	    "This object specifies the maximum local delay 
            for CDP to CDP High Speed data connection. 
            This is a network wide parameter."
	::= { parSysParms 22}

parSysParmsMaxIphsdDelay OBJECT-TYPE
	SYNTAX     Integer32
        UNITS      "milliseconds"
	MAX-ACCESS read-only
	STATUS     current
	DESCRIPTION
	    "This object specifies the maximum local delay 
            for High Speed data connection. 
            This is a network wide parameter."
	::= { parSysParms 23}

parSysParmsFpdDeJitter OBJECT-TYPE
	SYNTAX     Integer32
	MAX-ACCESS read-only
	STATUS     current
	DESCRIPTION
	    "This object specifies the jitter delay for 
            Fast Pad.
            This is a network wide parameter."
	::= { parSysParms 24}

parNetParmCondInitialStgr OBJECT-TYPE
	SYNTAX     Integer32
        UNITS      "milliseconds"
	MAX-ACCESS read-write
	STATUS     current
	DESCRIPTION
	    "This object specifies the initial pause time 
	    (in milliseconds) per new node added on addition
            of node(s) in the network before initiating
            conditional updates."
	DEFVAL { 5000 }
	::= { parNetworkingParms 1}

parNetParmCondPerNodeInterval OBJECT-TYPE
	SYNTAX     Integer32
        UNITS      "milliseconds"
	MAX-ACCESS read-write
	STATUS     current
	DESCRIPTION 
	    "This object specifies the minimum interval 
            (in milliseconds) between sending of conditional 
            updates to any two nodes."
	DEFVAL {30000}
	::= { parNetworkingParms 2}

parNetParmCbDelay OBJECT-TYPE
	SYNTAX     Integer32
        UNITS      "milliseconds"
	MAX-ACCESS read-write
	STATUS     current
	DESCRIPTION
	    "This object specifies the minimum interval 
            (in milliseconds) between initiating comm break 
            tests between any two nodes."
	DEFVAL { 30000 }
	::= { parNetworkingParms 3}

parNetParmCbOffset OBJECT-TYPE
	SYNTAX     Integer32
	MAX-ACCESS read-write
	STATUS     current
	DESCRIPTION
	    "Offset for CB."
	DEFVAL { 10 }
	::= { parNetworkingParms 4}
	
parNetParmMsgTimeout OBJECT-TYPE
	SYNTAX     Integer32
        UNITS      "milliseconds"
	MAX-ACCESS read-write
	STATUS     current
	DESCRIPTION 
	    "This object specifies the timeout (in milliseconds)
            for acknowledgment for control plane message sent to
            another node."
	DEFVAL { 1700 }
	::= { parNetworkingParms 5}

parNetParmMsgMaxTimeout OBJECT-TYPE
	SYNTAX     Integer32
	MAX-ACCESS read-write
	STATUS     current
	DESCRIPTION
	    "This object specifies the maximum number of 
            times a network handler timeout waiting for 
            acknowledgment for control plane message sent 
            to another node reachable through all 
            terrestrial trunks."
	DEFVAL { 7 }
	::= { parNetworkingParms 6}
	
parNetParmMsgMaxTimeoutSat OBJECT-TYPE
	SYNTAX     Integer32
	MAX-ACCESS read-write
	STATUS     current
	DESCRIPTION
	    "This object specifies the maximum number of 
            times a network handler timeout waiting for 
            acknowledgment for control plane message sent 
            to another node reachable through all 
            satellite trunks."
	DEFVAL { 6 }
	::= { parNetworkingParms 7}

parNetParmBlindMaxTimeout OBJECT-TYPE
	SYNTAX     Integer32
	MAX-ACCESS read-write
	STATUS     current
	DESCRIPTION 
	    "This object specifies the maximum number of 
            times a network handler timeout waiting for 
            acknowledgment for control plane blind message 
            sent to another node."
	DEFVAL { 4 }
	::= { parNetworkingParms 8}

parNetParmCbMaxTimeout OBJECT-TYPE
	SYNTAX     Integer32
	MAX-ACCESS read-write
	STATUS     current
	DESCRIPTION
	    "This object specifies the maximum number of 
            times a network handler timeout waiting for 
            acknowledgment for comm break test message sent 
            to another node."
	DEFVAL { 5 }
	::= { parNetworkingParms 9}

parNetParmCfTestInterval OBJECT-TYPE
	SYNTAX     Integer32
	MAX-ACCESS read-write
	STATUS     current
	DESCRIPTION
	    "This object specifies the minimum time interval 
            between the comm fail tests for a trunk."
	DEFVAL { 10000 }
	::= { parNetworkingParms 10}

parNetParmCfTestMultiplier OBJECT-TYPE
	SYNTAX     Integer32 
	MAX-ACCESS read-write
	STATUS     current
	DESCRIPTION 
	    "This object specifies the multiplier for the 
            comm fail test interval for good trunks, that is,
            trunks not in comm fail."
	DEFVAL { 3 }
	::= { parNetworkingParms 11}

parNetParmNetwWindowSz OBJECT-TYPE
	SYNTAX     Integer32
	MAX-ACCESS read-write
	STATUS     current
	DESCRIPTION 
	    "This object specifies the window size for the 
            network handler for messages to any node.
            That is, the number of messages that the network 
            handler can send simultaneous to a node without 
	    receiving the acknowledgment for them."
	DEFVAL { 1 }
	::= { parNetworkingParms 12}

parNetParmNetwLetWait OBJECT-TYPE
	SYNTAX     Integer32
        UNITS      "milliseconds"
	MAX-ACCESS read-write
	STATUS     current
	DESCRIPTION 
	    "This object specifies the maximum interval 
            (in milliseconds) network handler waits for 
            the letter (message) from the processes running 
            on its nodes before checking the received cells."
	DEFVAL { 50 }
	::= { parNetworkingParms 13}

parNetParmCfDelay OBJECT-TYPE
	SYNTAX     Integer32
	MAX-ACCESS read-write
	STATUS current
	DESCRIPTION
	    "TBD (in milliseconds)."
	DEFVAL { 60 }
	::= { parNetworkingParms 14}

parNetParmHighTxRate OBJECT-TYPE
	SYNTAX     Integer32
	MAX-ACCESS read-write
	STATUS     current
	DESCRIPTION
	    "This object specifies the rate 
            (in fast packets per second) at which the 
            network handler sends control plane message cells 
	    to high performance nodes 
            (High performance node are BPX and MGX)."
	DEFVAL { 2500 }
	::= { parNetworkingParms 15}

parNetParmLowTxRate OBJECT-TYPE
	SYNTAX     Integer32
	MAX-ACCESS read-write
	STATUS     current
	DESCRIPTION
	    "This object specifies the rate 
            (in fast packets per second) at which the 
            network handler sends control plane message cells to 
	    low capacity nodes (Low capacity node are IPX and IGX)."
	DEFVAL { 500 }
	::= { parNetworkingParms 16}

parNetParmMaxNodeBlks OBJECT-TYPE
	SYNTAX     Integer32
	MAX-ACCESS read-write
	STATUS     current
	DESCRIPTION
	    "This object specifies the maximum number of blocks
            of size 256 bytes, that should be queued up for
            transmission to a node."
	DEFVAL { 3000 }
	::= { parNetworkingParms 17}

parNetParmTopoMsgSegSz OBJECT-TYPE
	SYNTAX     Integer32
        UNITS      "bytes"
	MAX-ACCESS read-write
	STATUS     current
	DESCRIPTION
	    "This object specifies the maximum size (in bytes)
            of the segment into which the topology message,
            sent during network join, is divided."
	DEFVAL { 3570 }
	::= { parNetworkingParms 18}

-- conformance information

cwParMIBConformance  OBJECT IDENTIFIER ::= { ciscoWanParMIB 2 }

cwParMIBGroups       OBJECT IDENTIFIER ::= { cwParMIBConformance 1 }

cwParMIBCompliances  OBJECT IDENTIFIER ::= { cwParMIBConformance 2 }

-- compliance statements

cwParCompliance MODULE-COMPLIANCE
    STATUS  current
    DESCRIPTION
        "The compliance statement for objects related
        to AutoRoute MIB."
    MODULE  -- this module
    MANDATORY-GROUPS{
        cwParCmParamsGroup,
        cwParCmParamsUpdateGroup,
        cwParGeneralGroup,
        cwParSysParamsGroup,
        cwParNetParamsGroup,
        cwParNodeGroup,
        cwParInterfaceConfGroup,
        cwParTrunkConfGroup,
        cwParTrunkLoadConfGroup,
        cwParConnConfGroup,
        cwParClockConfGroup 
    }
    ::= { cwParMIBCompliances 1 }


cwParCmParamsGroup OBJECT-GROUP
    OBJECTS {
        parCmParmsMaxRoutingBundle,
        parCmParmsRerouteTimer,         
        parCmParmsResetTimer,      
        parCmParmsDnUpPerPass,     
        parCmParmsDnUpTimer,
        parCmParmsRrtErrsPerCycle,
        parCmParmsRrtCycleInterval,
        parCmParmsMaxRrtCycles,
        parCmParmsRrtPauseTime,
        parCmParmsMaxUpdates,
        parCmParmsRerouteGroups,
        parCmParmsMinRrGroupSize,
        parCmParmsRrGroupInc,
        parCmParmsCostBased,
        parCmParmsUseCache,
        parCmParmsUseDelay,
        parCmParmMaxViaCons
      }
      STATUS current
      DESCRIPTION
          "The collection of objects which are applicable
          for PAR connection management."
      ::= { cwParMIBGroups 1 }

cwParCmParamsUpdateGroup OBJECT-GROUP
    OBJECTS {
        parMnUpdtInterval,
        parMnUpdtNodesPerInt,
        parMnUpdtBatchSend
       
      }
      STATUS current
      DESCRIPTION
          "The collection of objects which are applicable
          for PAR Connection Management parameters updates."
      ::= { cwParMIBGroups 2 }

cwParGeneralGroup OBJECT-GROUP
    OBJECTS {
        parSwFuncAbrVsvd,
        parSwFuncNodeType,
        parOnOffBackgroundUpdt,
        parOnOffDynamicBwAlloc,
        parOnOffCmUpdts,
        parOnOffRouting,
        parOnOffCommFailTest,
        parOnOffDrtDelay,
        parOnOffRenumRec,
        parOnOffCommBreak
      }
      STATUS current
      DESCRIPTION
          "The collection of objects which are applicable
          for general PAR configuration."
      ::= { cwParMIBGroups 3 }

cwParSysParamsGroup OBJECT-GROUP
    OBJECTS {
        parSysParmsTsPacketAge,
        parSysParmsConnFail,
        parSysParmsVcPollRate,
        parSysParmsMaxVDelay,
        parSysParmsMaxCDelay,
        parSysParmsMaxDDelay,
        parSysParmsMaxADelay,
        parSysParmsMaxHsdDelay,
        parSysParmsDeEnable,
        parSysParmsFrStandard,
        parSysParmsDrtDelay,
        parSysParmsInvLogAlarmThres,
        parSysParmsMaxCdpVDelay,
        parSysParmsMaxCdpCDelay,
        parSysParmsMaxCdpDDelay,
        parSysParmsMaxCdpADelay,
        parSysParmsMaxCdpHsdDelay,
        parSysParmsMaxIpcdpVDelay,
        parSysParmsMaxIpcdpCDelay,
        parSysParmsMaxIpcdpDDelay,
        parSysParmsMaxIpcdpADelay,
        parSysParmsMaxIpcdpHsdDelay,
        parSysParmsMaxIphsdDelay,
        parSysParmsFpdDeJitter
      }
      STATUS current
      DESCRIPTION
          "The collection of objects which are applicable
          for PAR system parameters."
      ::= { cwParMIBGroups 4 }

cwParNetParamsGroup OBJECT-GROUP
    OBJECTS {
        parNetParmCondInitialStgr,
        parNetParmCondPerNodeInterval,
        parNetParmCbDelay,
        parNetParmCbOffset,
        parNetParmMsgTimeout,
        parNetParmMsgMaxTimeout,
        parNetParmMsgMaxTimeoutSat,
        parNetParmBlindMaxTimeout,
        parNetParmCbMaxTimeout,
        parNetParmCfTestInterval,
        parNetParmCfTestMultiplier,
        parNetParmNetwWindowSz,
        parNetParmNetwLetWait,
        parNetParmCfDelay,
        parNetParmHighTxRate,
        parNetParmLowTxRate,
        parNetParmMaxNodeBlks,
        parNetParmTopoMsgSegSz
      }
      STATUS current
      DESCRIPTION
          "The collection of objects which are applicable
          for parameters applicable network-wide."
      ::= { cwParMIBGroups 5 }

cwParNodeGroup OBJECT-GROUP
    OBJECTS {
        parSnNodeId,
        parSnNodeIP,         
        parSnNodeName,      
        parSnRevision,     
        parSnNodeAlarmStatus,
        parSnNumberOfTrunks
      }
      STATUS current
      DESCRIPTION
          "The collection of objects which are applicable
          for node level configuration of auto route controller."
      ::= { cwParMIBGroups 6 }

cwParInterfaceConfGroup OBJECT-GROUP
    OBJECTS {
	parIfLogicalInterface,
	parIfType,
	parIfOperStatus,
	parIfTxBw,
	parIfRxBw,
	parIfMaxConn,
	parIfHiAddrMin,
	parIfHiAddrMax,
	parIfLoAddrMin,
	parIfLoAddrMax
      }
      STATUS current
      DESCRIPTION
          "The collection of objects which are used for
          configuring autoroute interfaces."
      ::= { cwParMIBGroups 7 }

cwParTrunkConfGroup OBJECT-GROUP
    OBJECTS {
	parTrkId,
	parTrkStatReserve,
	parTrkCnfgCcRestrict,
	parTrkCnfgLineType,
	parTrkCnfgPassSync,
	parTrkCnfgDerouteDelay,
	parTrkCnfgTrafficClassFst,
	parTrkCnfgTrafficClassFr,
	parTrkCnfgTrafficClassNts,
	parTrkCnfgTrafficClassTs,
	parTrkCnfgTrafficClassVoice,
	parTrkCnfgTrafficClassCbr,
	parTrkCnfgTrafficClassVbr,
	parTrkCnfgTrafficClassAbr,
	parTrkCnfgAdminStatus,
	parTrkCnfgRoutingCost,
	parTrkCnfgVpcConids,
	parTrkCnfgVccConids,
	parTrkLocalSlotNumber,
	parTrkLocalPortNumber,
	parTrkLocalVTrunkId,
	parTrkRemoteNodeId,
	parTrkRemoteTrunkId,
	parTrkRemoteSlotNumber,
	parTrkRemotePortNumber,
	parTrkRemoteVTrunkId,
	parTrkRemoteNodeIP,
	parTrkRemoteNodeType,
	parTrkRemoteNodeName,
	parTrkAlarmStatus,
	parTrkAlarmType,
	parTrkLineLoad,
	parTrkBwCapacity
      }
      STATUS current
      DESCRIPTION
          "The collection of objects which are used for
          configuring trunks in portable autoroute."
      ::= { cwParMIBGroups 8 }
  
cwParTrunkLoadConfGroup OBJECT-GROUP
    OBJECTS {
	parTrkLoadXmtUsedCbr,
	parTrkLoadRcvUsedCbr,
	parTrkLoadXmtUsedVbr,
	parTrkLoadRcvUsedVbr,
	parTrkLoadXmtUsedAbr,
	parTrkLoadRcvUsedAbr,
	parTrkLoadXmtUsedNts,
	parTrkLoadRcvUsedNts,
	parTrkLoadXmtUsedTs,
	parTrkLoadRcvUsedTs,
	parTrkLoadXmtUsedVoice,
	parTrkLoadRcvUsedVoice,
	parTrkLoadXmtUsedBdataA,
	parTrkLoadRcvUsedBdataA,
	parTrkLoadXmtUsedBdataB,
	parTrkLoadRcvUsedBdataB,
	parTrkLoadVccConidsUsed,
	parTrkLoadVpcConidsUsed
      }
      STATUS current
      DESCRIPTION
          "The collection of objects which are used for
          configuring trunks in portable autoroute."
      ::= { cwParMIBGroups 9 }
  
cwParConnConfGroup OBJECT-GROUP
    OBJECTS {
	parConnLocalSlot,
	parConnLocalPort,
	parConnLocalVpi,
	parConnLocalVci,
        parConnMasterShip,
	parConnLocalVcIndx,
        parConnLocalEndpt,
	parConnRemoteNodeName,
	parConnRemoteSlot,
	parConnRemotePort,
	parConnRemoteVpi,
	parConnRemoteVci,
	parConnRemoteVcIndx,
        parConnRemoteEndpt,
	parConnOperStatus,
	parConnAdminStatus,
	parConnRoute,
        parPrefRoute,
        parConnFailRsn,
        parRrtFailRsn,
	parConnRstrTyp,
	parConnRstrZcs,
        parConnCos
      }
      STATUS current
      DESCRIPTION
          "The collection of objects which are used for
          configuring trunks in portable autoroute."
      ::= { cwParMIBGroups 10 }
  
cwParClockConfGroup OBJECT-GROUP
    OBJECTS {
	parClockIndex,
	parClockType,
        parClockCurSource,
	parClockSource,
	parClockSourceId,
        parClockPath
      }
      STATUS current
      DESCRIPTION
          "The collection of objects which are used for
          configuring trunks in portable autoroute."
      ::= { cwParMIBGroups 11 }
  

END
