-- *****************************************************************
-- CISCO-LWAPP-CLIENT-ROAMING-CAPABILITY.my:  
-- CISCO-LWAPP-CLIENT-ROAMING MIB CAPABILITIES
--
-- May 2006 -  Prasanna Viswakumar
--
-- Copyright (c) 2006 by cisco Systems, Inc.
-- All rights reserved.
--
-- *****************************************************************

CISCO-LWAPP-CLIENT-ROAMING-CAPABILITY DEFINITIONS ::= BEGIN

IMPORTS
        MODULE-IDENTITY
                FROM SNMPv2-SMI
        AGENT-CAPABILITIES
                FROM SNMPv2-CONF
        ciscoAgentCapability
                FROM CISCO-SMI;

ciscoLwappClientRoamingCapability MODULE-IDENTITY  
        LAST-UPDATED         "200605090000Z"
        ORGANIZATION         "Cisco Systems, Inc."
        CONTACT-INFO
                "             Cisco Systems
                              Customer Service

                      Postal: 170 W Tasman Drive
                              San Jose, CA  95134
                              USA
  
                         Tel: +1 800 553-NETS
 
                      E-mail: cs-wnbu-snmp@cisco.com"
        DESCRIPTION
                "Agent capabilities for 
                 CISCO-LWAPP-CLIENT-ROAMING-MIB. "
        REVISION      "200605090000Z"
        DESCRIPTION
                "Initial version of this MIB module. "
        ::= { ciscoAgentCapability 501 }

ciscoLwappClientRoamingCapabilityCUWNSV4R0   AGENT-CAPABILITIES

PRODUCT-RELEASE         "Cisco Unified Wireless Network Software
                        Release 4.0. "
        STATUS          current
        DESCRIPTION     "CISCO-LWAPP-CLIENT-ROAMING-MIB
                        capabilities. "

        SUPPORTS        CISCO-LWAPP-CLIENT-ROAMING-MIB
        INCLUDES        {
                        ciscoLwappClRoamDot11aRfParamsGroup,
                        ciscoLwappClRoamDot11bRfParamsGroup,
                        ciscoLwappClRoamroamReasonGroup
                        }   
                           
        VARIATION       clcrDot11aMode
        SYNTAX          INTEGER { 
                                default(1),
                                custom(2) 
                        }
        DESCRIPTION
                        "The values supported are 'default'
                        and 'custom'. "

        VARIATION       clcrDot11bMode
        SYNTAX          INTEGER { 
                                default(1),
                                custom(2) 
                        }
        DESCRIPTION
                        "The values supported are 'default'
                        and 'custom'. "

        ::= { ciscoLwappClientRoamingCapability 1 }

END
