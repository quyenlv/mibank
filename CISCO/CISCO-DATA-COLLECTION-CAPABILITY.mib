-- *****************************************************************
-- CISCO-DATA-COLLECTION-CAPABILITY.my:
-- CISCO-DATA-COLLECTION-MIB AGENT-CAPABILITIES
-- 
-- January 2005, Radhika Dharwadkar
-- 
-- Copyright (c) 2006 by cisco Systems, Inc.
-- All rights reserved.
-- 
-- *****************************************************************
--

CISCO-DATA-COLLECTION-CAPABILITY DEFINITIONS ::= BEGIN

IMPORTS
    MODULE-IDENTITY
        FROM SNMPv2-SMI
    AGENT-CAPABILITIES
        FROM SNMPv2-CONF
    ciscoAgentCapability
        FROM CISCO-SMI;

cDataCollectionCapability MODULE-IDENTITY

LAST-UPDATED  "200501050000Z"
ORGANIZATION   "Cisco Systems, Inc."
CONTACT-INFO
           "Cisco Systems
           Customer Service
            
         Postal: 170 West Tasman Drive
              San Jose, CA  95134
               USA
            
               Tel:+1 800 553-NETS
            
                   E-mail:    cs-snmp@cisco.com"
DESCRIPTION
        "Agent capabilities for CISCO-DATA-COLLECTION-MIB"
REVISION        "200501050000Z"
DESCRIPTION
        "Initial version of this MIB module."

::= { ciscoAgentCapability 999999}

cDataCollectionCapabilityV12R0S AGENT-CAPABILITIES

PRODUCT-RELEASE    "Cisco IOS 12.0S"
STATUS             current
DESCRIPTION        "cisco-data-collection mib capabilities"

SUPPORTS    CISCO-DATA-COLLECTION-MIB
INCLUDES    { cdcNotificationGroup }

VARIATION    cdcVFilePersistentStorage
ACCESS        not-implemented
DESCRIPTION    "This scalar object is not supported"

VARIATION    cdcVFileMaxSizeHitsLimit
ACCESS        not-implemented
DESCRIPTION    " This scalar object is not supported"

VARIATION    cdcVFileIndex
ACCESS        not-implemented
DESCRIPTION    "Table for CdcVFileEntry not supported"

VARIATION    cdcVFileName
ACCESS        not-implemented
DESCRIPTION    "Table for CdcVFileEntry not supported"

VARIATION    cdcVFileDescription
ACCESS        not-implemented
DESCRIPTION    "Table for CdcVFileEntry not supported"

VARIATION    cdcVFileCommand
ACCESS        not-implemented
DESCRIPTION    "Table for CdcVFileEntry not supported"

VARIATION    cdcVFileMaxSize
ACCESS        not-implemented
DESCRIPTION    "Table for CdcVFileEntry not supported"

VARIATION    cdcVFileCurrentSize
ACCESS        not-implemented
DESCRIPTION    "Table for CdcVFileEntry not supported"

VARIATION    cdcVFileFormat
ACCESS        not-implemented
DESCRIPTION    "Table for CdcVFileEntry not supported"

VARIATION    cdcVFileCollectMode
ACCESS        not-implemented
DESCRIPTION    "Table for CdcVFileEntry not supported"

VARIATION    cdcVFileCollectionPeriod
ACCESS        not-implemented
DESCRIPTION    "Table for CdcVFileEntry not supported"

VARIATION    cdcVFileRetentionPeriod
ACCESS        not-implemented
DESCRIPTION    "Table for CdcVFileEntry not supported"

VARIATION    cdcVFileAdminStatus
ACCESS        not-implemented
DESCRIPTION    "Table for CdcVFileEntry not supported"

VARIATION    cdcVFileOperStatus
ACCESS        not-implemented
DESCRIPTION    "Table for CdcVFileEntry not supported"

VARIATION    cdcVFileErrorCode
ACCESS        not-implemented
DESCRIPTION    "Table for CdcVFileEntry not supported"

VARIATION    cdcVFileCollectionErrorEnable
ACCESS        not-implemented
DESCRIPTION    "Table for CdcVFileEntry not supported"

VARIATION    cdcVFileRowStatus
ACCESS        not-implemented
DESCRIPTION    "Table for CdcVFileEntry not supported"

VARIATION    cdcVFileMgmtIndex
ACCESS        not-implemented
DESCRIPTION    "Table for cdcVFileMgmtEntry not supported"

VARIATION    cdcVFileMgmtName
ACCESS        not-implemented
DESCRIPTION    "Table for cdcVFileMgmtEntry not supported"

VARIATION    cdcVFileMgmtTimestamp
ACCESS        not-implemented
DESCRIPTION    "Table for cdcVFileMgmtEntry not supported"

VARIATION    cdcVFileMgmtTimeToLive
ACCESS        not-implemented
DESCRIPTION    "Table for cdcVFileMgmtEntry not supported"

VARIATION    cdcVFileMgmtCommand
ACCESS        not-implemented
DESCRIPTION    "Table for cdcVFileMgmtEntry not supported"

VARIATION    cdcVFileMgmtXferURL
ACCESS        not-implemented
DESCRIPTION    "Table for cdcVFileMgmtEntry not supported"

VARIATION    cdcVFileMgmtLastXferStatus
ACCESS        not-implemented
DESCRIPTION    "Table for cdcVFileMgmtEntry not supported"

VARIATION    cdcVFileMgmtLastXferURL
ACCESS        not-implemented
DESCRIPTION    "Table for cdcVFileMgmtEntry not supported"

VARIATION    cdcDGIndex
ACCESS        not-implemented
DESCRIPTION    "Table for CdcDGEntry not supported"

VARIATION    cdcDGComment
ACCESS        not-implemented
DESCRIPTION    "Table for CdcDGEntry not supported"

VARIATION    cdcDGType
ACCESS        not-implemented
DESCRIPTION    "Table for CdcDGEntry not supported"

VARIATION    cdcDGVFileIndex
ACCESS        not-implemented
DESCRIPTION    "Table for CdcDGEntry not supported"

VARIATION    cdcDGTargetTag
ACCESS        not-implemented
DESCRIPTION    "Table for CdcDGEntry not supported"

VARIATION    cdcDGContextName
ACCESS        not-implemented
DESCRIPTION    "Table for CdcDGEntry not supported"

VARIATION    cdcDGObject
ACCESS        not-implemented
DESCRIPTION    "Table for CdcDGEntry not supported"

VARIATION    cdcDGObjectGrpIndex
ACCESS        not-implemented
DESCRIPTION    "Table for CdcDGEntry not supported"

VARIATION    cdcDGInstGrpIndex
ACCESS        not-implemented
DESCRIPTION    "Table for CdcDGEntry not supported"

VARIATION    cdcDGPollPeriod
ACCESS        not-implemented
DESCRIPTION    "Table for CdcDGEntry not supported"

VARIATION    cdcDGRowStatus
ACCESS        not-implemented
DESCRIPTION    "Table for CdcDGEntry not supported"

VARIATION    cdcDGBaseObjectGrpIndex
ACCESS        not-implemented
DESCRIPTION    "Table for cdcDGBaseObjectEntry not supported"

VARIATION    cdcDGBaseObjectIndex
ACCESS        not-implemented
DESCRIPTION    "Table for cdcDGBaseObjectEntry not supported"

VARIATION    cdcDGBaseObjectSubtree
ACCESS        not-implemented
DESCRIPTION    "Table for cdcDGBaseObjectEntry not supported"

VARIATION    cdcDGBaseObjectList
ACCESS        not-implemented
DESCRIPTION    "Table for cdcDGBaseObjectEntry not supported"

VARIATION    cdcDGBaseObjectRowStatus
ACCESS        not-implemented
DESCRIPTION    "Table for cdcDGBaseObjectEntry not supported"

VARIATION    cdcDGInstanceGrpIndex
ACCESS        not-implemented
DESCRIPTION    "Table for cdcDGInstanceEntry not supported"

VARIATION    cdcDGInstanceIndex
ACCESS        not-implemented
DESCRIPTION    "Table for cdcDGInstanceEntry not supported"

VARIATION    cdcDGInstanceType
ACCESS        not-implemented
DESCRIPTION    "Table for cdcDGInstanceEntry not supported"

VARIATION    cdcDGInstanceOid
ACCESS        not-implemented
DESCRIPTION    "Table for cdcDGInstanceEntry not supported"

VARIATION    cdcDGInstanceOidEnd
ACCESS        not-implemented
DESCRIPTION    "Table for cdcDGInstanceEntry not supported"

VARIATION    cdcDGInstanceNumRepititions
ACCESS        not-implemented
DESCRIPTION    "Table for cdcDGInstanceEntry not supported"

VARIATION    cdcDGInstanceOtherPtr
ACCESS        not-implemented
DESCRIPTION    "Table for cdcDGInstanceEntry not supported"

VARIATION    cdcDGInstanceRowStatus
ACCESS        not-implemented
DESCRIPTION    "Table for cdcDGInstanceEntry not supported"

VARIATION    cdcFileXferConfPriUrl
ACCESS        not-implemented
DESCRIPTION    "Table for cdcFileXferConfEntry not supported"

VARIATION    cdcFileXferConfSecUrl
ACCESS        not-implemented
DESCRIPTION    "Table for cdcFileXferConfEntry not supported"

VARIATION    cdcFileXferConfRetryPeriod
ACCESS        not-implemented
DESCRIPTION    "Table for cdcFileXferConfEntry not supported"

VARIATION    cdcFileXferConfRetryCount
ACCESS        not-implemented
DESCRIPTION    "Table for cdcFileXferConfEntry not supported"

VARIATION    cdcFileXferConfSuccessEnable
ACCESS        not-implemented
DESCRIPTION    "Table for cdcFileXferConfEntry not supported"

VARIATION    cdcFileXferConfFailureEnable
ACCESS        not-implemented
DESCRIPTION    "Table for cdcFileXferConfEntry not supported"

    ::= { cDataCollectionCapability 1 }

END
