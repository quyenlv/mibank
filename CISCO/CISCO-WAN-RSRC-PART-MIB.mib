-- *****************************************************************
-- ciscoWANRsrcPart MIB
--
-- March, 2002
--
-- Copyright (c) 1999 by cisco Systems, Inc.
-- All rights reserved.
-- *****************************************************************

CISCO-WAN-RSRC-PART-MIB DEFINITIONS ::= BEGIN
IMPORTS
    MODULE-IDENTITY,
    OBJECT-TYPE,
    Unsigned32,
    Integer32   	 FROM SNMPv2-SMI
    TruthValue,
    RowStatus     	 FROM SNMPv2-TC
    MODULE-COMPLIANCE,
    OBJECT-GROUP 	 FROM SNMPv2-CONF
    ifIndex        	 FROM IF-MIB
    ciscoMgmt       	 FROM CISCO-SMI;


ciscoWANRsrcPartMIB MODULE-IDENTITY
LAST-UPDATED   "200209140000Z"
ORGANIZATION   "Cisco Systems, Inc."
CONTACT-INFO
               "Cisco Systems
                Customer Service

        Postal: 170 W Tasman Drive
                San Jose, CA  95134
                USA

          Tel: +1 800 553-NETS

     E-mail: cs-wanatm@cisco.com"

DESCRIPTION
    "The MIB module to manage resource partition objects. A resource
     partition is configured on a virtual interface (ifType value
     atmVirtual(149)) or atm interface (ifType value atm(37)). 
     An administrator can partition connection related resources like
     VPI, VCI ranges, bandwidth and total amount of available connection
     entries in the switch through these MIB tables.

     Terminolgies used:
     VSI       - Virtual Switch Interface, a hardware-independent switch
         control protocol. This allows a Switch to be
         controlled by a multiple controllers such as PNNI, MPLS.
         These control planes can be internal or external to the
         switch.The VSI interface defines the messages and associated
         functions which allow communication between the controller
         and the switch.This interface is expected to support all
         types of connections (voice,data,frame relay,ATM) for PVCs,
         SPVCs and SVCs.
 
     VSI Master - software component which requests connections and
          receives switch generic information. This controls one or
          more VSI Slaves. This may run on the switch or a dedicated
          controller platform. This is the master module.It performs
          the interface to the higher layer networking software and
          handles all VSI related functions.

     Controller - Software ( and possibly hardware) which manages
          topology and network resources and performs VSI Master
          function.  This performs source routing for end-to-end SVCs,
          including general call acceptance GCAC,setup calls with other
          controllers.
          PNNI and MPLS are examples of controllers.

     ILMI       - Integrated Local Management Interface (ILMI). An ATM
          Forum defined, SNMP-based management protocol for an ATM UNI.
          It provides interface status and configuration information,
          and also supports dynamic ATM address registration.

     CAC - Call Admission Control (CAC). When a new call coming to the
           gateway, a process checks the availability of the resources 
           involved in the connection establishment before the gateway
           sets up the call.

     ATM - Asynchronous Transfer Mode (ATM).
     PNNI - Private Network to Network Interface (PNNI).
     MPLS - MultiProtocol Label Switching (MPLS).
     GCAC - Generic Connection Admittance Control (GCAC).
     PVC - Permanent Virtual Circuits (PVC).
     SVC - Switched Virtual Circuits (SVC).
     SPVC - Soft Permanent Virtual Circuits (SPVC).
     VPI - Virtual Path Identifier (VPI).
     VCI - Virtual Circuit Identifier (VCI).
     "

REVISION "200209140000Z"
DESCRIPTION
         "Added the cwRsrcSvcAggrTable to manage SVC aggregate
          resources.
          Added the cwRsrcPartMIBComplianceRev1 which supersedes the
          cwRsrcPartMIBCompliance after the group cwRsrcSvcAggrGroup
          was added."

REVISION  "200203060000Z"
DESCRIPTION
    "Made following changes:
     (1) Changed cwRsrcPartSignallingVpi range to be consistent with
         values defined in standard document.
     (2) Changed cwRsrcPartIlmiTable description."

REVISION  "9910120000Z"
DESCRIPTION
    "Initial version of the MIB."
   ::= {ciscoMgmt 125 }

ciscoWANRsrcPartMIBObjects OBJECT IDENTIFIER ::= {ciscoWANRsrcPartMIB 1}
cwRsrcPartConfGrp   OBJECT IDENTIFIER ::= {ciscoWANRsrcPartMIBObjects 1}
cwRsrcSvcAggrGrp           OBJECT IDENTIFIER 
                                ::= {ciscoWANRsrcPartMIBObjects 2}

-- --------------------------------------------------------------------
-- Resource Partition MIB
-- --------------------------------------------------------------------

cwRsrcPartConfTable OBJECT-TYPE
    SYNTAX  SEQUENCE OF CwRsrcPartConfEntry
    MAX-ACCESS  not-accessible
    STATUS  current
    DESCRIPTION 
        "This table is for configuring resource partition parameters.
         A resource partition is configured on an interface whose
         ifType is atmVirtual(149) or atm(37). An entry can be added,
         deleted or modified. Entries in this table can be modified
         through the commands provided by the CLI also."
   ::= { cwRsrcPartConfGrp 1 }
 
cwRsrcPartConfEntry  OBJECT-TYPE
    SYNTAX  CwRsrcPartConfEntry
    MAX-ACCESS  not-accessible
    STATUS  current
    DESCRIPTION 
        "An entry for a resource partition. A resource partition 
         has to be created before connections can be added to the 
         interface.
	 In the following objects, ingress direction  means, from network
         to switch, and egress direction means, from switch to network."
    INDEX   { ifIndex, cwRsrcPartID }
    ::= { cwRsrcPartConfTable 1 }

CwRsrcPartConfEntry ::=
    SEQUENCE {
        cwRsrcPartID 	     		Unsigned32,
	cwRsrcPartController          	Unsigned32,
	cwRsrcPartEgrGuarPctBwConf  	Unsigned32,
        cwRsrcPartEgrMaxPctBwConf  	Unsigned32,
        cwRsrcPartIngGuarPctBwConf      Unsigned32,
        cwRsrcPartIngMaxPctBwConf     	Unsigned32,
        cwRsrcPartEgrPctBwUsed          Unsigned32,
        cwRsrcPartIngPctBwUsed          Unsigned32,
        cwRsrcPartEgrPctBwAvail         Unsigned32,
        cwRsrcPartIngPctBwAvail         Unsigned32,
        cwRsrcPartVpiLo                 Unsigned32,
        cwRsrcPartVpiHigh      	        Unsigned32,
        cwRsrcPartVciLo	       		Unsigned32,
        cwRsrcPartVciHigh      		Unsigned32,
        cwRsrcPartGuarCon 	        Unsigned32,
        cwRsrcPartMaxCon		Unsigned32,
        cwRsrcPartUsedCon		Unsigned32,
        cwRsrcPartAvailCon		Unsigned32,
        cwRsrcPartRowStatus    	  	RowStatus
    }

cwRsrcPartID OBJECT-TYPE
    SYNTAX Unsigned32 (1.. 255) 
    MAX-ACCESS not-accessible 
    STATUS  current
    DESCRIPTION 
        "This is resource partition identifier. One interface can
         have multiple resource partitions on it."
    ::= { cwRsrcPartConfEntry 1}

cwRsrcPartController OBJECT-TYPE
    SYNTAX Unsigned32 (1.. 255) 
    MAX-ACCESS read-create 
    STATUS  current
    DESCRIPTION 
        "This is controller identifier. Once a resource partition
         is added the controller identified by this identifier
         can access resources configured for this partition."
    ::= { cwRsrcPartConfEntry 2}

cwRsrcPartEgrGuarPctBwConf OBJECT-TYPE
    SYNTAX  Unsigned32 (0..1000000)
    UNITS "0.0001 percentage"
    MAX-ACCESS  read-create
    STATUS  current
    DESCRIPTION 
        "The guaranteed percentage bandwidth reserved for the 
         resource partition in egress direction.
         The sum of all resource partition guaranteed 
         bandwidths cannot exceed 100% of interface's guaranteed
         bandwidth."
    DEFVAL { 0 }
    ::= { cwRsrcPartConfEntry 3 }
 
cwRsrcPartEgrMaxPctBwConf OBJECT-TYPE
    SYNTAX  Unsigned32 (0..1000000)
    UNITS "0.0001 percentage"
    MAX-ACCESS  read-create
    STATUS  current
    DESCRIPTION 
       "The maximum percentage bandwidth for the resource partition 
        in egress direction. This is not the guaranteed bandwidth.
        If bandwidth is available, the resource partition will be
        allocated bandwidth up to this value."
    DEFVAL { 0 }
    ::= { cwRsrcPartConfEntry 4 }

cwRsrcPartIngGuarPctBwConf OBJECT-TYPE
    SYNTAX  Unsigned32 (0..1000000)
    UNITS "0.0001 percentage"
    MAX-ACCESS  read-create
    STATUS  current
    DESCRIPTION 
        "The guaranteed percentage bandwidth reserved for the 
         resource partition in ingress direction.
         The sum of all resource partition guaranteed
         bandwidths cannot exceed 100% of the interface's guaranteed
         bandwidth."
    DEFVAL { 0 }
    ::= { cwRsrcPartConfEntry 5 }
 
cwRsrcPartIngMaxPctBwConf OBJECT-TYPE
    SYNTAX  Unsigned32 (0..1000000)
    UNITS "0.0001 percentage"
    MAX-ACCESS  read-create
    STATUS  current
    DESCRIPTION 
      " The maximum percentage bandwidth allocated for the resource 
        partition in ingress direction. 
        This is not the guaranteed bandwidth. If bandwidth
        is available, the resource partition will be allocated 
        bandwidth up to this value."
    DEFVAL { 0 }
    ::= { cwRsrcPartConfEntry 6 }

cwRsrcPartEgrPctBwUsed OBJECT-TYPE
    SYNTAX  Unsigned32 (0..1000000)
    UNITS "0.0001 percentage"
    MAX-ACCESS  read-only
    STATUS  current
    DESCRIPTION
      " This is the percentage bandwidth used by the resource
        partition in egress direction."
    ::= { cwRsrcPartConfEntry 7 }
 
cwRsrcPartIngPctBwUsed OBJECT-TYPE
    SYNTAX  Unsigned32 (0..1000000)
    UNITS "0.0001 percentage"
    MAX-ACCESS  read-only
    STATUS  current
    DESCRIPTION
      " This is the percentage bandwidth used by the resource
        partition in ingress direction."
    ::= { cwRsrcPartConfEntry 8 }

cwRsrcPartEgrPctBwAvail OBJECT-TYPE
    SYNTAX  Unsigned32 (0..1000000)
    UNITS "0.0001 percentage"
    MAX-ACCESS  read-only
    STATUS  current
    DESCRIPTION
      " This is the percentage bandwidth available on the resource
        partition in egress direction."
    ::= { cwRsrcPartConfEntry 9 }

cwRsrcPartIngPctBwAvail OBJECT-TYPE
    SYNTAX  Unsigned32 (0..1000000)
    UNITS "0.0001 percentage"
    MAX-ACCESS  read-only
    STATUS  current
    DESCRIPTION
      " This is the percentage bandwidth available on the resource
        partition in ingress direction."
    ::= { cwRsrcPartConfEntry 10 }
 
cwRsrcPartVpiLo OBJECT-TYPE
    SYNTAX  Unsigned32 (0..4095)
    MAX-ACCESS  read-create
    STATUS  current
    DESCRIPTION 
         "The beginning of the VPI range for this partition. Connections
          provisioned on this partition must  have a VPI greater than or
          equal to this value."
    ::= { cwRsrcPartConfEntry 11 }
 
cwRsrcPartVpiHigh OBJECT-TYPE
    SYNTAX  Unsigned32 (0..4095)
    MAX-ACCESS  read-create
    STATUS  current
    DESCRIPTION 
        "The end of the VPI range for this partition.  Connections
         provisioned on this partition must have a VPI less than or
         equal to this value."
    ::= { cwRsrcPartConfEntry 12 }
 
cwRsrcPartVciLo OBJECT-TYPE
    SYNTAX  Unsigned32 (0..65535)
    MAX-ACCESS  read-create
    STATUS  current
    DESCRIPTION 
        "The beginning of the VCI range  for this partition. Connections
         provisioned on this partition must  have VCI greater than or
         equal to this VCI."
    ::= { cwRsrcPartConfEntry 13 }
 
cwRsrcPartVciHigh OBJECT-TYPE
    SYNTAX  Unsigned32 (0..65535)
    MAX-ACCESS  read-create
    STATUS  current
    DESCRIPTION 
        "The end of the VCI range reserved for this partition.
         Connections provisioned on this partition must have a VCI
         less than or equal to this VCI."
    ::= { cwRsrcPartConfEntry 14 }
 
cwRsrcPartGuarCon  OBJECT-TYPE
    SYNTAX  Unsigned32 (0..131072)
    MAX-ACCESS  read-create
    STATUS  current
    DESCRIPTION 
       "The guaranteed number of connections that can be
        configured on this partition."
    DEFVAL {0}
    ::= { cwRsrcPartConfEntry 15 }
 
cwRsrcPartMaxCon  OBJECT-TYPE
    SYNTAX  Unsigned32 (0..131072)
    MAX-ACCESS  read-create
    STATUS  current
    DESCRIPTION 
       "The maximum number of connections that can be configured on
        this partition."
::= { cwRsrcPartConfEntry 16 }

cwRsrcPartUsedCon  OBJECT-TYPE
    SYNTAX  Unsigned32 (0..131072)
    MAX-ACCESS  read-only
    STATUS  current
    DESCRIPTION
       "This is the number of connections currently in use on this
        partition." 
::= { cwRsrcPartConfEntry 17 }

cwRsrcPartAvailCon  OBJECT-TYPE
    SYNTAX  Unsigned32 (0..131072)
    MAX-ACCESS  read-only
    STATUS  current
    DESCRIPTION
       "This is the number of connections available, that can be 
        added on this partition."
::= { cwRsrcPartConfEntry 18 }

cwRsrcPartRowStatus OBJECT-TYPE
    SYNTAX RowStatus
    MAX-ACCESS  read-create
    STATUS  current
    DESCRIPTION
       "This will add, delete or modify the partition. Resource
        partition can be created by setting this object to
        createAndGo(4).  Row may be deleted by setting this object
        to destroy(6)."
    ::= { cwRsrcPartConfEntry 19 }

-- --------------------------------------------------------------------
-- cwRsrcPartIlmi Table
-- --------------------------------------------------------------------
 
cwRsrcPartIlmiTable    OBJECT-TYPE
    SYNTAX SEQUENCE OF CwRsrcPartIlmiEntry
    MAX-ACCESS not-accessible
    STATUS     current
    DESCRIPTION
        "This is the ILMI configuration table. If the interface supports
         ILMI, the agent will automatically create a row in this table
         when a row is created in cwRsrcPartConfTable. The ILMI objects
         will be set with default values, i.e, with ILMI signalling
         disabled."
    ::= { cwRsrcPartConfGrp 2 }
 
cwRsrcPartIlmiEntry OBJECT-TYPE
    SYNTAX    CwRsrcPartIlmiEntry
    MAX-ACCESS not-accessible
    STATUS    current
    DESCRIPTION 
       "If the interface supports ILMI, the agent will automatically 
        create an entry in this table when a resource partition is
        created.  By default, ILMI is disabled on resource partitions.
        ILMI can be enabled by setting 'cwRsrcPartIlmiEnabled' to
        'true'.  An entry will be deleted from this table when
        a corresponding resource partition entry is deleted from
        cwRsrcPartConfTable."
    INDEX    { ifIndex, cwRsrcPartID }
    ::= { cwRsrcPartIlmiTable 1} 

CwRsrcPartIlmiEntry  ::=
    SEQUENCE {
        cwRsrcPartIlmiEnabled          		TruthValue,
        cwRsrcPartSignallingVpi        		INTEGER,
        cwRsrcPartSignallingVci        		INTEGER,
        cwRsrcPartIlmiTrapEnable        	TruthValue,
        cwRsrcPartIlmiEstablishConPollIntvl	Unsigned32,
        cwRsrcPartIlmiCheckConPollIntvl     	Unsigned32,
        cwRsrcPartIlmiConPollInactFactor        Unsigned32
    }

cwRsrcPartIlmiEnabled OBJECT-TYPE
    SYNTAX TruthValue 
    MAX-ACCESS read-write
    STATUS  current
    DESCRIPTION
       "By setting the value of this object to 'true', ILMI signalling
        is enabled on the resource partition." 
    DEFVAL {false} 
    ::= { cwRsrcPartIlmiEntry 1 }

cwRsrcPartSignallingVpi   OBJECT-TYPE
    SYNTAX    INTEGER (0..4095 )
    MAX-ACCESS read-write
    STATUS    current
    DESCRIPTION 
        "Indicates the VPI on which signalling cells arrive on this
         resource partition."
    DEFVAL { 0 }
    ::= { cwRsrcPartIlmiEntry 2}
 
cwRsrcPartSignallingVci OBJECT-TYPE
    SYNTAX    INTEGER (0..65535 )
    MAX-ACCESS read-write
    STATUS     current
    DESCRIPTION 
        "Indicates the VCI on which signalling cells arrive on this
         resource partition."
    DEFVAL { 16 }
    ::= { cwRsrcPartIlmiEntry 3}
 
cwRsrcPartIlmiTrapEnable OBJECT-TYPE
    SYNTAX    TruthValue
    MAX-ACCESS    read-write
    STATUS    current
    DESCRIPTION 
        "ILMI trap generation can be enabled or disabled using
         this object."
    ::= { cwRsrcPartIlmiEntry 4}

cwRsrcPartIlmiEstablishConPollIntvl    OBJECT-TYPE
    SYNTAX       Unsigned32 (1..65535)
    UNITS        "seconds"
    MAX-ACCESS   read-write
    STATUS       current
    DESCRIPTION
       "The amount of time S between successive transmissions
        of ILMI messages on this interface for the purpose of
        detecting establishment of ILMI connectivity."
    REFERENCE
       "ATM Forum ILMI 4.0 Section 8.3.1"
    DEFVAL { 1 }
    ::= { cwRsrcPartIlmiEntry 5 }
 
cwRsrcPartIlmiCheckConPollIntvl    OBJECT-TYPE
     SYNTAX       Unsigned32 (0..65535)
     UNITS        "seconds"
     MAX-ACCESS   read-write
     STATUS       current
     DESCRIPTION
        "The amount of time T between successive transmissions
         of ILMI messages on this interface for the purpose of
         detecting loss of ILMI connectivity.  The distinguished
         value zero disables ILMI connectivity procedures on
         this interface."
     REFERENCE
         "ATM Forum ILMI 4.0 Section 8.3.1"
     DEFVAL { 5 }
     ::= { cwRsrcPartIlmiEntry 6 }

cwRsrcPartIlmiConPollInactFactor    OBJECT-TYPE
      SYNTAX       Unsigned32 (0..65535)
      MAX-ACCESS   read-write
      STATUS       current
      DESCRIPTION
         "The number K of consecutive polls on this interface
         for which no ILMI response message is received before
         ILMI connectivity is declared lost."
      REFERENCE
          "ATM Forum ILMI 4.0 Section 8.3.1"
      DEFVAL { 4 }
      ::= { cwRsrcPartIlmiEntry 7 }

-- ----------------------------------------------------------------------
-- cwRsrcPartCtlrConf Table
-- ----------------------------------------------------------------------
 
cwRsrcPartCtlrConfTable  OBJECT-TYPE
    SYNTAX  SEQUENCE OF CwRsrcPartCtlrConfEntry
    MAX-ACCESS  not-accessible
    STATUS  current
    DESCRIPTION
        "This table is for configuring additional controllers to
         manage a resource partition."
   ::= { cwRsrcPartConfGrp 3 }
 
cwRsrcPartCtlrConfEntry  OBJECT-TYPE
    SYNTAX  CwRsrcPartCtlrConfEntry
    MAX-ACCESS  not-accessible
    STATUS  current
    DESCRIPTION
        "An entry for additional controllers to control an existing
         resource partition. The resource partition, identified by
         indices ifIndex and cwRsrcPartID, must exist in the
         cwRsrcPartConfTable.  An entry from this table is deleted if
         the cwRsrcPartID associated entry from cwRsrcPartConfTable is
         deleted."
    INDEX   { ifIndex, cwRsrcPartID, cwRsrcPartCtlrController}
    ::= { cwRsrcPartCtlrConfTable 1 }
 
CwRsrcPartCtlrConfEntry ::=
    SEQUENCE {
        cwRsrcPartCtlrController            Unsigned32,
        cwRsrcPartCtlrRowStatus             RowStatus
    }
 
cwRsrcPartCtlrController OBJECT-TYPE
    SYNTAX Unsigned32 (1.. 255)
    MAX-ACCESS not-accessible
    STATUS  current
    DESCRIPTION
        "This is controller identifier. One resource partition can be
         controlled by multiple controllers.User may want to do this to
         configure redundant controllers."
    ::= { cwRsrcPartCtlrConfEntry 1}

cwRsrcPartCtlrRowStatus OBJECT-TYPE
    SYNTAX RowStatus
    MAX-ACCESS  read-create
    STATUS  current
    DESCRIPTION
       "This is used to  create a row in the cwRsrcPartCtlrConfTable.
        A redundant controller is added by  setting this object to 
        createAndGo(4).
        Row may be deleted by setting this object to destroy(6)."
    ::= { cwRsrcPartCtlrConfEntry 2}

-- ---------------------------------------------------------------------
--
-- SVC Aggregate Table
--  
-- ---------------------------------------------------------------------
cwRsrcSvcAggregateTable  OBJECT-TYPE
    SYNTAX               SEQUENCE OF CwRsrcSvcAggregateEntry
    MAX-ACCESS           not-accessible
    STATUS               current
    DESCRIPTION
        "This table is for configuring an SVC aggregate resource within 
         a resource partition. This provides aggregate bandwidth and 
         VPI range within a resource partition that CAC (Call Admission
         Control) can dynamically allocate the required resource from 
         it to establish a SVC connection for the incoming call. 

         The allocated bandwidth will become available in the SVC 
         aggregate when the call is torn down.  When the required 
         bandwidth of an incoming call exceeds the bandwidth available 
         for SVC connection, the CAC will fail the establishment of the 
         new call."
   ::= { cwRsrcSvcAggrGrp 1 }
 
cwRsrcSvcAggregateEntry  OBJECT-TYPE
    SYNTAX               CwRsrcSvcAggregateEntry
    MAX-ACCESS           not-accessible
    STATUS               current
    DESCRIPTION
        "An entry of SVC Aggregate.  
         An SVC Aggregate is used to reserve certain bandwidth
         in the resource partition to be dedicated for call set-up."
    INDEX   { ifIndex, cwRsrcPartID }
    ::= { cwRsrcSvcAggregateTable 1 }
 
CwRsrcSvcAggregateEntry ::=
    SEQUENCE {
              cwRsrcSvcAggrVpiLow            Unsigned32,
              cwRsrcSvcAggrVpiHigh           Unsigned32,
              cwRsrcSvcAggrEgrPctBw          Integer32,
              cwRsrcSvcAggrIngPctBw          Integer32,
              cwRsrcSvcAggrChanVADTolerance  Integer32,
              cwRsrcSvcAggrChanVADDutyCycle  Integer32,
              cwRsrcSvcAggrRowStatus         RowStatus        
              }

cwRsrcSvcAggrVpiLow OBJECT-TYPE
    SYNTAX          Unsigned32 (0..4095)
    MAX-ACCESS      read-create
    STATUS          current
    DESCRIPTION
        "The low end of the VPI range for this SVC aggregate. 
         This value has to be greater than or equal to the value of
         cwRsrcPartVpiLo of the containing resource partition.
         SVC connection provisioned on this SVC aggregate must have 
         a VPI greater than or equal to this value."
    ::= { cwRsrcSvcAggregateEntry 1}

cwRsrcSvcAggrVpiHigh OBJECT-TYPE
    SYNTAX           Unsigned32 (0..4095)
    MAX-ACCESS       read-create
    STATUS           current
    DESCRIPTION
        "The high end of the VPI range for this SVC aggregate.
         This value has to be less than or equal to the value of
         cwRsrcPartVpiHigh of the containing resource partition.
         SVC connection provisioned on this SVC aggregate must have 
         a VPI less than or equal to this value. 

         If cwRsrcSvcAggrVpiLow and cwRsrcSvcAggrVpiHigh are equal, 
         then only one VSI is allocated for this SVC aggregate."
    ::= { cwRsrcSvcAggregateEntry 2}

cwRsrcSvcAggrEgrPctBw OBJECT-TYPE
    SYNTAX            Integer32 (1..100)
    UNITS             "percent"
    MAX-ACCESS        read-create
    STATUS            current
    DESCRIPTION
        "This object indicates the percentage egress bandwidth that  
         is used by SVC connections within the resource partition.

         The total egress bandwidth will be used by SVC connections 
         within the resource partition is determined by 
         multiplying the value of this object and
         cwRsrcPartEgrGuarPctBwConf and port speed (ifSpeed).

         Total egress bandwidth available to SVCs = ifSpeed *
                   cwRsrcPartEgrGuarPctBwConf *
                   cwRsrcSvcAggrEgrPctBw

         Note that the total egress bandwidth for all PVC connections  
         on the resource partition plus the egress bandwidth of SVC 
         aggregate can't be greater than the maximum egress bandwidth 
         (cwRsrcPartEgrMaxPctBwConf) of the containing resource 
         partition."
    ::= { cwRsrcSvcAggregateEntry 3}

cwRsrcSvcAggrIngPctBw OBJECT-TYPE
    SYNTAX            Integer32 (1..100)
    UNITS             "percent"
    MAX-ACCESS        read-create
    STATUS            current
    DESCRIPTION
        "This object indicates the percentage ingress bandwidth that  
         is used by SVC connections within the resource partition.

         The total ingress bandwidth will be used by SVC connections 
         within the resource partition is determined by 
         multiplying the value of this object and
         cwRsrcPartIngGuarPctBwConf and port speed (ifSpeed).

         Total ingress bandwidth available to SVCs = ifSpeed *
                   cwRsrcPartIngGuarPctBwConf *
                   cwRsrcSvcAggrIngPctBw

         Note that the total ingress bandwidth for all PVC connections 
         on the resource partition plus the ingress bandwidth of SVC  
         aggregate can't be greater than the maximum ingress 
         bandwidth (cwRsrcPartIngMaxPctBwConf) of the containing 
         resource partition."
    ::= { cwRsrcSvcAggregateEntry 4}

cwRsrcSvcAggrChanVADTolerance  OBJECT-TYPE
    SYNTAX                     Integer32(1..10000)
    UNITS                      "0.0001"
    MAX-ACCESS                 read-create
    STATUS                     current
    DESCRIPTION
	"The value in this object refers to the customer accepted 
         drop rate for voice connections when the bandwidth usage
         exceeds allowed value.  
                 
         The actual range of this object is 0.0001(or 0.01%) to 
         1.00(or 100%).
  
         However, when the underlying CAC(Connection Admission Control)
         module is notified of the change in this object, then the 
         value has to be divided by a factor of 10000." 
    DEFVAL { 100 }
    ::= { cwRsrcSvcAggregateEntry 5}

cwRsrcSvcAggrChanVADDutyCycle  OBJECT-TYPE
    SYNTAX                     Integer32(1..99) 
    UNITS                      "0.01"  
    MAX-ACCESS                 read-create
    STATUS                     current
    DESCRIPTION
	"This object refers to the talk-spurts duty cycle.
  
         The actual range of this object is 0.01(or 1%) to 
         0.99(or 99%).

         When the value of this object is to be passed to underlying 
         CAC module this value has to be divided by 100." 
    DEFVAL {61}
    ::= { cwRsrcSvcAggregateEntry 6}

cwRsrcSvcAggrRowStatus OBJECT-TYPE
    SYNTAX             RowStatus
    MAX-ACCESS         read-create
    STATUS             current
    DESCRIPTION
        "When an entry of the table is created, the following 
         objects are mandatory:
             cwRsrcSvcAggrVpiLow
             cwRsrcSvcAggrVpiHigh
             cwRsrcSvcAggrEgrPctBw
             cwRsrcSvcAggrIngPctBw "
    ::= { cwRsrcSvcAggregateEntry 7}

-- ---------------------------------------------------------------------
-- conformance information
-- ---------------------------------------------------------------------
 
cwRsrcPartMIBConformance OBJECT IDENTIFIER ::= {ciscoWANRsrcPartMIB 3}

cwRsrcPartMIBCompliances OBJECT IDENTIFIER
     ::= {cwRsrcPartMIBConformance 1}
cwRsrcPartMIBGroups  OBJECT IDENTIFIER
     ::= {cwRsrcPartMIBConformance 2}

cwRsrcPartMIBCompliance MODULE-COMPLIANCE
    STATUS deprecated -- superseded by cwRsrcPartMIBComplianceRev1
    DESCRIPTION
       "The Compliance statement for Resource partition 
        management group."
    MODULE -- this module
    MANDATORY-GROUPS { cwRsrcPartMIBGroup }
    GROUP cwRsrcPartIlmiMIBGroup
    DESCRIPTION
        "Implementation of this group is not mandatory for the
         switches which does not support 
         ILMI(Integrated Local Management Interface)."

    GROUP cwRsrcPartMappingGroup
    DESCRIPTION 
        "Implementation of this group is not mandatory for the
         switches which do not support redundant controllers."

    ::= {cwRsrcPartMIBCompliances 1}

cwRsrcPartMIBComplianceRev1 MODULE-COMPLIANCE
    STATUS current
    DESCRIPTION
       "The Compliance statement for Resource partition 
        management group."
    MODULE -- this module
    MANDATORY-GROUPS { cwRsrcPartMIBGroup }
    GROUP cwRsrcPartIlmiMIBGroup
    DESCRIPTION
        "Implementation of this group is not mandatory for the
         switches which does not support 
         ILMI(Integrated Local Management Interface)."

    GROUP cwRsrcPartMappingGroup
    DESCRIPTION 
        "Implementation of this group is not mandatory for the
         switches which do not support redundant controllers."

    GROUP cwRsrcSvcAggrGroup
    DESCRIPTION 
        "Implementation of this group is not mandatory for the
         switches which does not support SVC aggregate."

    ::= {cwRsrcPartMIBCompliances 2}

-- units of conformance
cwRsrcPartMIBGroup OBJECT-GROUP
        OBJECTS {
            cwRsrcPartController,
            cwRsrcPartEgrGuarPctBwConf,
            cwRsrcPartEgrMaxPctBwConf,
            cwRsrcPartIngGuarPctBwConf,
            cwRsrcPartIngMaxPctBwConf,
            cwRsrcPartEgrPctBwAvail,
            cwRsrcPartIngPctBwAvail,
            cwRsrcPartEgrPctBwUsed,
            cwRsrcPartIngPctBwUsed,
            cwRsrcPartVpiLo,
            cwRsrcPartVpiHigh,
            cwRsrcPartVciLo,
            cwRsrcPartVciHigh,
            cwRsrcPartGuarCon,
            cwRsrcPartMaxCon,
            cwRsrcPartUsedCon,
            cwRsrcPartAvailCon,
            cwRsrcPartRowStatus
        }
       STATUS current
       DESCRIPTION
          "These are objects related to Resource partition group."
       ::= { cwRsrcPartMIBGroups 1}
 
cwRsrcPartIlmiMIBGroup  OBJECT-GROUP
        OBJECTS {
	    cwRsrcPartIlmiEnabled,
            cwRsrcPartSignallingVpi,
            cwRsrcPartSignallingVci,
            cwRsrcPartIlmiTrapEnable,
            cwRsrcPartIlmiEstablishConPollIntvl,
            cwRsrcPartIlmiCheckConPollIntvl,
            cwRsrcPartIlmiConPollInactFactor
       }
       STATUS current
       DESCRIPTION
          "These are objects related to Ilmi configuration on a 
           Resource partition."
       ::= { cwRsrcPartMIBGroups 2}

cwRsrcPartMappingGroup  OBJECT-GROUP
       OBJECTS {
           cwRsrcPartCtlrRowStatus
       }
       STATUS current
       DESCRIPTION
          "These are objects used to configure redundant controllers
           for resource partitions." 
       ::= { cwRsrcPartMIBGroups 3}

cwRsrcSvcAggrGroup  OBJECT-GROUP
       OBJECTS {
              cwRsrcSvcAggrVpiLow,
              cwRsrcSvcAggrVpiHigh,
              cwRsrcSvcAggrEgrPctBw,
              cwRsrcSvcAggrIngPctBw,
              cwRsrcSvcAggrChanVADTolerance,
              cwRsrcSvcAggrChanVADDutyCycle,
              cwRsrcSvcAggrRowStatus      
       }
       STATUS       current
       DESCRIPTION
          "These are objects used to configure SVC aggregate within
           resource partitions." 

       ::= { cwRsrcPartMIBGroups 4}


END
