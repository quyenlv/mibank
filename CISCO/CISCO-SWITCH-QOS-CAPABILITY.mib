-- ****************************************************************
-- Cisco CISCO-SWITCH-QOS-MIB AGENT-CAPABILITIES
--   
-- June 2007, Edward Pham
--   
-- Copyright (c) 2007, 2008, 2010 by Cisco Systems, Inc.
-- All rights reserved.
-- *****************************************************************

CISCO-SWITCH-QOS-CAPABILITY DEFINITIONS ::= BEGIN

IMPORTS
    MODULE-IDENTITY
        FROM SNMPv2-SMI
    AGENT-CAPABILITIES
        FROM SNMPv2-CONF
    ciscoAgentCapability
        FROM CISCO-SMI;


ciscoSwitchQosCapability MODULE-IDENTITY
    LAST-UPDATED    "201011170000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of CISCO-SWITCH-QOS-MIB."
    REVISION        "201011170000Z"
    DESCRIPTION
        "Add ciscoSwitchQosCapV12R0250SYPCat6k agent
        capability statement."
    REVISION        "201003190000Z"
    DESCRIPTION
        "Add ciscoSwitchQosCapV12R0233SXI4PCat6k agent
        capability statement."
    REVISION        "200806040000Z"
    DESCRIPTION
        "Add ciscoSwitchQosCapV12R0233SXIPCat6k agent
        capability statement."
    REVISION        "200706290000Z"
    DESCRIPTION
        "Initial version of this MIB module."
    ::= { ciscoAgentCapability 541 }



ciscoSwitchQosCapV12R0233SXHPCat6k AGENT-CAPABILITIES
    PRODUCT-RELEASE "Cisco IOS 12.2(33)SXH on Catalyst 6000/6500
                         devices."
    STATUS          current
    DESCRIPTION
        "CISCO-SWITCH-QOS-MIB capabilities."

    SUPPORTS        CISCO-SWITCH-QOS-MIB
    INCLUDES        {
                        ciscoSwitchQosIfConfigGroup,
                        ciscoSwitchQosIfStatsGroup,
                        ciscoSwitchQosModuleStatsGroup,
                        ciscoSwitchQosPortQueueingGroup,
                        ciscoSwitchQosRedirectPolicingGroup,
                        ciscoSwitchQosDscpRewriteGroup,
                        ciscoSwitchQosMappingGroup,
                        ciscoSwitchQosMutationGroup,
                        ciscoSwitchQosIfCosToQueueGroup,
                        ciscoSwitchQosIfDropConfigGroup,
                        ciscoSwitchQosIfQueueGroup,
                        ciscoSwitchQosMarkingStatsGroup,
                        ciscoSwitchQosIfModeConfigGroup,
                        ciscoSwitchQosIfCCGroup
                    }
    VARIATION       csqDscpRewriteEnable
    ACCESS          read-only
    DESCRIPTION
        "Unable to set this in this release."

    VARIATION       csqPoliceRedirectedTrafficEnable
    ACCESS          read-only
    DESCRIPTION
        "Unable to set this in this release."

    VARIATION       csqPortQueueingModeEnable
    ACCESS          read-only
    DESCRIPTION
        "Unable to set this in this release."

    VARIATION       csqMarkingStatisticsEnable
    ACCESS          read-only
    DESCRIPTION
        "Unable to set this in this release."

    VARIATION       csqCosToDscpDscp
    ACCESS          read-only
    DESCRIPTION
        "Unable to set this in this release."

    VARIATION       csqIpPrecToDscpDscp
    ACCESS          read-only
    DESCRIPTION
        "Unable to set this in this release."

    VARIATION       csqExpToDscpDscp
    ACCESS          read-only
    DESCRIPTION
        "Unable to set this in this release."

    VARIATION       csqDscpMappingCos
    ACCESS          read-only
    DESCRIPTION
        "Unable to set this in this release."

    VARIATION       csqDscpMappingExp
    ACCESS          read-only
    DESCRIPTION
        "Unable to set this in this release."

    VARIATION       csqDscpMappingNormalBurstDscp
    ACCESS          read-only
    DESCRIPTION
        "Unable to set this in this release."

    VARIATION       csqDscpMappingMaxBurstDscp
    ACCESS          read-only
    DESCRIPTION
        "Unable to set this in this release."

    VARIATION       csqCosMutationRowStatus
    ACCESS          read-only
    DESCRIPTION
        "Unable to set this in this release."

    VARIATION       csqCosMutationToCos
    ACCESS          read-only
    DESCRIPTION
        "Unable to set this in this release."

    VARIATION       csqDscpMutationRowStatus
    ACCESS          read-only
    DESCRIPTION
        "Unable to set this in this release."

    VARIATION       csqDscpMutationToDscp
    ACCESS          read-only
    DESCRIPTION
        "Unable to set this in this release."

    VARIATION       csqExpMutationRowStatus
    ACCESS          read-only
    DESCRIPTION
        "Unable to set this in this release."

    VARIATION       csqExpMutationToExp
    ACCESS          read-only
    DESCRIPTION
        "Unable to set this in this release."

    VARIATION       csqIfCosMutationMap
    ACCESS          read-only
    DESCRIPTION
        "Unable to set this in this release."

    VARIATION       csqIfDscpMutationMap
    ACCESS          read-only
    DESCRIPTION
        "Unable to set this in this release."

    VARIATION       csqIfExpMutationMap
    ACCESS          read-only
    DESCRIPTION
        "Unable to set this in this release."

    VARIATION       csqIfMutationRowStatus
    ACCESS          read-only
    DESCRIPTION
        "Unable to set this in this release."

    VARIATION       csqIfDefaultCos
    ACCESS          read-only
    DESCRIPTION
        "Unable to set this in this release."

    VARIATION       csqIfTrustState
    ACCESS          read-only
    DESCRIPTION
        "Unable to set this in this release."

    VARIATION       csqIfCosToQueueQueueNumber
    ACCESS          read-only
    DESCRIPTION
        "Unable to set this in this release."

    VARIATION       csqIfCosToQueueThresholdNumber
    ACCESS          read-only
    DESCRIPTION
        "Unable to set this in this release."

    VARIATION       csqIfDropConfigDropAlgorithm
    ACCESS          read-only
    DESCRIPTION
        "Unable to set this in this release."

    VARIATION       csqIfDropConfigDropThreshold
    ACCESS          read-only
    DESCRIPTION
        "Unable to set this in this release."

    VARIATION       csqIfDropConfigMinWredThreshold
    ACCESS          read-only
    DESCRIPTION
        "Unable to set this in this release."

    VARIATION       csqIfDropConfigMaxWredThreshold
    ACCESS          read-only
    DESCRIPTION
        "Unable to set this in this release."

    VARIATION       csqIfQueueWrrWeight
    ACCESS          read-only
    DESCRIPTION
        "Unable to set this in this release."

    VARIATION       csqIfQueueSizeWeight
    ACCESS          read-only
    DESCRIPTION
        "Unable to set this in this release."

    VARIATION       csqIfVlanBasedQosModeEnable
    ACCESS          read-only
    DESCRIPTION
        "Unable to set this in this release."

    VARIATION       csqIfConsistencyCheckEnable
    ACCESS          read-only
    DESCRIPTION
        "Unable to set this in this release."

    ::= { ciscoSwitchQosCapability 1 }

ciscoSwitchQosCapV12R0233SXIPCat6k AGENT-CAPABILITIES
    PRODUCT-RELEASE "Cisco IOS 12.2(33)SXI on Catalyst 6000/6500
                         devices."
    STATUS          current
    DESCRIPTION
        "CISCO-SWITCH-QOS-MIB capabilities."

    SUPPORTS        CISCO-SWITCH-QOS-MIB
    INCLUDES        {
                        ciscoSwitchQosIfConfigGroup,
                        ciscoSwitchQosIfStatsGroup,
                        ciscoSwitchQosModuleStatsGroup,
                        ciscoSwitchQosPortQueueingGroup,
                        ciscoSwitchQosRedirectPolicingGroup,
                        ciscoSwitchQosDscpRewriteGroup,
                        ciscoSwitchQosMappingGroup,
                        ciscoSwitchQosMutationGroup,
                        ciscoSwitchQosIfCosToQueueGroup,
                        ciscoSwitchQosIfDropConfigGroup,
                        ciscoSwitchQosIfQueueGroup,
                        ciscoSwitchQosMarkingStatsGroup,
                        ciscoSwitchQosIfModeConfigGroup,
                        ciscoSwitchQosIfCCGroup,
                        ciscoSwitchQosPolicerUsageGroup
                    }
    VARIATION       csqDscpRewriteEnable
    ACCESS          read-only
    DESCRIPTION
        "Unable to set this in this release."

    VARIATION       csqPoliceRedirectedTrafficEnable
    ACCESS          read-only
    DESCRIPTION
        "Unable to set this in this release."

    VARIATION       csqPortQueueingModeEnable
    ACCESS          read-only
    DESCRIPTION
        "Unable to set this in this release."

    VARIATION       csqMarkingStatisticsEnable
    ACCESS          read-only
    DESCRIPTION
        "Unable to set this in this release."

    VARIATION       csqCosToDscpDscp
    ACCESS          read-only
    DESCRIPTION
        "Unable to set this in this release."

    VARIATION       csqIpPrecToDscpDscp
    ACCESS          read-only
    DESCRIPTION
        "Unable to set this in this release."

    VARIATION       csqExpToDscpDscp
    ACCESS          read-only
    DESCRIPTION
        "Unable to set this in this release."

    VARIATION       csqDscpMappingCos
    ACCESS          read-only
    DESCRIPTION
        "Unable to set this in this release."

    VARIATION       csqDscpMappingExp
    ACCESS          read-only
    DESCRIPTION
        "Unable to set this in this release."

    VARIATION       csqDscpMappingNormalBurstDscp
    ACCESS          read-only
    DESCRIPTION
        "Unable to set this in this release."

    VARIATION       csqDscpMappingMaxBurstDscp
    ACCESS          read-only
    DESCRIPTION
        "Unable to set this in this release."

    VARIATION       csqCosMutationRowStatus
    ACCESS          read-only
    DESCRIPTION
        "Unable to set this in this release."

    VARIATION       csqCosMutationToCos
    ACCESS          read-only
    DESCRIPTION
        "Unable to set this in this release."

    VARIATION       csqDscpMutationRowStatus
    ACCESS          read-only
    DESCRIPTION
        "Unable to set this in this release."

    VARIATION       csqDscpMutationToDscp
    ACCESS          read-only
    DESCRIPTION
        "Unable to set this in this release."

    VARIATION       csqExpMutationRowStatus
    ACCESS          read-only
    DESCRIPTION
        "Unable to set this in this release."

    VARIATION       csqExpMutationToExp
    ACCESS          read-only
    DESCRIPTION
        "Unable to set this in this release."

    VARIATION       csqIfCosMutationMap
    ACCESS          read-only
    DESCRIPTION
        "Unable to set this in this release."

    VARIATION       csqIfDscpMutationMap
    ACCESS          read-only
    DESCRIPTION
        "Unable to set this in this release."

    VARIATION       csqIfExpMutationMap
    ACCESS          read-only
    DESCRIPTION
        "Unable to set this in this release."

    VARIATION       csqIfMutationRowStatus
    ACCESS          read-only
    DESCRIPTION
        "Unable to set this in this release."

    VARIATION       csqIfDefaultCos
    ACCESS          read-only
    DESCRIPTION
        "Unable to set this in this release."

    VARIATION       csqIfTrustState
    ACCESS          read-only
    DESCRIPTION
        "Unable to set this in this release."

    VARIATION       csqIfCosToQueueQueueNumber
    ACCESS          read-only
    DESCRIPTION
        "Unable to set this in this release."

    VARIATION       csqIfCosToQueueThresholdNumber
    ACCESS          read-only
    DESCRIPTION
        "Unable to set this in this release."

    VARIATION       csqIfDropConfigDropAlgorithm
    ACCESS          read-only
    DESCRIPTION
        "Unable to set this in this release."

    VARIATION       csqIfDropConfigDropThreshold
    ACCESS          read-only
    DESCRIPTION
        "Unable to set this in this release."

    VARIATION       csqIfDropConfigMinWredThreshold
    ACCESS          read-only
    DESCRIPTION
        "Unable to set this in this release."

    VARIATION       csqIfDropConfigMaxWredThreshold
    ACCESS          read-only
    DESCRIPTION
        "Unable to set this in this release."

    VARIATION       csqIfQueueWrrWeight
    ACCESS          read-only
    DESCRIPTION
        "Unable to set this in this release."

    VARIATION       csqIfQueueSizeWeight
    ACCESS          read-only
    DESCRIPTION
        "Unable to set this in this release."

    VARIATION       csqIfVlanBasedQosModeEnable
    ACCESS          read-only
    DESCRIPTION
        "Unable to set this in this release."

    VARIATION       csqIfConsistencyCheckEnable
    ACCESS          read-only
    DESCRIPTION
        "Unable to set this in this release."

    ::= { ciscoSwitchQosCapability 2 }

ciscoSwitchQosCapV12R0233SXI4PCat6k AGENT-CAPABILITIES
    PRODUCT-RELEASE "Cisco IOS 12.2(33)SXI4 on Catalyst 6000/6500
                         devices."
    STATUS          current
    DESCRIPTION
        "CISCO-SWITCH-QOS-MIB capabilities."

    SUPPORTS        CISCO-SWITCH-QOS-MIB
    INCLUDES        {
                        ciscoSwitchQosIfConfigGroup,
                        ciscoSwitchQosIfStatsGroup,
                        ciscoSwitchQosModuleStatsGroup,
                        ciscoSwitchQosPortQueueingGroup,
                        ciscoSwitchQosRedirectPolicingGroup,
                        ciscoSwitchQosDscpRewriteGroup,
                        ciscoSwitchQosMappingGroup,
                        ciscoSwitchQosMutationGroup,
                        ciscoSwitchQosIfCosToQueueGroup,
                        ciscoSwitchQosIfDropConfigGroup,
                        ciscoSwitchQosIfQueueGroup,
                        ciscoSwitchQosMarkingStatsGroup,
                        ciscoSwitchQosIfModeConfigGroup,
                        ciscoSwitchQosIfCCGroup,
                        ciscoSwitchQosPolicerUsageGroup,
                        ciscoSwitchQosIfDscpAssignGroup
                    }
    VARIATION       csqDscpRewriteEnable
    ACCESS          read-only
    DESCRIPTION
        "Unable to set this in this release."

    VARIATION       csqPoliceRedirectedTrafficEnable
    ACCESS          read-only
    DESCRIPTION
        "Unable to set this in this release."

    VARIATION       csqPortQueueingModeEnable
    ACCESS          read-only
    DESCRIPTION
        "Unable to set this in this release."

    VARIATION       csqMarkingStatisticsEnable
    ACCESS          read-only
    DESCRIPTION
        "Unable to set this in this release."

    VARIATION       csqCosToDscpDscp
    ACCESS          read-only
    DESCRIPTION
        "Unable to set this in this release."

    VARIATION       csqIpPrecToDscpDscp
    ACCESS          read-only
    DESCRIPTION
        "Unable to set this in this release."

    VARIATION       csqExpToDscpDscp
    ACCESS          read-only
    DESCRIPTION
        "Unable to set this in this release."

    VARIATION       csqDscpMappingCos
    ACCESS          read-only
    DESCRIPTION
        "Unable to set this in this release."

    VARIATION       csqDscpMappingExp
    ACCESS          read-only
    DESCRIPTION
        "Unable to set this in this release."

    VARIATION       csqDscpMappingNormalBurstDscp
    ACCESS          read-only
    DESCRIPTION
        "Unable to set this in this release."

    VARIATION       csqDscpMappingMaxBurstDscp
    ACCESS          read-only
    DESCRIPTION
        "Unable to set this in this release."

    VARIATION       csqCosMutationRowStatus
    ACCESS          read-only
    DESCRIPTION
        "Unable to set this in this release."

    VARIATION       csqCosMutationToCos
    ACCESS          read-only
    DESCRIPTION
        "Unable to set this in this release."

    VARIATION       csqDscpMutationRowStatus
    ACCESS          read-only
    DESCRIPTION
        "Unable to set this in this release."

    VARIATION       csqDscpMutationToDscp
    ACCESS          read-only
    DESCRIPTION
        "Unable to set this in this release."

    VARIATION       csqExpMutationRowStatus
    ACCESS          read-only
    DESCRIPTION
        "Unable to set this in this release."

    VARIATION       csqExpMutationToExp
    ACCESS          read-only
    DESCRIPTION
        "Unable to set this in this release."

    VARIATION       csqIfCosMutationMap
    ACCESS          read-only
    DESCRIPTION
        "Unable to set this in this release."

    VARIATION       csqIfDscpMutationMap
    ACCESS          read-only
    DESCRIPTION
        "Unable to set this in this release."

    VARIATION       csqIfExpMutationMap
    ACCESS          read-only
    DESCRIPTION
        "Unable to set this in this release."

    VARIATION       csqIfMutationRowStatus
    ACCESS          read-only
    DESCRIPTION
        "Unable to set this in this release."

    VARIATION       csqIfDefaultCos
    ACCESS          read-only
    DESCRIPTION
        "Unable to set this in this release."

    VARIATION       csqIfTrustState
    ACCESS          read-only
    DESCRIPTION
        "Unable to set this in this release."

    VARIATION       csqIfCosToQueueQueueNumber
    ACCESS          read-only
    DESCRIPTION
        "Unable to set this in this release."

    VARIATION       csqIfCosToQueueThresholdNumber
    ACCESS          read-only
    DESCRIPTION
        "Unable to set this in this release."

    VARIATION       csqIfDropConfigDropAlgorithm
    ACCESS          read-only
    DESCRIPTION
        "Unable to set this in this release."

    VARIATION       csqIfDropConfigDropThreshold
    ACCESS          read-only
    DESCRIPTION
        "Unable to set this in this release."

    VARIATION       csqIfDropConfigMinWredThreshold
    ACCESS          read-only
    DESCRIPTION
        "Unable to set this in this release."

    VARIATION       csqIfDropConfigMaxWredThreshold
    ACCESS          read-only
    DESCRIPTION
        "Unable to set this in this release."

    VARIATION       csqIfQueueWrrWeight
    ACCESS          read-only
    DESCRIPTION
        "Unable to set this in this release."

    VARIATION       csqIfQueueSizeWeight
    ACCESS          read-only
    DESCRIPTION
        "Unable to set this in this release."

    VARIATION       csqIfVlanBasedQosModeEnable
    ACCESS          read-only
    DESCRIPTION
        "Unable to set this in this release."

    VARIATION       csqIfConsistencyCheckEnable
    ACCESS          read-only
    DESCRIPTION
        "Unable to set this in this release."

    VARIATION       csqIfDscpToQueueQueueNumber
    ACCESS          read-only
    DESCRIPTION
        "Unable to set this in this release."

    VARIATION       csqIfDscpToQueueThresholdNumber
    ACCESS          read-only
    DESCRIPTION
        "Unable to set this in this release."

    ::= { ciscoSwitchQosCapability 3 }

ciscoSwitchQosCapV12R0250SYPCat6k AGENT-CAPABILITIES
    PRODUCT-RELEASE "Cisco IOS 12.2(50)SY on Catalyst 6000/6500
                         devices."
    STATUS          current
    DESCRIPTION
        "CISCO-SWITCH-QOS-MIB capabilities."

    SUPPORTS        CISCO-SWITCH-QOS-MIB
    INCLUDES        {
                        ciscoSwitchQosIfConfigGroup,
                        ciscoSwitchQosIfStatsGroup,
                        ciscoSwitchQosModuleStatsGroup,
                        ciscoSwitchQosPortQueueingGroup,
                        ciscoSwitchQosRedirectPolicingGroup,
                        ciscoSwitchQosDscpRewriteGroup,
                        ciscoSwitchQosMappingGroup,
                        ciscoSwitchQosMutationGroup,
                        ciscoSwitchQosIfCosToQueueGroup,
                        ciscoSwitchQosIfDropConfigGroup,
                        ciscoSwitchQosIfQueueGroup,
                        ciscoSwitchQosMarkingStatsGroup,
                        ciscoSwitchQosIfModeConfigGroup,
                        ciscoSwitchQosIfCCGroup,
                        ciscoSwitchQosPolicerUsageGroup,
                        ciscoSwitchQosIfDscpAssignGroup,
                        ciscoSwitchQosModuleStatsExtGroup,
                        ciscoSwitchQosIfStatsExtGroup
                    }
    VARIATION       csqDscpRewriteEnable
    ACCESS          read-only
    DESCRIPTION
        "Unable to set this in this release."

    VARIATION       csqPoliceRedirectedTrafficEnable
    ACCESS          read-only
    DESCRIPTION
        "Unable to set this in this release."

    VARIATION       csqPortQueueingModeEnable
    ACCESS          read-only
    DESCRIPTION
        "Unable to set this in this release."

    VARIATION       csqMarkingStatisticsEnable
    ACCESS          read-only
    DESCRIPTION
        "Unable to set this in this release."

    VARIATION       csqCosToDscpDscp
    ACCESS          read-only
    DESCRIPTION
        "Unable to set this in this release."

    VARIATION       csqIpPrecToDscpDscp
    ACCESS          read-only
    DESCRIPTION
        "Unable to set this in this release."

    VARIATION       csqExpToDscpDscp
    ACCESS          read-only
    DESCRIPTION
        "Unable to set this in this release."

    VARIATION       csqDscpMappingCos
    ACCESS          read-only
    DESCRIPTION
        "Unable to set this in this release."

    VARIATION       csqDscpMappingExp
    ACCESS          read-only
    DESCRIPTION
        "Unable to set this in this release."

    VARIATION       csqDscpMappingNormalBurstDscp
    ACCESS          read-only
    DESCRIPTION
        "Unable to set this in this release."

    VARIATION       csqDscpMappingMaxBurstDscp
    ACCESS          read-only
    DESCRIPTION
        "Unable to set this in this release."

    VARIATION       csqCosMutationRowStatus
    ACCESS          read-only
    DESCRIPTION
        "Unable to set this in this release."

    VARIATION       csqCosMutationToCos
    ACCESS          read-only
    DESCRIPTION
        "Unable to set this in this release."

    VARIATION       csqDscpMutationRowStatus
    ACCESS          read-only
    DESCRIPTION
        "Unable to set this in this release."

    VARIATION       csqDscpMutationToDscp
    ACCESS          read-only
    DESCRIPTION
        "Unable to set this in this release."

    VARIATION       csqExpMutationRowStatus
    ACCESS          read-only
    DESCRIPTION
        "Unable to set this in this release."

    VARIATION       csqExpMutationToExp
    ACCESS          read-only
    DESCRIPTION
        "Unable to set this in this release."

    VARIATION       csqIfCosMutationMap
    ACCESS          read-only
    DESCRIPTION
        "Unable to set this in this release."

    VARIATION       csqIfDscpMutationMap
    ACCESS          read-only
    DESCRIPTION
        "Unable to set this in this release."

    VARIATION       csqIfExpMutationMap
    ACCESS          read-only
    DESCRIPTION
        "Unable to set this in this release."

    VARIATION       csqIfMutationRowStatus
    ACCESS          read-only
    DESCRIPTION
        "Unable to set this in this release."

    VARIATION       csqIfDefaultCos
    ACCESS          read-only
    DESCRIPTION
        "Unable to set this in this release."

    VARIATION       csqIfTrustState
    ACCESS          read-only
    DESCRIPTION
        "Unable to set this in this release."

    VARIATION       csqIfCosToQueueQueueNumber
    ACCESS          read-only
    DESCRIPTION
        "Unable to set this in this release."

    VARIATION       csqIfCosToQueueThresholdNumber
    ACCESS          read-only
    DESCRIPTION
        "Unable to set this in this release."

    VARIATION       csqIfDropConfigDropAlgorithm
    ACCESS          read-only
    DESCRIPTION
        "Unable to set this in this release."

    VARIATION       csqIfDropConfigDropThreshold
    ACCESS          read-only
    DESCRIPTION
        "Unable to set this in this release."

    VARIATION       csqIfDropConfigMinWredThreshold
    ACCESS          read-only
    DESCRIPTION
        "Unable to set this in this release."

    VARIATION       csqIfDropConfigMaxWredThreshold
    ACCESS          read-only
    DESCRIPTION
        "Unable to set this in this release."

    VARIATION       csqIfQueueWrrWeight
    ACCESS          read-only
    DESCRIPTION
        "Unable to set this in this release."

    VARIATION       csqIfQueueSizeWeight
    ACCESS          read-only
    DESCRIPTION
        "Unable to set this in this release."

    VARIATION       csqIfVlanBasedQosModeEnable
    ACCESS          read-only
    DESCRIPTION
        "Unable to set this in this release."

    VARIATION       csqIfConsistencyCheckEnable
    ACCESS          read-only
    DESCRIPTION
        "Unable to set this in this release."

    VARIATION       csqIfDscpToQueueQueueNumber
    ACCESS          read-only
    DESCRIPTION
        "Unable to set this in this release."

    VARIATION       csqIfDscpToQueueThresholdNumber
    ACCESS          read-only
    DESCRIPTION
        "Unable to set this in this release."

    ::= { ciscoSwitchQosCapability 4 }

END
