-- *****************************************************************
-- CISCO-VOICE-HDLC-DIAL-CONTROL-MIB.my: Voice HDLC Dial Control MIB 
--                                       file
--
-- April 1998, Steve Yang
--
-- Copyright (c) 1998 by cisco Systems, Inc.
-- All rights reserved.
-- *****************************************************************

CISCO-VOICE-HDLC-DIAL-CONTROL-MIB DEFINITIONS ::= BEGIN

IMPORTS
        MODULE-IDENTITY,
        OBJECT-TYPE
                FROM SNMPv2-SMI
        DisplayString
                FROM SNMPv2-TC
        MODULE-COMPLIANCE,
        OBJECT-GROUP
                FROM SNMPv2-CONF
        CvcGUid
                FROM  CISCO-VOICE-COMMON-DIAL-CONTROL-MIB
        cCallHistoryIndex
                FROM CISCO-DIAL-CONTROL-MIB
        ciscoExperiment
                FROM CISCO-SMI;
 
ciscoVoiceHdlcDialControlMIB MODULE-IDENTITY
        LAST-UPDATED    "9804140000Z"
        ORGANIZATION    "Cisco Systems, Inc."
        CONTACT-INFO
                "       Cisco Systems
                        Customer Service

                Postal: 170 W. Tasman Drive
                        San Jose, CA  95134
                        USA
 
                Tel: +1 800 553-NETS
 
                E-mail: cs-voice@cisco.com"
        DESCRIPTION
                "This MIB module enhances the IETF Dial Control MIB (RFC2128)
                 by providing HDLC management information over a data network.
                "
        ::= { ciscoExperiment 37 }

-- Voice HDLC Dial Control MIB objects definitions

cvhdlcdcMIBObjects OBJECT IDENTIFIER ::= { ciscoVoiceHdlcDialControlMIB 1 }

-- The Voice Dial Control MIB consists of the following group
-- [1] Voice HDLC Dial Control Call History Group (cvHdlcCallHistory)

cvHdlcCallHistory        OBJECT IDENTIFIER ::= { cvhdlcdcMIBObjects 1 }

--****************************************************************************
-- Voice over HDLC Dial Control Call History Group
--****************************************************************************

--
-- Voice over HDLC Call History Table
-- 

cvHdlcCallHistoryTable OBJECT-TYPE
        SYNTAX      SEQUENCE OF CvHdlcCallHistoryEntry
        MAX-ACCESS  not-accessible
        STATUS      current
        DESCRIPTION
            "This table is the HDLC extension to the call history table of
             IETF Dial Control MIB. It contains HDLC call leg information
             about specific voice over HDLC call.
            "
        ::= { cvHdlcCallHistory 1 }

cvHdlcCallHistoryEntry OBJECT-TYPE
        SYNTAX      CvHdlcCallHistoryEntry
        MAX-ACCESS  not-accessible
        STATUS      current
        DESCRIPTION
            "The information regarding a single HDLC call leg.
             An entry of this table is created when its associated call
             history entry in the IETF Dial Control MIB is created and the
             call history entry contains information for the call
             establishment to the peer on the data network backbone via a voice 
             over HDLC peer.
             The entry is deleted when its associated call history entry in
             the IETF Dial Control MIB is deleted.
            "
        INDEX       { cCallHistoryIndex }
        ::= { cvHdlcCallHistoryTable 1 }


CvHdlcCallHistoryEntry ::=
        SEQUENCE {
            cvHdlcCallHistoryConnectionId             CvcGUid,
            cvHdlcCallHistoryLowerIfName              DisplayString,
            cvHdlcCallHistorySessionTarget            DisplayString
        }

cvHdlcCallHistoryConnectionId OBJECT-TYPE
        SYNTAX      CvcGUid 
        MAX-ACCESS  read-only
        STATUS      current
        DESCRIPTION
            "The global call identifier for the tandem call."
        ::= { cvHdlcCallHistoryEntry 1 }

cvHdlcCallHistoryLowerIfName OBJECT-TYPE
    SYNTAX      DisplayString (SIZE (0..24))
    MAX-ACCESS  read-only 
    STATUS      current
    DESCRIPTION
            "The textual name of lower layer interface associated
             with this HDLC call."
    ::= { cvHdlcCallHistoryEntry 2 }

cvHdlcCallHistorySessionTarget OBJECT-TYPE
    SYNTAX      DisplayString 
    MAX-ACCESS  read-only
    STATUS      current
    DESCRIPTION
            "The object specifies the session target of the peer that
             is used for the voice over HDLC call. A null string indicates 
             that the value is unavailable."
    ::= { cvHdlcCallHistoryEntry 3 }

cvhdlcdcMIBConformance OBJECT IDENTIFIER ::=
                                { ciscoVoiceHdlcDialControlMIB 3 }
cvhdlcdcMIBCompliances OBJECT IDENTIFIER ::=
                                { cvhdlcdcMIBConformance 1 }
cvhdlcdcMIBGroups      OBJECT IDENTIFIER ::=
                                { cvhdlcdcMIBConformance 2 }

-- compliance statements

cvhdlcdcMIBCompliance MODULE-COMPLIANCE
        STATUS      current
        DESCRIPTION
            "The compliance statement for entities which
             implement the CISCO VOICE HDLC DIAL CONTROL MIB"
        MODULE      -- this module
        MANDATORY-GROUPS
            { cvHdlcCallHistoryGroup }
        ::= { cvhdlcdcMIBCompliances 1 }

-- units of conformance

cvHdlcCallHistoryGroup OBJECT-GROUP
        OBJECTS {
            cvHdlcCallHistoryConnectionId,
            cvHdlcCallHistoryLowerIfName,
            cvHdlcCallHistorySessionTarget            
        }
        STATUS      current
        DESCRIPTION
            "A collection of objects providing the HDLC Call
             capability."
        ::= { cvhdlcdcMIBGroups 1 }
END
