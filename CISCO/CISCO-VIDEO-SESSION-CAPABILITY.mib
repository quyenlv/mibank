-- *****************************************************************
-- CISCO-VIDEO-SESSION-CAPABILITY.my
--   
-- Copyright (c) 2010 by cisco Systems, Inc.
-- All rights reserved.
--   
-- *****************************************************************

CISCO-VIDEO-SESSION-CAPABILITY DEFINITIONS ::= BEGIN

IMPORTS
    MODULE-IDENTITY
        FROM SNMPv2-SMI
    AGENT-CAPABILITIES
        FROM SNMPv2-CONF
    ciscoAgentCapability
        FROM CISCO-SMI;


ciscoVideoSessionCapability MODULE-IDENTITY
    LAST-UPDATED    "201011110000Z"
    ORGANIZATION    "Cisco Systems, Inc."
    CONTACT-INFO
            "Cisco Systems
            Customer Service

            Postal: 170 W Tasman Drive
            San Jose, CA  95134
            USA

            Tel: +1 800 553-NETS

            E-mail: cs-<list>@cisco.com"
    DESCRIPTION
        "Agent capabilities for CISCO-VIDEO-SESSION-MIB."
    REVISION        "201011110000Z"
    DESCRIPTION
        "Initial version of this MIB module."
    ::= { ciscoAgentCapability 599 }



ciscoVideoSessionCapabilityV15R01 AGENT-CAPABILITIES
    PRODUCT-RELEASE "OS=IOS
                     OSVERSION=15.1
                     PLATFORM=c29xx,c3925,c3945,c3925E,c3945E
                     INTERFACE=None"
    STATUS          current
    DESCRIPTION
        "Cisco Video Session MIB capabilities."

    SUPPORTS        CISCO-VIDEO-SESSION-MIB
    INCLUDES        {
                        cVideoSessionHistoryGroup,
                        cVideoSessionActiveGroup
                    }
    ::= { ciscoVideoSessionCapability 1 }

END
