-- *****************************************************************
-- CISCO-INTERFACETOPN-EXT-CAPABILITY.my:
-- Cisco CISCO-INTERFACETOPN-EXT-MIB AGENT-CAPABILITIES
--   
-- July 2007, Liwei Wang
--   
-- Copyright (c) 2007 by Cisco Systems, Inc.
-- All rights reserved.
-- *****************************************************************

CISCO-INTERFACETOPN-EXT-CAPABILITY DEFINITIONS ::= BEGIN

IMPORTS
    MODULE-IDENTITY
        FROM SNMPv2-SMI
    AGENT-CAPABILITIES
        FROM SNMPv2-CONF
    ciscoAgentCapability
        FROM CISCO-SMI;


ciscoTopNExtCapability MODULE-IDENTITY
    LAST-UPDATED    "200707060000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of CISCO-INTERFACETOPN-EXT-MIB."
    REVISION        "200707060000Z"
    DESCRIPTION
        "Initial version of this MIB module."
    ::= { ciscoAgentCapability 543 }



ciscoTopNExtCapV12R0233SXHPCat6k AGENT-CAPABILITIES
    PRODUCT-RELEASE "Cisco IOS 12.2(33)SXH on Catalyst 6000/6500
                         series devices."
    STATUS          current
    DESCRIPTION
        "CISCO-INTERFACETOPN-EXT-MIB capabilities."

    SUPPORTS        CISCO-INTERFACETOPN-EXT-MIB
    INCLUDES        {
                        ciscoIfTopNExtCapsGroup,
                        ciscoIfTopNExtControlGroup,
                        ciscoIfTopNExtCtrlVlanGroup
                    }
    ::= { ciscoTopNExtCapability 1 }

END
