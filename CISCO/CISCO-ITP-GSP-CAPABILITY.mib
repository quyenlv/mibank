-- *****************************************************************
-- CISCO-ITP-GSP-CAPABILITY.my:  ITP Gateway Signalling Point Agent 
--                               capability MIB
--
-- May 2003, John Linton
--
-- Copyright (c) 2003, 2006 by cisco Systems, Inc.
-- All rights reserved.
-- *****************************************************************
CISCO-ITP-GSP-CAPABILITY DEFINITIONS ::= BEGIN

IMPORTS
        MODULE-IDENTITY
                FROM SNMPv2-SMI
                
        AGENT-CAPABILITIES
                FROM SNMPv2-CONF
                
        ciscoAgentCapability
                FROM CISCO-SMI; 
                

ciscoGspCapability MODULE-IDENTITY
                LAST-UPDATED    "200601600000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-ss7@cisco.com"
                DESCRIPTION
                   "Agent capabilities for the CISCO-ITP-GSP-MIB."

                REVISION        "200601600000Z"
                DESCRIPTION
                        "Added support for new isolation notifcation.
                         Added capability statement 
                         ciscoGspCapabilityV12R0225SW3."
                         
                REVISION        "200310150000Z"
                DESCRIPTION
                        "Deprecate cgspLinkSctpAssociation and 
                         replace with cgspLinkSctpAssociationId to 
                         allow larger range for association 
                         identifiers."
                        
                REVISION        "200307170000Z"
                DESCRIPTION
                        "Initial version of this MIB module."
        ::= { ciscoAgentCapability 306 }


ciscoGspCapabilityV12R0204MB10 AGENT-CAPABILITIES

    PRODUCT-RELEASE "Cisco IOS 12.2(4)MB10"
    STATUS           current
    DESCRIPTION     "IOS 12.2(4)MB1 Cisco CISCO-ITP-GSP-MIB.my User 
                     Agent MIB capabilities."

    SUPPORTS        CISCO-ITP-GSP-MIB
        INCLUDES    { 
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkGroup,
                        ciscoGspLinkTimerGroup,
                        ciscoGspLinkRemoteIpGroup,
                        ciscoGspLinkUtilGroup,
                        ciscoGspNotificationsEnableGroup,
                        ciscoGspNotificationsGroup
                    }  
    
--  cgspProfileTable
    VARIATION    cgspProfileVariant
    ACCESS       not-implemented
    DESCRIPTION "Not implemented."
    
    VARIATION    cgspProfileMtp2BundleTimer
    ACCESS       not-implemented
    DESCRIPTION "Not implemented."
    
    VARIATION    cgspProfileMtp2SendQueueDepth 
    ACCESS       not-implemented
    DESCRIPTION "Not implemented."
    
    VARIATION    cgspProfileRowStatus 
    ACCESS       not-implemented
    DESCRIPTION "Not implemented."
    
    
--  cgspProfileTimerTable  
    VARIATION    cgspProfileTimerValue 
    ACCESS       not-implemented
    DESCRIPTION "Not implemented."
    
    VARIATION    cgspProfileTimerRowStatus
    ACCESS       not-implemented
    DESCRIPTION "Not implemented."

--  cgspLinksetTable
    VARIATION    cgspLinksetActPriority
    ACCESS       not-implemented
    DESCRIPTION "Not implemented."
    ::= { ciscoGspCapability 1 }

ciscoGspCapabilityV12R0219SW AGENT-CAPABILITIES

    PRODUCT-RELEASE "Cisco IOS 12.2(19)SW"
    STATUS           current
    DESCRIPTION     "IOS 12.2(19)SW Cisco CISCO-ITP-GSP-MIB.my User 
                     Agent MIB capabilities."

    SUPPORTS        CISCO-ITP-GSP-MIB
        INCLUDES    { 
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkGroupRev1,
                        ciscoGspLinkTimerGroup,
                        ciscoGspLinkRemoteIpGroup,
                        ciscoGspLinkUtilGroup,
                        ciscoGspNotificationsEnableGroup,
                        ciscoGspNotificationsGroup
                    }  
    
--  cgspProfileTable
    VARIATION    cgspProfileVariant
    ACCESS       not-implemented
    DESCRIPTION "Not implemented."
    
    VARIATION    cgspProfileMtp2BundleTimer
    ACCESS       not-implemented
    DESCRIPTION "Not implemented."
    
    VARIATION    cgspProfileMtp2SendQueueDepth 
    ACCESS       not-implemented
    DESCRIPTION "Not implemented."
    
    VARIATION    cgspProfileRowStatus 
    ACCESS       not-implemented
    DESCRIPTION "Not implemented."
    
    
--  cgspProfileTimerTable  
    VARIATION    cgspProfileTimerValue 
    ACCESS       not-implemented
    DESCRIPTION "Not implemented."
    
    VARIATION    cgspProfileTimerRowStatus
    ACCESS       not-implemented
    DESCRIPTION "Not implemented."

--  cgspLinksetTable
    VARIATION    cgspLinksetActPriority
    ACCESS       not-implemented
    DESCRIPTION "Not implemented."
    ::= { ciscoGspCapability 2 }
    
ciscoGspCapabilityV12R0225SW3 AGENT-CAPABILITIES

    PRODUCT-RELEASE "Cisco IOS 12.2(25)SW3"
    STATUS           current
    DESCRIPTION     "IOS 12.2(25)SW3 Cisco CISCO-ITP-GSP-MIB.my User 
                     Agent MIB capabilities."

    SUPPORTS        CISCO-ITP-GSP-MIB
        INCLUDES    { 
                        ciscoGspScalarsGroup,
                        ciscoGspProfileGroup,
                        ciscoGspInstanceGroup,
                        ciscoGspInstTimerGroup,
                        ciscoGspPointCodeGroup,
                        ciscoGspLinksetGroup,
                        ciscoGspLinksetTimerGroup,
                        ciscoGspLinkGroupRev1,
                        ciscoGspLinkTimerGroup,
                        ciscoGspLinkRemoteIpGroup,
                        ciscoGspLinkUtilGroup,
                        ciscoGspNotificationsEnableGroup,
                        ciscoGspNotificationsGroup,
                        ciscoGspNotificationsEnableGroupSup1,
                        ciscoGspNotificationsGroupSup1
                    }  
    
--  cgspProfileTable
    VARIATION    cgspProfileVariant
    ACCESS       not-implemented
    DESCRIPTION "Not implemented."
    
    VARIATION    cgspProfileMtp2BundleTimer
    ACCESS       not-implemented
    DESCRIPTION "Not implemented."
    
    VARIATION    cgspProfileMtp2SendQueueDepth 
    ACCESS       not-implemented
    DESCRIPTION "Not implemented."
    
    VARIATION    cgspProfileRowStatus 
    ACCESS       not-implemented
    DESCRIPTION "Not implemented."
    
    
--  cgspProfileTimerTable  
    VARIATION    cgspProfileTimerValue 
    ACCESS       not-implemented
    DESCRIPTION "Not implemented."
    
    VARIATION    cgspProfileTimerRowStatus
    ACCESS       not-implemented
    DESCRIPTION "Not implemented."

--  cgspLinksetTable
    VARIATION    cgspLinksetActPriority
    ACCESS       not-implemented
    DESCRIPTION "Not implemented."
    ::= { ciscoGspCapability 3 }
END
