-- *****************************************************************
-- CISCO-COPS-CLIENT-CAPABILITY.my:
-- Cisco CISCO-COPS-CLIENT-MIB AGENT-CAPABILITIES
--
-- March 2004, Dipesh Gorashia
--
-- Copyright (c) 2004 by Cisco Systems, Inc.
-- All rights reserved.
-- *****************************************************************

CISCO-COPS-CLIENT-CAPABILITY DEFINITIONS ::= BEGIN

IMPORTS
        MODULE-IDENTITY
                FROM SNMPv2-SMI
        AGENT-CAPABILITIES
                FROM SNMPv2-CONF
        ciscoAgentCapability
                FROM CISCO-SMI;

ciscoCopsClientCapability MODULE-IDENTITY
        LAST-UPDATED    "200403300000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                CISCO-COPS-CLIENT-MIB."

        REVISION        "200403300000Z"
        DESCRIPTION
                "Initial version of this MIB module."
        ::= { ciscoAgentCapability 313 }

ccopsClientCapCatOSV53R2Cat6k AGENT-CAPABILITIES
    PRODUCT-RELEASE      "Cisco CatOS 5.3(2)."
    STATUS               current
    DESCRIPTION          "CISCO-COPS-CLIENT-MIB capabilities."

    SUPPORTS             CISCO-COPS-CLIENT-MIB
        INCLUDES         { ccopsGlobalGroup }

    ::= { ciscoCopsClientCapability 1 }

ccopsClientCapCatOSV61R1Cat6k AGENT-CAPABILITIES
    PRODUCT-RELEASE      "Cisco CatOS 6.1(1)."
    STATUS               current
    DESCRIPTION          "CISCO-COPS-CLIENT-MIB capabilities."

    SUPPORTS             CISCO-COPS-CLIENT-MIB
        INCLUDES         { ccopsGlobalGroupRev2, ccopsRoleGroup }

    ::= { ciscoCopsClientCapability 2 }

END
