-- *********************************************************************
-- CISCO-SYSTEM-EXT-MIB.my: System Extension MIB
--   
-- October 2002, Vinay Gaonkar
-- Copyright (c) 2002, 2003, 2005-2007 by cisco Systems Inc.
-- All rights reserved.
--   
-- ********************************************************************

CISCO-SYSTEM-EXT-MIB DEFINITIONS ::= BEGIN

IMPORTS
    MODULE-IDENTITY,
    OBJECT-TYPE,
    NOTIFICATION-TYPE,
    Unsigned32,
    Gauge32
        FROM SNMPv2-SMI
    MODULE-COMPLIANCE,
    OBJECT-GROUP,
    NOTIFICATION-GROUP
        FROM SNMPv2-CONF
    TEXTUAL-CONVENTION,
    TruthValue,
    DateAndTime
        FROM SNMPv2-TC
    SnmpAdminString
        FROM SNMP-FRAMEWORK-MIB
    InetAddressType,
    InetAddress
        FROM INET-ADDRESS-MIB
    sysName
        FROM SNMPv2-MIB
    EntPhysicalIndexOrZero,
    TimeIntervalSec
        FROM CISCO-TC
    ciscoMgmt
        FROM CISCO-SMI;


ciscoSystemExtMIB MODULE-IDENTITY
    LAST-UPDATED    "200708060000Z"
    ORGANIZATION    "Cisco Systems Inc."
    CONTACT-INFO
            "Cisco Systems
            Customer Service
            Postal: 170 W Tasman Drive
            San Jose, CA  95134
            USA
            Tel: +1 800 553 -NETS
            E-mail: cs-san@cisco.com"
    DESCRIPTION
        "MIB module for monitoring High Availability, SNMP SET
        errors and bandwidths.  This mib module also provides the
        information on core files that are generated in the
        system.
        GLOSSARY
        FIPS Federal Information Processing Standards Publication."
    REVISION        "200708060000Z"
    DESCRIPTION
        "-Added a scalar object 'cseSysUpTime'
        -Added an Object Group ciscoSystemExtInfoGroupRev3 and
         a MODULE-COMPLIANCE ciscoSystemExtMIBComplianceRev8
         to include the new object."
    REVISION        "200611290000Z"
    DESCRIPTION
        "Added ciscoSystemExtInfoFIPSGroup.
        Added a new object cseSysFIPSModeActivation."
    REVISION        "200609250000Z"
    DESCRIPTION
        "-Added cseSwCoresFileName in cseSwCoresTable.
        -Added new notification cseFailSwCoreNotifyExtended.
        -Added new group ciscoSystemExtSwFailureGroup3.
        -Added new group ciscoSystemExtNotificationGroupSup2.
        -Added compliance ciscoSystemExtMIBComplianceRev6 to
         replace ciscoSystemExtMIBComplianceRev5.
        -Added new group ciscoSystemExtSwFailureControlGroup.
        -Added new ciscoSwFailureNotifEnable object."
    REVISION        "200511090000Z"
    DESCRIPTION
        "Added a new group ciscoSystemExtInfoTelnetGroup.
        Added a new object cseSysTelnetServiceActivation."
    REVISION        "200506140000Z"
    DESCRIPTION
        "Updated CseHaRestartReason
        Added a new table cseSwCoresTable. 
        Added notifications - cseFailSwCoreNotify
                            - cseShutDownNotify
        Added a new group ciscoSystemExtSwFailureGroup2.
        Added a new group ciscoSystemExtNotificationGroup1.

        Added a new object cseSysConsolePortStatus. 
        Added a new group ciscoSystemExtInfoGroupRev2.
        Added a new compliance group 
                ciscoSystemExtMIBComplianceRev4."
    REVISION        "200404190000Z"
    DESCRIPTION
        "Added a new object cseSwCorePath."
    REVISION        "200305020000Z"
    DESCRIPTION
        "Added a new object cseWriteErase.
        Added a new group ciscoSystemExtInfoGroupOptional.
        A new compliance ciscoSystemExtMIBComplianceRev2 
        added to replace ciscoSystemExtMIBComplianceRev1."
    REVISION        "200303020000Z"
    DESCRIPTION
        "Added cseSysAutoSync and cseSysAutoSyncState."
    REVISION        "200211190000Z"
    DESCRIPTION
        "Added cseSysConfLastChange."
    REVISION        "200210040000Z"
    DESCRIPTION
        "Initial version of this MIB module."
    ::= { ciscoMgmt 305 }


ciscoSystemExtMIBNotifsPrefix  OBJECT IDENTIFIER
    ::= { ciscoSystemExtMIB 0 }

ciscoSystemExtMIBObjects  OBJECT IDENTIFIER
    ::= { ciscoSystemExtMIB 1 }

ciscoSystemExtMIBConformance  OBJECT IDENTIFIER
    ::= { ciscoSystemExtMIB 2 }

ciscoSysInfoGroup  OBJECT IDENTIFIER
    ::= { ciscoSystemExtMIBObjects 1 }

ciscoSysErrorGroup  OBJECT IDENTIFIER
    ::= { ciscoSystemExtMIBObjects 2 }

ciscoHaGroup  OBJECT IDENTIFIER
    ::= { ciscoSystemExtMIBObjects 3 }

ciscoSwFailureGroup  OBJECT IDENTIFIER
    ::= { ciscoSystemExtMIBObjects 4 }

ciscoSwFailureNotifControl  OBJECT IDENTIFIER
    ::= { ciscoSystemExtMIBObjects 5 }


-- Textual Conventions

CseHaRestartReason ::= TEXTUAL-CONVENTION
    STATUS          current
    DESCRIPTION
        "Reason codes for the restart of a service.
        unknown (1)           - ungraceful exit
        ungracefulExit (2)    - ungraceful exit
        otherSignal (3)       - service got some other signal
        sigterm (4)           - received SIGTERM
        softwareUpgrade (5)   - software upgrade
        configUpdate (6)      - config update
        configRemove (7)      - config removal
        shutdown (8)          - manually shutdown
        aborted (9)           - aborted
        heartbeatFailure (10) - heartbeat failure
        userTerminate (11)    - user termination
        gracefulExit (12)     - graceful exit
        failureNoCallhome (13)- service exited but it 
                                does not want a callhome
                                message to be generated 
        serviceTimeout (14)   - service timeout"
    SYNTAX          INTEGER  {
                        unknown(1),
                        ungracefulExit(2),
                        otherSignal(3),
                        sigterm(4),
                        softwareUpgrade(5),
                        configUpdate(6),
                        configRemove(7),
                        shutdown(8),
                        aborted(9),
                        heartbeatFailure(10),
                        userTerminate(11),
                        gracefulExit(12),
                        noCallHomeFailure(13),
                        serviceTimeout(14)
                    }

-- System Information Group

cseSysCPUUtilization OBJECT-TYPE
    SYNTAX          Gauge32 (0..100 )
    UNITS           "%"
    MAX-ACCESS      read-only
    STATUS          current
    DESCRIPTION
        "The average utilization of CPU on the active
        supervisor." 
    ::= { ciscoSysInfoGroup 1 }

-- Memory utilization

cseSysMemoryUtilization OBJECT-TYPE
    SYNTAX          Gauge32 (0..100 )
    UNITS           "%"
    MAX-ACCESS      read-only
    STATUS          current
    DESCRIPTION
        "The average utilization of memory on the active
        supervisor." 
    ::= { ciscoSysInfoGroup 2 }

cseSysConfLastChange OBJECT-TYPE
    SYNTAX          DateAndTime
    MAX-ACCESS      read-only
    STATUS          current
    DESCRIPTION
        "The local date and time when the
        configuration was last changed. This object will 
        be set to zero on power cycle or on reboot of 
        the system. Also, if the clock is changed on 
        local system it is set to zero." 
    ::= { ciscoSysInfoGroup 3 }

cseSysAutoSync OBJECT-TYPE
    SYNTAX          INTEGER  {
                        sync(1),
                        noSync(2)
                    }
    MAX-ACCESS      read-write
    STATUS          current
    DESCRIPTION
        "The state of the auto synchronization of images
        between the active and standby supervisor.
        Setting the value to sync when the existing value
        is sync, has no effect on the operation."
    DEFVAL          { noSync } 
    ::= { ciscoSysInfoGroup 4 }

cseSysAutoSyncState OBJECT-TYPE
    SYNTAX          INTEGER  {
                        inProgress(1),
                        succeeded(2),
                        failed(3),
                        notStarted(4)
                    }
    MAX-ACCESS      read-only
    STATUS          current
    DESCRIPTION
        "The status of the current auto synchronization
        process, or if no such process is in progress,  
        then the state of the most recent one.  The 
        value 'notStarted' indicates no auto synchronization 
        process has occurred recently." 
    ::= { ciscoSysInfoGroup 5 }

cseWriteErase OBJECT-TYPE
    SYNTAX          INTEGER  {
                        noOp(1),
                        eraseAll(2)
                    }
    MAX-ACCESS      read-write
    STATUS          current
    DESCRIPTION
        "This object is used to initiate a write erase on the
        device's saved configuration file(s) from which the 
        device loads its configuration when it restarts.

        If the value of this object is set to 'eraseAll', then
        all the saved configurations are removed.

        No action is taken when the this object is set to 
        'noOp'.
        When read, the value of this object is always 'noOp'." 
    ::= { ciscoSysInfoGroup 6 }

cseSysConsolePortStatus OBJECT-TYPE
    SYNTAX          INTEGER  {
                        connected(1),
                        notConnected(2)
                    }
    MAX-ACCESS      read-only
    STATUS          current
    DESCRIPTION
        "This object describes the status of the console
        port on this device.  

        The status 'connected' means that there is
        a cable attached to the console port.

        The status 'notConnected' means that there is
        no connection out of the console port." 
    ::= { ciscoSysInfoGroup 7 }

cseSysTelnetServiceActivation OBJECT-TYPE
    SYNTAX          TruthValue
    MAX-ACCESS      read-write
    STATUS          current
    DESCRIPTION
        "Enables or disables the Telnet service on the
        device. In other words, it enables or disables
        the telneting to the device."
    DEFVAL          { true } 
    ::= { ciscoSysInfoGroup 8 }

cseSysFIPSModeActivation OBJECT-TYPE
    SYNTAX          TruthValue
    MAX-ACCESS      read-write
    STATUS          current
    DESCRIPTION
        "The object to enable/disable FIPS mode  on the device.
        FIPS 140-2 is a set of security requirements for cryptographic
        modules and it details the U.S. Government requirements for
        cryptographic modules.
        A module will comprise both hardware and software, eg a
        datacenter  switching or routing module. The module is said to
        be in FIPS enabled mode when a request is recieved to enable the
        FIPS mode and a set of self-tests are successfully run in
        response to the request. If the self-tests fail, then an
        appropriate error is returned."
    REFERENCE
        "FIPS PUB 140-2 Security Requirements for Cryptographic  
               Modules"
    DEFVAL          { false } 
    ::= { ciscoSysInfoGroup 9 }

cseSysUpTime OBJECT-TYPE
    SYNTAX          TimeIntervalSec
    UNITS           "Seconds"
    MAX-ACCESS      read-only
    STATUS          current
    DESCRIPTION
        "The time (in seconds) since the entire system
        was last re-initialized as a result of reload. The 
        initialization being system loaded and running with a system
        image software on the first active supervisor (SUP). In High 
        Availibility (HA) capable system / System that provides 
        Supervisor module redundancy, this uptime indicates time 
        elapsed since the first active SUP was booted. This will not 
        change even if the active SUP goes down and stand-by takes
        over as active." 
    ::= { ciscoSysInfoGroup 10 }

cseSnmpErrorTable OBJECT-TYPE
    SYNTAX          SEQUENCE OF CseSnmpErrorEntry 
    MAX-ACCESS      not-accessible
    STATUS          current
    DESCRIPTION
        "A table containing information about the errors which have
        recently caused the generation of a SNMP Response PDU with a 
        non-zero value in its error-status field for SNMP Set Response
        PDU. 

        This table serves as an extension to the SNMP's error status 
        when a SNMP Set request fails. SNMP returns only a pre-defined
        set of standard error codes which does not convey the specific 
        cause for an error. Typically, there is an incumbent and 
        sizable burden on the configuration application to determine 
        if the configuration request failure is the result of a 
        resource issue, a security issue, or an application error 
        (like an object depending on some other objects). So from a 
        user perspective, it is important that a specific error be 
        made known.

        Ideally, when a 'badValue' error occurs for a given set 
        request, an application can query the command responder for 
        more details on the error. 

        This table provides a framework for the command responders to 
        provide more information on the SET errors.

        It is up to the implementation to create entries in this table 
        for either only certain SNMP errors or all of the SNMP errors.

        Note that only most recent incarnation of an entry is kept in 
        this table."
    ::= { ciscoSysErrorGroup 1 }

cseSnmpErrorEntry OBJECT-TYPE
    SYNTAX          CseSnmpErrorEntry
    MAX-ACCESS      not-accessible
    STATUS          current
    DESCRIPTION
        "An entry (conceptual row) in the  cseSnmpErrorTable, containing
        information about an error which has recently caused a SNMP 
        SetRequest to fail.  An entry is created by the agent 
        on the occurrence of an error, and is deleted approximately 5
        minutes later. The reasons for this are :
        - to prevent old entries clogging the table.
        - optimal utilization of the resources like memory."
    INDEX           {
                        cseSnmpErrorAddressType,
                        cseSnmpErrorAddress,
                        cseSnmpErrorRequestId
                    } 
    ::= { cseSnmpErrorTable 1 }

CseSnmpErrorEntry ::= SEQUENCE {
        cseSnmpErrorAddressType InetAddressType,
        cseSnmpErrorAddress     InetAddress,
        cseSnmpErrorRequestId   Unsigned32,
        cseSnmpErrorCode        Unsigned32,
        cseSnmpErrorDescription SnmpAdminString
}

cseSnmpErrorAddressType OBJECT-TYPE
    SYNTAX          InetAddressType
    MAX-ACCESS      not-accessible
    STATUS          current
    DESCRIPTION
        "The type of address from which the error-ed SetRequest
        originated." 
    ::= { cseSnmpErrorEntry 1 }

cseSnmpErrorAddress OBJECT-TYPE
    SYNTAX          InetAddress
    MAX-ACCESS      not-accessible
    STATUS          current
    DESCRIPTION
        "The address from which the error-ed SetRequest originated." 
    ::= { cseSnmpErrorEntry 2 }

cseSnmpErrorRequestId OBJECT-TYPE
    SYNTAX          Unsigned32
    MAX-ACCESS      not-accessible
    STATUS          current
    DESCRIPTION
        "The request-id of the error-ed SetRequest." 
    ::= { cseSnmpErrorEntry 3 }

cseSnmpErrorCode OBJECT-TYPE
    SYNTAX          Unsigned32
    MAX-ACCESS      read-only
    STATUS          current
    DESCRIPTION
        "The code for the Mib object specific error which
        caused a SetRequest to fail.
        This error code is platform-specific and for debugging
        purposes only. For information on this code, the 
        corresponding instance of cseSnmpErrorDescription must be 
        used. 
        This code is not the same as the value contained
        in the error-status field of SNMP Response PDU." 
    ::= { cseSnmpErrorEntry 4 }

cseSnmpErrorDescription OBJECT-TYPE
    SYNTAX          SnmpAdminString
    MAX-ACCESS      read-only
    STATUS          current
    DESCRIPTION
        "The error description for the error happened for the
        SetRequest." 
    ::= { cseSnmpErrorEntry 5 }
 


-- Notification informations

cseHaRestartReason OBJECT-TYPE
    SYNTAX          CseHaRestartReason
    MAX-ACCESS      accessible-for-notify
    STATUS          current
    DESCRIPTION
        "The reason for most recent restart of a service on the
        'active' supervisor." 
    ::= { ciscoHaGroup 2 }

cseHaRestartStateless OBJECT-TYPE
    SYNTAX          TruthValue
    MAX-ACCESS      accessible-for-notify
    STATUS          current
    DESCRIPTION
        "Tells if the most recent restart of a service on the
        'active' supervisor was 'stateless' or not.
         A 'stateless' restart of a service is where no runtime 
         information is preserved while restarting the service." 
    ::= { ciscoHaGroup 3 }

cseHaRestartService OBJECT-TYPE
    SYNTAX          SnmpAdminString (SIZE  (0..255))
    MAX-ACCESS      accessible-for-notify
    STATUS          current
    DESCRIPTION
        "Name of the service (or process) that was restarted on
        the 'active' supervisor." 
    ::= { ciscoHaGroup 4 }

cseHaShutDownReason OBJECT-TYPE
    SYNTAX          SnmpAdminString (SIZE  (0..255))
    MAX-ACCESS      accessible-for-notify
    STATUS          current
    DESCRIPTION
        "The description of the reason as to why the system
        is going to go down." 
    ::= { ciscoHaGroup 6 }

-- software failure group

cseSwCorePath OBJECT-TYPE
    SYNTAX          SnmpAdminString (SIZE  (0..255))
    MAX-ACCESS      read-only
    STATUS          current
    DESCRIPTION
        "Provides the path where the software cores are
        stored on the system. The management application can
        use this path to copy the cores from the system using
        CISCO-FLASH-MIB." 
    ::= { ciscoSwFailureGroup 1 }

cseSwCoresTable OBJECT-TYPE
    SYNTAX          SEQUENCE OF CseSwCoresEntry 
    MAX-ACCESS      not-accessible
    STATUS          current
    DESCRIPTION
        "A table containing information about the system cores that
        have been generated as an effect of some system failures."
    ::= { ciscoSwFailureGroup 2 }

cseSwCoresEntry OBJECT-TYPE
    SYNTAX          CseSwCoresEntry
    MAX-ACCESS      not-accessible
    STATUS          current
    DESCRIPTION
        "An entry (conceptual row) in the  cseSwCoresTable, containing
        information about cores that have been generated."
    INDEX           {
                        cseSwCoresModule,
                        cseSwCoresProcName,
                        cseSwCoresInstance
                    } 
    ::= { cseSwCoresTable 1 }

CseSwCoresEntry ::= SEQUENCE {
        cseSwCoresModule      EntPhysicalIndexOrZero,
        cseSwCoresProcName    SnmpAdminString,
        cseSwCoresInstance    Unsigned32,
        cseSwCoresPID         Unsigned32,
        cseSwCoresTimeCreated DateAndTime,
        cseSwCoresSlotNum     Unsigned32,
        cseSwCoresFileName    SnmpAdminString
}

cseSwCoresModule OBJECT-TYPE
    SYNTAX          EntPhysicalIndexOrZero
    MAX-ACCESS      not-accessible
    STATUS          current
    DESCRIPTION
        "The physical module on which the process crashed." 
    ::= { cseSwCoresEntry 1 }

cseSwCoresProcName OBJECT-TYPE
    SYNTAX          SnmpAdminString (SIZE  (1..64))
    MAX-ACCESS      not-accessible
    STATUS          current
    DESCRIPTION
        "The name of the process that crashed and generated core." 
    ::= { cseSwCoresEntry 2 }

cseSwCoresInstance OBJECT-TYPE
    SYNTAX          Unsigned32
    MAX-ACCESS      not-accessible
    STATUS          current
    DESCRIPTION
        "The instance of the core for a process identified by
        cseSwCoresProcName and on the module identified by
        cseSwCoresModule. 

        To uniquely identify a core, the module number and 
        process name are not sufficient as there could be 
        multiple cores for the same module number and process
        name." 
    ::= { cseSwCoresEntry 3 }

cseSwCoresPID OBJECT-TYPE
    SYNTAX          Unsigned32
    MAX-ACCESS      read-only
    STATUS          current
    DESCRIPTION
        "The process identifier of the process that dumped the
        core." 
    ::= { cseSwCoresEntry 4 }

cseSwCoresTimeCreated OBJECT-TYPE
    SYNTAX          DateAndTime
    MAX-ACCESS      read-only
    STATUS          current
    DESCRIPTION
        "The time at which the core was created." 
    ::= { cseSwCoresEntry 5 }

cseSwCoresSlotNum OBJECT-TYPE
    SYNTAX          Unsigned32
    MAX-ACCESS      read-only
    STATUS          current
    DESCRIPTION
        "The slot number corresponding to the cseSwCoresModule
        in this chassis." 
    ::= { cseSwCoresEntry 6 }

cseSwCoresFileName OBJECT-TYPE
    SYNTAX          SnmpAdminString
    MAX-ACCESS      read-only
    STATUS          current
    DESCRIPTION
        "This object contains the core file-name(including the
        path, relative to the value in the cseSwCorePath object). 
        If the cseSwCorePath contains zero length octet string,
        then this object will contain the filename with absolute
        path.  If this object contains zero length octet string,
        then the core file is available in path identified in
        cseSwCorePath." 
    ::= { cseSwCoresEntry 7 }
 


-- Notification Control Group

ciscoSwFailureNotifEnable OBJECT-TYPE
    SYNTAX          TruthValue
    MAX-ACCESS      read-write
    STATUS          current
    DESCRIPTION
        "This object is used for administratively
        enabling/disabling the cseFailSwCoreNotify or
        cseFailSwCoreNotifyExtended notifications."
    DEFVAL          { false } 
    ::= { ciscoSwFailureNotifControl 1 }
-- Notifications
--   

-- High Availability Notifications

cseHaNotification  OBJECT IDENTIFIER
    ::= { ciscoHaGroup 5 }

cseHaNotificationPrefix  OBJECT IDENTIFIER
    ::= { cseHaNotification 0 }


cseHaRestartNotify NOTIFICATION-TYPE
    OBJECTS         {
                        cseHaRestartReason,
                        cseHaRestartService,
                        cseHaRestartStateless
                    }
    STATUS          current
    DESCRIPTION
        "A service restart notification is generated
        whenever a service (or a process) on the 'active' 
        supervisor is restarted."
   ::= { cseHaNotificationPrefix 1 }

cseShutDownNotify NOTIFICATION-TYPE
    OBJECTS         { cseHaShutDownReason }
    STATUS          current
    DESCRIPTION
        "A system shutdown notification is generated
        whenever a system is going to shut down. The
        cseHaShutDownReason, describes the reason as to
        why the system is going to go down."
   ::= { cseHaNotificationPrefix 2 }
-- Failure Group Notifications

cseFailNotification  OBJECT IDENTIFIER
    ::= { ciscoSwFailureGroup 3 }

cseFailNotificationPrefix  OBJECT IDENTIFIER
    ::= { cseFailNotification 0 }


cseFailSwCoreNotify NOTIFICATION-TYPE
    STATUS          current
    DESCRIPTION
        "A notification is generated whenever a software
        crash occurs and a core file is generated."
   ::= { cseFailNotificationPrefix 1 }

cseFailSwCoreNotifyExtended NOTIFICATION-TYPE
    OBJECTS         {
                        sysName,
                        cseSwCoresFileName,
                        cseSwCorePath,
                        cseSwCoresPID
                    }
    STATUS          current
    DESCRIPTION
        "A notification is generated whenever a software
        crash occurs and a core file is generated."
   ::= { cseFailNotificationPrefix 2 }
-- Conformance

ciscoSystemExtMIBCompliances  OBJECT IDENTIFIER
    ::= { ciscoSystemExtMIBConformance 1 }

ciscoSystemExtMIBGroups  OBJECT IDENTIFIER
    ::= { ciscoSystemExtMIBConformance 2 }


ciscoSystemExtMIBCompliance MODULE-COMPLIANCE
    STATUS          deprecated
    DESCRIPTION
        "The compliance statement for entities which
        implement the CISCO-SYTEM-EXT-MIB."
    MODULE          -- this module
    MANDATORY-GROUPS {
                        ciscoSystemExtInfoGroup,
                        ciscoSystemExtErrorGroup,
                        ciscoSystemExtHaGroup,
                        ciscoSystemExtNotificationGroup
                    }
    ::= { ciscoSystemExtMIBCompliances 1 }

ciscoSystemExtMIBComplianceRev1 MODULE-COMPLIANCE
    STATUS          deprecated
    DESCRIPTION
        "The compliance statement for entities which
        implement the CISCO-SYTEM-EXT-MIB."
    MODULE          -- this module
    MANDATORY-GROUPS {
                        ciscoSystemExtInfoGroupRev1,
                        ciscoSystemExtErrorGroup,
                        ciscoSystemExtHaGroup,
                        ciscoSystemExtNotificationGroup
                    }
    ::= { ciscoSystemExtMIBCompliances 2 }

ciscoSystemExtMIBComplianceRev2 MODULE-COMPLIANCE
    STATUS          deprecated
    DESCRIPTION
        "The compliance statement for entities which
        implement the CISCO-SYTEM-EXT-MIB."
    MODULE          -- this module
    MANDATORY-GROUPS {
                        ciscoSystemExtInfoGroupRev1,
                        ciscoSystemExtErrorGroup,
                        ciscoSystemExtHaGroup,
                        ciscoSystemExtNotificationGroup
                    }

    GROUP           ciscoSystemExtInfoGroupOptional
    DESCRIPTION
        "Implementation of this group is optional."
    ::= { ciscoSystemExtMIBCompliances 3 }

ciscoSystemExtMIBComplianceRev3 MODULE-COMPLIANCE
    STATUS          deprecated
    DESCRIPTION
        "The compliance statement for entities which
        implement the CISCO-SYTEM-EXT-MIB."
    MODULE          -- this module
    MANDATORY-GROUPS {
                        ciscoSystemExtInfoGroupRev1,
                        ciscoSystemExtErrorGroup,
                        ciscoSystemExtHaGroup,
                        ciscoSystemExtNotificationGroup
                    }

    GROUP           ciscoSystemExtInfoGroupOptional
    DESCRIPTION
        "Implementation of this group is optional."

    GROUP           ciscoSystemExtSwFailureGroup
    DESCRIPTION
        "Implementation of this group is optional."
    ::= { ciscoSystemExtMIBCompliances 4 }

ciscoSystemExtMIBComplianceRev4 MODULE-COMPLIANCE
    STATUS          deprecated
    DESCRIPTION
        "The compliance statement for entities which
        implement the CISCO-SYTEM-EXT-MIB."
    MODULE          -- this module
    MANDATORY-GROUPS {
                        ciscoSystemExtInfoGroupRev1,
                        ciscoSystemExtInfoGroupRev2,
                        ciscoSystemExtErrorGroup,
                        ciscoSystemExtHaGroup,
                        ciscoSystemExtNotificationGroup,
                        ciscoSystemExtNotificationGroupSup1,
                        ciscoSystemExtHaGroupRev1
                    }

    GROUP           ciscoSystemExtInfoGroupOptional
    DESCRIPTION
        "Implementation of this group is optional."

    GROUP           ciscoSystemExtSwFailureGroup
    DESCRIPTION
        "Implementation of this group is optional."
    ::= { ciscoSystemExtMIBCompliances 5 }

ciscoSystemExtMIBComplianceRev5 MODULE-COMPLIANCE
    STATUS          deprecated
    DESCRIPTION
        "The compliance statement for entities which
        implement the CISCO-SYTEM-EXT-MIB."
    MODULE          -- this module
    MANDATORY-GROUPS {
                        ciscoSystemExtInfoGroupRev1,
                        ciscoSystemExtInfoGroupRev2,
                        ciscoSystemExtErrorGroup,
                        ciscoSystemExtHaGroup,
                        ciscoSystemExtNotificationGroup,
                        ciscoSystemExtNotificationGroupSup1,
                        ciscoSystemExtHaGroupRev1
                    }

    GROUP           ciscoSystemExtInfoGroupOptional
    DESCRIPTION
        "Implementation of this group is optional."

    GROUP           ciscoSystemExtSwFailureGroup
    DESCRIPTION
        "Implementation of this group is optional."

    GROUP           ciscoSystemExtSwFailureGroup2
    DESCRIPTION
        "Implementation of this group is optional."

    GROUP           ciscoSystemExtInfoTelnetGroup
    DESCRIPTION
        "Implementation of this group is mandatory if the
        support of telnet device can be enabled/disabled 
        by the system."
    ::= { ciscoSystemExtMIBCompliances 6 }

ciscoSystemExtMIBComplianceRev6 MODULE-COMPLIANCE
    STATUS          deprecated
    DESCRIPTION
        "The compliance statement for entities which implement the
        CISCO-SYTEM-EXT-MIB."
    MODULE          -- this module
    MANDATORY-GROUPS {
                        ciscoSystemExtInfoGroupRev1,
                        ciscoSystemExtInfoGroupRev2,
                        ciscoSystemExtErrorGroup,
                        ciscoSystemExtHaGroup,
                        ciscoSystemExtNotificationGroup,
                        ciscoSystemExtHaGroupRev1
                    }

    GROUP           ciscoSystemExtInfoGroupOptional
    DESCRIPTION
        "Implementation of this group is optional."

    GROUP           ciscoSystemExtSwFailureGroup
    DESCRIPTION
        "Implementation of this group is optional."

    GROUP           ciscoSystemExtSwFailureGroup2
    DESCRIPTION
        "Implementation of this group is optional."

    GROUP           ciscoSystemExtInfoTelnetGroup
    DESCRIPTION
        "Implementation of this group is optional."

    GROUP           ciscoSystemExtSwFailureGroup3
    DESCRIPTION
        "This group is mandatory if cseFailSwCoreNotifyExtended
        notification is implemented."

    GROUP           ciscoSystemExtNotificationGroupSup2
    DESCRIPTION
        "Implementation of this group is optional. Implementing one
        of the two notifications cseFailSwCoreNotify or
        cseFailSwCoreNotifyExtended will suffice."

    GROUP           ciscoSystemExtNotificationGroupSup1
    DESCRIPTION
        "The implementation of cseShutDownNotify is mandatory.
        However the implementation of cseFailSwCoreNotify is
        optional. Implementing one of the two notifications
        cseFailSwCoreNotify or cseFailSwCoreNotifyExtended will
        suffice."

    GROUP           ciscoSystemExtSwFailureControlGroup
    DESCRIPTION
        "Implementation of this group is optional.  Implementing of
        this group is mandatory only when either
        cseFailSwCoreNotify or cseFailSwCoreNotifyExtended
        notification is implemented."
    ::= { ciscoSystemExtMIBCompliances 7 }

ciscoSystemExtMIBComplianceRev7 MODULE-COMPLIANCE
    STATUS          deprecated
    DESCRIPTION
        "The compliance statement for entities which
        implement the CISCO-SYTEM-EXT-MIB."
    MODULE          -- this module
    MANDATORY-GROUPS {
                        ciscoSystemExtInfoGroupRev1,
                        ciscoSystemExtInfoGroupRev2,
                        ciscoSystemExtErrorGroup,
                        ciscoSystemExtHaGroup,
                        ciscoSystemExtNotificationGroup,
                        ciscoSystemExtNotificationGroupSup1,
                        ciscoSystemExtHaGroupRev1
                    }

    GROUP           ciscoSystemExtInfoGroupOptional
    DESCRIPTION
        "Implementation of this group is optional."

    GROUP           ciscoSystemExtSwFailureGroup
    DESCRIPTION
        "Implementation of this group is optional."

    GROUP           ciscoSystemExtSwFailureGroup2
    DESCRIPTION
        "Implementation of this group is optional."

    GROUP           ciscoSystemExtInfoTelnetGroup
    DESCRIPTION
        "Implementation of this group is optional."

    GROUP           ciscoSystemExtInfoFIPSGroup
    DESCRIPTION
        "Implementation of this group is optional."
    ::= { ciscoSystemExtMIBCompliances 8 }

ciscoSystemExtMIBComplianceRev8 MODULE-COMPLIANCE
    STATUS          current
    DESCRIPTION
        "The compliance statement for entities which
        implement the CISCO-SYTEM-EXT-MIB."
    MODULE          -- this module
    MANDATORY-GROUPS {
                        ciscoSystemExtInfoGroupRev3,
                        ciscoSystemExtInfoGroupRev2,
                        ciscoSystemExtErrorGroup,
                        ciscoSystemExtHaGroup,
                        ciscoSystemExtNotificationGroup,
                        ciscoSystemExtNotificationGroupSup1,
                        ciscoSystemExtHaGroupRev1
                    }

    GROUP           ciscoSystemExtInfoGroupOptional
    DESCRIPTION
        "Implementation of this group is optional."

    GROUP           ciscoSystemExtSwFailureGroup
    DESCRIPTION
        "Implementation of this group is optional."

    GROUP           ciscoSystemExtSwFailureGroup2
    DESCRIPTION
        "Implementation of this group is optional."

    GROUP           ciscoSystemExtInfoTelnetGroup
    DESCRIPTION
        "Implementation of this group is optional."

    GROUP           ciscoSystemExtInfoFIPSGroup
    DESCRIPTION
        "Implementation of this group is optional."
    ::= { ciscoSystemExtMIBCompliances 9 }

-- Units of Conformance

ciscoSystemExtInfoGroup OBJECT-GROUP
    OBJECTS         {
                        cseSysCPUUtilization,
                        cseSysMemoryUtilization,
                        cseSysConfLastChange
                    }
    STATUS          deprecated
    DESCRIPTION
        "A collection of objects for system information."
    ::= { ciscoSystemExtMIBGroups 1 }

ciscoSystemExtErrorGroup OBJECT-GROUP
    OBJECTS         {
                        cseSnmpErrorCode,
                        cseSnmpErrorDescription
                    }
    STATUS          current
    DESCRIPTION
        "A collection of objects for logging SNMP set error."
    ::= { ciscoSystemExtMIBGroups 2 }

ciscoSystemExtHaGroup OBJECT-GROUP
    OBJECTS         {
                        cseHaRestartReason,
                        cseHaRestartService,
                        cseHaRestartStateless
                    }
    STATUS          current
    DESCRIPTION
        "A collection of objects for High Availability."
    ::= { ciscoSystemExtMIBGroups 3 }

ciscoSystemExtNotificationGroup NOTIFICATION-GROUP
   NOTIFICATIONS    { cseHaRestartNotify }
    STATUS          current
    DESCRIPTION
        "A collection of notifications for the
        High Availability."
    ::= { ciscoSystemExtMIBGroups 4 }

ciscoSystemExtInfoGroupRev1 OBJECT-GROUP
    OBJECTS         {
                        cseSysCPUUtilization,
                        cseSysMemoryUtilization,
                        cseSysConfLastChange,
                        cseSysAutoSync,
                        cseSysAutoSyncState
                    }
    STATUS          deprecated
    DESCRIPTION
        "A collection of objects for system information."
    ::= { ciscoSystemExtMIBGroups 5 }

ciscoSystemExtInfoGroupOptional OBJECT-GROUP
    OBJECTS         { cseWriteErase }
    STATUS          current
    DESCRIPTION
        "A collection of objects for system information
        which are optional."
    ::= { ciscoSystemExtMIBGroups 6 }

ciscoSystemExtSwFailureGroup OBJECT-GROUP
    OBJECTS         { cseSwCorePath }
    STATUS          current
    DESCRIPTION
        "A collection of objects for system software failure
        information which are optional."
    ::= { ciscoSystemExtMIBGroups 7 }

ciscoSystemExtInfoGroupRev2 OBJECT-GROUP
    OBJECTS         { cseSysConsolePortStatus }
    STATUS          current
    DESCRIPTION
        "A collection of objects for system information."
    ::= { ciscoSystemExtMIBGroups 8 }

ciscoSystemExtSwFailureGroup2 OBJECT-GROUP
    OBJECTS         {
                        cseSwCoresPID,
                        cseSwCoresTimeCreated,
                        cseSwCoresSlotNum
                    }
    STATUS          current
    DESCRIPTION
        "A collection of objects for system software failure
        information which are optional."
    ::= { ciscoSystemExtMIBGroups 9 }

ciscoSystemExtNotificationGroupSup1 NOTIFICATION-GROUP
   NOTIFICATIONS    {
                        cseShutDownNotify,
                        cseFailSwCoreNotify
                    }
    STATUS          current
    DESCRIPTION
        "A collection of notifications for the
        system MIB."
    ::= { ciscoSystemExtMIBGroups 10 }

ciscoSystemExtHaGroupRev1 OBJECT-GROUP
    OBJECTS         { cseHaShutDownReason }
    STATUS          current
    DESCRIPTION
        "A collection of objects for High Availability."
    ::= { ciscoSystemExtMIBGroups 11 }

ciscoSystemExtInfoTelnetGroup OBJECT-GROUP
    OBJECTS         { cseSysTelnetServiceActivation }
    STATUS          current
    DESCRIPTION
        "A collection of objects related to telnet support
        to the device."
    ::= { ciscoSystemExtMIBGroups 12 }

ciscoSystemExtNotificationGroupSup2 NOTIFICATION-GROUP
   NOTIFICATIONS    { cseFailSwCoreNotifyExtended }
    STATUS          current
    DESCRIPTION
        "A collection of notification related to core file
        creation."
    ::= { ciscoSystemExtMIBGroups 13 }

ciscoSystemExtSwFailureGroup3 OBJECT-GROUP
    OBJECTS         { cseSwCoresFileName }
    STATUS          current
    DESCRIPTION
        "A collection of objects related to the core file."
    ::= { ciscoSystemExtMIBGroups 14 }

ciscoSystemExtSwFailureControlGroup OBJECT-GROUP
    OBJECTS         { ciscoSwFailureNotifEnable }
    STATUS          current
    DESCRIPTION
        "This group of objects controls the sending of
        notifications defined in this MIB module."
    ::= { ciscoSystemExtMIBGroups 15 }

ciscoSystemExtInfoFIPSGroup OBJECT-GROUP
    OBJECTS         { cseSysFIPSModeActivation }
    STATUS          current
    DESCRIPTION
        "A collection of objects related to FIPS support
        to the device."
    ::= { ciscoSystemExtMIBGroups 16 }

ciscoSystemExtInfoGroupRev3 OBJECT-GROUP
    OBJECTS         {
                        cseSysCPUUtilization,
                        cseSysMemoryUtilization,
                        cseSysConfLastChange,
                        cseSysAutoSync,
                        cseSysAutoSyncState,
                        cseSysUpTime
                    }
    STATUS          current
    DESCRIPTION
        "A collection of objects for system information."
    ::= { ciscoSystemExtMIBGroups 17 }

END
