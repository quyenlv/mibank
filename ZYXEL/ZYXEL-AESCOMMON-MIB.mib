-- ZyXEL Communications Corporation
-- Private Enterprise MIB definition

-- $Log: zyxel-AESCommon.mib $
-- Revision 1.5  2005/06/08 08:04:08  jennyhsu
-- Changes for IES-2k/3k R3.02
-- Revision 1.4  2004/06/08 10:12:54  jenny
-- Add ADSL2 and ADSL2+ mode
-- Revision 1.3  2003/11/25 04:00:31  jennyhsu
-- add etsi mode
-- Revision 1.2  2002/11/12 07:48:38  jennyhsu
-- Revision 1.1  2002/11/12 07:40:54  jennyhsu
-- Initial revision


ZYXEL-AESCOMMON-MIB DEFINITIONS ::= BEGIN

	IMPORTS
		OBJECT-TYPE		FROM RFC-1212
		DisplayString, ifIndex 	FROM RFC1213-MIB
		Unsigned32		FROM SNMPv2-SMI
		aesSeriesCommon 	FROM ZYXEL-MIB;
		
        aesMaxNumOfProfiles OBJECT-TYPE
        SYNTAX  INTEGER
        ACCESS  read-only
        STATUS  mandatory
        DESCRIPTION
                      "The maximum number of ADSL profiles which the system supports."
        ::= { aesSeriesCommon 1 }

        aesLineConfTable OBJECT-TYPE
        SYNTAX	SEQUENCE OF AesLineConfEntry
        ACCESS  not-accessible
        STATUS  mandatory
        DESCRIPTION
                 	"This table includes common attributes describing the ADSL line."
        ::= { aesSeriesCommon 2 }

	aesLineConfEntry OBJECT-TYPE
        SYNTAX	AesLineConfEntry
        ACCESS	not-accessible
        STATUS	mandatory
        DESCRIPTION    	"An entry in aesLineConfTable."
        INDEX          	{ ifIndex }
        ::= { aesLineConfTable 1 }

        AesLineConfEntry ::=
           SEQUENCE {
        	aesLineConfAdslMode	INTEGER,
		aesLineConfEncap	INTEGER,
		aesLineConfVpi		INTEGER,
		aesLineConfVci		INTEGER,
		aesLineConfAnnexL	INTEGER,
		aesLineConfPmMode	INTEGER,
		aesLineConfRateMode	INTEGER
           }

        aesLineConfAdslMode OBJECT-TYPE
        SYNTAX  INTEGER {
			gDotLite(1),
			gDotDmt(2),
			t1Dot413(3),
			auto(4), 
			etsi(5),
			adsl2(6),
			adsl2Plus(7)
	}
        ACCESS  read-write
        STATUS  mandatory
        DESCRIPTION
                      	"The mode of the ADSL line."
        ::= { aesLineConfEntry 1 }

        aesLineConfEncap OBJECT-TYPE
        SYNTAX  INTEGER {
			llc(1),
			vc(2)
	}
        ACCESS  read-write
        STATUS  mandatory
        DESCRIPTION
                      	"The encapsulation of the ADSL line."
        ::= { aesLineConfEntry 2 }

        aesLineConfVpi OBJECT-TYPE
        SYNTAX  INTEGER
        ACCESS  read-write
        STATUS  mandatory
        DESCRIPTION
                      	"The VPI of the ADSL line."
        ::= { aesLineConfEntry 3 }

        aesLineConfVci OBJECT-TYPE
        SYNTAX  INTEGER
        ACCESS  read-write
        STATUS  mandatory
        DESCRIPTION
                      	"The VCI of the ADSL line."
        ::= { aesLineConfEntry 4 }

        aesLineConfAnnexL OBJECT-TYPE
        SYNTAX  INTEGER {
        		enableNarrowMode(1),
        		enableWideMode(2),
        		disable(3)
        	}
        ACCESS  read-write
        STATUS  mandatory
        DESCRIPTION
                      	"The annex L setting of the ADSL line."
        ::= { aesLineConfEntry 5 }			

        aesLineConfPmMode OBJECT-TYPE
        SYNTAX  INTEGER {
        		enableL2Mode(1),
        		enableL3Mode(2),
        		disable(3)
        	}
        ACCESS  read-write
        STATUS  mandatory
        DESCRIPTION
                      	"The power management mode of the ADSL line."
        ::= { aesLineConfEntry 6 }
        
        aesLineConfRateMode OBJECT-TYPE
        SYNTAX	INTEGER {
                 	fixed(1),		-- no rate adaptation
                 	adaptAtStartup(2),	-- perform rate adaptation
                                         	-- only at initialization
                 	adaptAtRuntime(3)	-- perform rate adaptation at
                                         	-- any time
             	}
        ACCESS  read-write
        STATUS	mandatory
        DESCRIPTION
                 	"Defines what form of transmit rate adaptation is
                 	configured on this modem.  See ADSL Forum TR-005 [3]
                 	for more information."
        ::= { aesLineConfEntry 7 }
                
         
-- ADSL Line Diagnostic

	aesLineDiagnostic	OBJECT IDENTIFIER ::= { aesSeriesCommon 3 }
	   
	aesAtucLineDiagLATN OBJECT-TYPE
	SYNTAX	INTEGER
	UNITS	"tenth dB"
	ACCESS	read-only
	STATUS	mandatory
	DESCRIPTION
		"Line Attenuation."
	::= { aesLineDiagnostic 1 }

	aesAtucLineDiagSATN OBJECT-TYPE
	SYNTAX	INTEGER
	UNITS	"tenth dB"
	ACCESS	read-only
	STATUS	mandatory
	DESCRIPTION
		"Signal Attenuation."
	::= { aesLineDiagnostic 2 }

	aesAtucLineDiagSNRM OBJECT-TYPE
	SYNTAX	INTEGER
	UNITS	"tenth dB"
	ACCESS	read-only
	STATUS	mandatory
	DESCRIPTION
		"Signal-to-Noise Ratio Margin."
	::= { aesLineDiagnostic 3 } 

	aesAtucLineDiagACTATP OBJECT-TYPE
	SYNTAX	INTEGER
	UNITS	"tenth dB"
	ACCESS	read-only
	STATUS	mandatory
	DESCRIPTION
		"Actual Aggregate Transmit Power."
	::= { aesLineDiagnostic 4 }
	
	aesAtucLineDiagATTNDR OBJECT-TYPE
	SYNTAX	Unsigned32
	ACCESS	read-only
	STATUS	mandatory
	DESCRIPTION
		"Attainable Net Data Rate, in bps."
	::= { aesLineDiagnostic 5 }

	aesAturLineDiagLATN OBJECT-TYPE
	SYNTAX	INTEGER
	UNITS	"tenth dB"
	ACCESS	read-only
	STATUS	mandatory
	DESCRIPTION
		"Line Attenuation."
	::= { aesLineDiagnostic 6 }

	aesAturLineDiagSATN OBJECT-TYPE
	SYNTAX	INTEGER
	UNITS	"tenth dB"
	ACCESS	read-only
	STATUS	mandatory
	DESCRIPTION
		"Signal Attenuation."
	::= { aesLineDiagnostic 7 }

	aesAturLineDiagSNRM OBJECT-TYPE
	SYNTAX	INTEGER
	UNITS	"tenth dB"
	ACCESS	read-only
	STATUS	mandatory
	DESCRIPTION
		"Signal-to-Noise Ratio Margin."
	::= { aesLineDiagnostic 8 } 

	aesAturLineDiagACTATP OBJECT-TYPE
	SYNTAX	INTEGER
	UNITS	"tenth dB"
	ACCESS	read-only
	STATUS	mandatory
	DESCRIPTION
		"Actual Aggregate Transmit Power."
	::= { aesLineDiagnostic 9 }
	
	aesAturLineDiagATTNDR OBJECT-TYPE
	SYNTAX	Unsigned32
	ACCESS	read-only
	STATUS	mandatory
	DESCRIPTION
		"Attainable Net Data Rate, in bps."
	::= { aesLineDiagnostic 10 }

	aesLineDiagTarget OBJECT-TYPE
	SYNTAX	INTEGER
	ACCESS	read-write
	STATUS	mandatory
	DESCRIPTION
		"Ifindex of the ADSL port which will be diagnosed."
	::= { aesLineDiagnostic 11 }
	
	aesLineDiagOps OBJECT-TYPE
	SYNTAX	INTEGER
	ACCESS	read-write
	STATUS	mandatory
	DESCRIPTION
		"The manager sets the object to one to start line diagnostics and the agent clears the
		object to zero when diagnostics is successfully completed."
	::= { aesLineDiagnostic 12 }

	aesLineDiagFailReason OBJECT-TYPE
	SYNTAX	DisplayString
	ACCESS	read-only
	STATUS	mandatory
	DESCRIPTION
		"The reason of failed diagnostics."
	::= { aesLineDiagnostic 13 }
	

-- ADSL Line Diagnostic Per Subcarrier

	aesLineDiagPs		OBJECT IDENTIFIER ::= { aesSeriesCommon 4 }

	aesAtucNumOfSubcarriersPerPort OBJECT-TYPE
	SYNTAX	INTEGER
	ACCESS	read-only
	STATUS	mandatory
	DESCRIPTION
		"The number of subcarriers per port for ATU-C."
	::= { aesLineDiagPs 1 }

	aesAturNumOfSubcarriersPerPort OBJECT-TYPE
	SYNTAX	INTEGER
	ACCESS	read-only
	STATUS	mandatory
	DESCRIPTION
		"The number of subcarriers per port for ATU-R."
	::= { aesLineDiagPs 2 }
			
	aesLineDiagPsCCFLirl1 OBJECT-TYPE
	SYNTAX	OCTET STRING
	ACCESS	read-only
	STATUS	mandatory
	DESCRIPTION
		"Channel Characteristics Function H(f) per subcarrier. The value is the real
		part of a complex value in liner scale.
		The first two octets specify the li.rl value for subcarrier 1, and the second
		two octets specify the li.rl value for subcarrier 2, and so on. The object
		provides li.rl values for subcarrier 1 to 256."
	::= { aesLineDiagPs 3 }

	aesLineDiagPsCCFLirl2 OBJECT-TYPE
	SYNTAX	OCTET STRING
	ACCESS	read-only
	STATUS	mandatory
	DESCRIPTION
		"Channel Characteristics Function H(f) per subcarrier. The value is the real
		part of a complex value in liner scale.
		The first two octets specify the li.rl value for subcarrier 257, and the second
		two octets specify the li.rl value for subcarrier 258, and so on. The object
		provides li.rl values for subcarrier 257 to 512."
	::= { aesLineDiagPs 4 }
		
	aesLineDiagPsCCFLiim1 OBJECT-TYPE
	SYNTAX	OCTET STRING
	ACCESS	read-only
	STATUS	mandatory
	DESCRIPTION
		"Channel Characteristics Function H(f) per subcarrier. The value is the image
		part of a complex value in liner scale.
		The first two octets specify the li.im value for subcarrier 1, and the second
		two octets specify the li.im value for subcarrier 2, and so on. The object
		provides li.im values for subcarrier 1 to 256."
	::= { aesLineDiagPs 5 }

	aesLineDiagPsCCFLiim2 OBJECT-TYPE
	SYNTAX	OCTET STRING
	ACCESS	read-only
	STATUS	mandatory
	DESCRIPTION
		"Channel Characteristics Function H(f) per subcarrier. The value is the image
		part of a complex value in liner scale.
		The first two octets specify the li.im value for subcarrier 257, and the second
		two octets specify the li.im value for subcarrier 258, and so on. The object
		provides li.im values for subcarrier 257 to 512."
	::= { aesLineDiagPs 6 }

	aesLineDiagPsCCFLog1 OBJECT-TYPE
	SYNTAX	OCTET STRING
	ACCESS	read-only
	STATUS	mandatory
	DESCRIPTION
		"Channel Characteristics Function H(f) per subcarrier. The value 
		provides magnitude value in a logarithmic scale.
		The first two octets specify the log value for subcarrier 1, and the second
		two octets specify the log value for subcarrier 2, and so on. The object
		provides log values for subcarrier 1 to 256."
	::= { aesLineDiagPs 7 }

	aesLineDiagPsCCFLog2 OBJECT-TYPE
	SYNTAX	OCTET STRING
	ACCESS	read-only
	STATUS	mandatory
	DESCRIPTION
		"Channel Characteristics Function H(f) per subcarrier. The value 
		provides magnitude value in a logarithmic scale.
		The first two octets specify the log value for subcarrier 257, and the second
		two octets specify the log value for subcarrier 258, and so on. The object
		provides log values for subcarrier 257 to 512."
	::= { aesLineDiagPs 8 }
			
	aesLineDiagPsQLN OBJECT-TYPE
	SYNTAX	OCTET STRING
	UNITS	"tenth dB"
	ACCESS	read-only
	STATUS	mandatory
	DESCRIPTION
		"Quiet Line Noise PSD QLN(f) per subcarrier. The first octet specify QLN
		for subcarrier 1, and the second octet specify QLN for subcarrier 2, and so on.
		The object provides QLN for subcarrier 1 to 512."
	::= { aesLineDiagPs 9 }

	aesLineDiagPsSNR OBJECT-TYPE
	SYNTAX	OCTET STRING
	UNITS	"tenth dB"
	ACCESS	read-only
	STATUS	mandatory
	DESCRIPTION
		"Signal-to-Noise Ratio SNR(f) per subcarrier. The first octet specify SNR
		for subcarrier 1, and the second octet specify SNR for subcarrier 2, and so on.
		The object provides SNR for subcarrier 1 to 512."
	::= { aesLineDiagPs 10 }

	
-- Max # of Alarm Profiles
	
        aesMaxNumOfAlarmProfiles OBJECT-TYPE
        SYNTAX  INTEGER
        ACCESS  read-only
        STATUS  mandatory
        DESCRIPTION
        	"The maximum number of ADSL alarm profiles which the system supports."
        ::= { aesSeriesCommon 5 }


-- Bit Loading

        aesBitLoadingTable OBJECT-TYPE
        SYNTAX	SEQUENCE OF AesBitLoadingEntry
        ACCESS  not-accessible
        STATUS  mandatory
        DESCRIPTION
        	"This table provides the number of bits per carrier for each ADSL port."
        ::= { aesSeriesCommon 6 }

	aesBitLoadingEntry OBJECT-TYPE
        SYNTAX	AesBitLoadingEntry
        ACCESS	not-accessible
        STATUS	mandatory
        DESCRIPTION    	"An entry in aesBitLoadingTable."
        INDEX          	{ ifIndex }
        ::= { aesBitLoadingTable 1 }

        AesBitLoadingEntry ::=
           SEQUENCE {
        	aesBitLoadingBits		OCTET STRING,
        	aesBitLoadingAtucNumOfCarriers 	INTEGER,
        	aesBitLoadingAturNumOfCarriers	INTEGER
           }

        aesBitLoadingBits OBJECT-TYPE
        SYNTAX  OCTET STRING
        ACCESS  read-only
        STATUS  mandatory
        DESCRIPTION
        	"This object provides the number of bits for all carriers in the port. 
        	The first octet specify the number of bits for carrier 1, and the second 
        	octet specify the number of bits for carrier 2, and so on.
		The object provides the number of bits for carrier 1 to 512."
        ::= { aesBitLoadingEntry 1 }

	aesBitLoadingAtucNumOfCarriers OBJECT-TYPE
	SYNTAX	INTEGER
	ACCESS	read-only
	STATUS	mandatory
	DESCRIPTION
		"The number of carriers for ATU-C."
	::= { aesBitLoadingEntry 2 }

	aesBitLoadingAturNumOfCarriers OBJECT-TYPE
	SYNTAX	INTEGER
	ACCESS	read-only
	STATUS	mandatory
	DESCRIPTION
		"The number of carriers for ATU-R."
	::= { aesBitLoadingEntry 3 }
	
	
-- Line Status

        aesLineStatusTable OBJECT-TYPE
        SYNTAX	SEQUENCE OF AesLineStatusEntry
        ACCESS  not-accessible
        STATUS  mandatory
        DESCRIPTION
                 	"This table includes the ADSL line status."
        ::= { aesSeriesCommon 7 }

	aesLineStatusEntry OBJECT-TYPE
        SYNTAX	AesLineStatusEntry
        ACCESS	not-accessible
        STATUS	mandatory
        DESCRIPTION    	"An entry in aesLineStatusTable."
        INDEX          	{ ifIndex }
        ::= { aesLineStatusTable 1 }

        AesLineStatusEntry ::=
           SEQUENCE {
        	aesLineStatusAdslMode	INTEGER
           }

        aesLineStatusAdslMode OBJECT-TYPE
        SYNTAX  INTEGER {
			gDotLite(1),
			gDotDmt(2),
			t1Dot413(3),
			etsi(4),
			adsl2(5),
			adsl2Plus(6)
	}
        ACCESS  read-only
        STATUS  mandatory
        DESCRIPTION
                      	"The link up mode of the ADSL line."
        ::= { aesLineStatusEntry 1 }	        
               		
END
