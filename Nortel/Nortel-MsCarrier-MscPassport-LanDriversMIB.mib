Nortel-MsCarrier-MscPassport-LanDriversMIB
DEFINITIONS ::= BEGIN



IMPORTS

      OBJECT-TYPE
   FROM RFC-1212

      mscPassportMIBs,
      mscComponents
   FROM Nortel-MsCarrier-MscPassport-UsefulDefinitionsMIB

      FddiMACLongAddressType,
      Counter32,
      DisplayString,
      FddiTimeNano,
      StorageType,
      RowStatus,
      InterfaceIndex,
      Gauge32,
      Integer32,
      MacAddress,
      FddiTimeMilli,
      Unsigned32
   FROM Nortel-MsCarrier-MscPassport-StandardTextualConventionsMIB

      AsciiString,
      NonReplicated,
      EnterpriseDateAndTime,
      PassportCounter64,
      Link
   FROM Nortel-MsCarrier-MscPassport-TextualConventionsMIB

      mscLpIndex,
      mscLp
   FROM Nortel-MsCarrier-MscPassport-LogicalProcessorMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     LanDrivers Enterprise MIB."

lanDriversMIB OBJECT IDENTIFIER ::= { mscPassportMIBs 30 }










-- Lp/n Ethernet/n
-- This component defines an instance of an Ethernet station attached to a 
-- bus. One instance of this component will be created for each hardware 
-- port. Each station will be provisioned prior to operating on the bus.

mscLpEnet OBJECT IDENTIFIER ::= { mscLp 3 }



mscLpEnetRowStatusTable OBJECT-TYPE
   SYNTAX     SEQUENCE OF MscLpEnetRowStatusEntry
   ACCESS     not-accessible
   STATUS     mandatory
   DESCRIPTION
     "This entry controls the addition and deletion of 
      mscLpEnet components."
::= { mscLpEnet 1 }

mscLpEnetRowStatusEntry OBJECT-TYPE
   SYNTAX     MscLpEnetRowStatusEntry
   ACCESS     not-accessible
   STATUS     mandatory
   DESCRIPTION
     "A single entry in the table represents a single 
      mscLpEnet component."
   INDEX {
      mscLpIndex,
      mscLpEnetIndex }
::= { mscLpEnetRowStatusTable 1 }

MscLpEnetRowStatusEntry ::= SEQUENCE {
   mscLpEnetRowStatus
      RowStatus,
   mscLpEnetComponentName
      DisplayString,
   mscLpEnetStorageType
      StorageType,
   mscLpEnetIndex
      Integer32 }

mscLpEnetRowStatus OBJECT-TYPE
   SYNTAX     RowStatus 
   ACCESS     read-write
   STATUS     mandatory
   DESCRIPTION
     "This variable is used as the basis for SNMP naming of
      mscLpEnet components.
      These components can be added and deleted."
::= { mscLpEnetRowStatusEntry 1 }

mscLpEnetComponentName OBJECT-TYPE
   SYNTAX     DisplayString 
   ACCESS     read-only
   STATUS     mandatory
   DESCRIPTION
     "This variable provides the component's string name for
      use with the ASCII Console Interface"
::= { mscLpEnetRowStatusEntry 2 }

mscLpEnetStorageType OBJECT-TYPE
   SYNTAX     StorageType 
   ACCESS     read-only
   STATUS     mandatory
   DESCRIPTION
     "This variable represents the storage type value for the
      mscLpEnet tables."
::= { mscLpEnetRowStatusEntry 4 }

mscLpEnetIndex OBJECT-TYPE
   SYNTAX     Integer32 (0..5)
   ACCESS     not-accessible
   STATUS     mandatory
   DESCRIPTION
     "This variable represents the index for the mscLpEnet tables."
::= { mscLpEnetRowStatusEntry 10 }

mscLpEnetCidDataTable OBJECT-TYPE
   SYNTAX     SEQUENCE OF MscLpEnetCidDataEntry
   ACCESS     not-accessible
   STATUS     mandatory
   DESCRIPTION
     "This group contains the attribute for a component's Customer 
      Identifier (CID). Refer to the attribute description for a detailed 
      explanation of CIDs."
::= { mscLpEnet 10 }

mscLpEnetCidDataEntry OBJECT-TYPE
   SYNTAX     MscLpEnetCidDataEntry
   ACCESS     not-accessible
   STATUS     mandatory
   DESCRIPTION
     "An entry in the mscLpEnetCidDataTable."
   INDEX {
      mscLpIndex,
      mscLpEnetIndex }
::= { mscLpEnetCidDataTable 1 }

MscLpEnetCidDataEntry ::= SEQUENCE {
   mscLpEnetCustomerIdentifier
      Unsigned32 }

mscLpEnetCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpEnetCidDataEntry 1 }

mscLpEnetIfEntryTable OBJECT-TYPE
   SYNTAX     SEQUENCE OF MscLpEnetIfEntryEntry
   ACCESS     not-accessible
   STATUS     mandatory
   DESCRIPTION
     "This group contains the provisionable attributes for the ifEntry."
::= { mscLpEnet 11 }

mscLpEnetIfEntryEntry OBJECT-TYPE
   SYNTAX     MscLpEnetIfEntryEntry
   ACCESS     not-accessible
   STATUS     mandatory
   DESCRIPTION
     "An entry in the mscLpEnetIfEntryTable."
   INDEX {
      mscLpIndex,
      mscLpEnetIndex }
::= { mscLpEnetIfEntryTable 1 }

MscLpEnetIfEntryEntry ::= SEQUENCE {
   mscLpEnetIfAdminStatus
      INTEGER,
   mscLpEnetIfIndex
      InterfaceIndex }

mscLpEnetIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpEnetIfEntryEntry 1 }

mscLpEnetIfIndex OBJECT-TYPE
   SYNTAX     InterfaceIndex (1..65535)
   ACCESS     read-only
   STATUS     mandatory
   DESCRIPTION
     "This is the index for the IfEntry. Its value is automatically initialized 
      during the provisioning process."
::= { mscLpEnetIfEntryEntry 2 }

mscLpEnetProvTable OBJECT-TYPE
   SYNTAX     SEQUENCE OF MscLpEnetProvEntry
   ACCESS     not-accessible
   STATUS     mandatory
   DESCRIPTION
     "This group contains provisioned attributes for the 		Ethernet component."
::= { mscLpEnet 12 }

mscLpEnetProvEntry OBJECT-TYPE
   SYNTAX     MscLpEnetProvEntry
   ACCESS     not-accessible
   STATUS     mandatory
   DESCRIPTION
     "An entry in the mscLpEnetProvTable."
   INDEX {
      mscLpIndex,
      mscLpEnetIndex }
::= { mscLpEnetProvTable 1 }

MscLpEnetProvEntry ::= SEQUENCE {
   mscLpEnetHeartbeatPacket
      INTEGER,
   mscLpEnetApplicationFramerName
      Link }

mscLpEnetHeartbeatPacket OBJECT-TYPE
   SYNTAX     INTEGER  {
                 enabled(1),
                 disabled(2) }
   ACCESS     read-write
   STATUS     mandatory
   DESCRIPTION
     "The heartbeat packet feature is used to select whether or not the station 
      will generate a heartbeat packet. If enabled, the station will generate one 
      heartbeat packet every second. If disabled, the station will not generate 
      any heartbeat packets."
   DEFVAL     { enabled }
::= { mscLpEnetProvEntry 1 }

mscLpEnetApplicationFramerName OBJECT-TYPE
   SYNTAX     Link 
   ACCESS     read-write
   STATUS     mandatory
   DESCRIPTION
     "This attribute contains the component name of a Framer which is 
      associated with the Ethernet component. This link is used by the 
      component administration system (CAS) to identify which card the 
      application component (associated with the Framer component) is to be 
      created."
::= { mscLpEnetProvEntry 2 }

mscLpEnetAdminInfoTable OBJECT-TYPE
   SYNTAX     SEQUENCE OF MscLpEnetAdminInfoEntry
   ACCESS     not-accessible
   STATUS     mandatory
   DESCRIPTION
     "This group contains the attributes pertaining to the vendor of the 
      equipment."
::= { mscLpEnet 13 }

mscLpEnetAdminInfoEntry OBJECT-TYPE
   SYNTAX     MscLpEnetAdminInfoEntry
   ACCESS     not-accessible
   STATUS     mandatory
   DESCRIPTION
     "An entry in the mscLpEnetAdminInfoTable."
   INDEX {
      mscLpIndex,
      mscLpEnetIndex }
::= { mscLpEnetAdminInfoTable 1 }

MscLpEnetAdminInfoEntry ::= SEQUENCE {
   mscLpEnetVendor
      AsciiString,
   mscLpEnetCommentText
      AsciiString }

mscLpEnetVendor OBJECT-TYPE
   SYNTAX     AsciiString (SIZE (0..20))
   ACCESS     read-write
   STATUS     mandatory
   DESCRIPTION
     "This is the name of the vendor supplying the facility."
::= { mscLpEnetAdminInfoEntry 1 }

mscLpEnetCommentText OBJECT-TYPE
   SYNTAX     AsciiString (SIZE (0..60))
   ACCESS     read-write
   STATUS     mandatory
   DESCRIPTION
     "Any miscellaneous text about the facility."
::= { mscLpEnetAdminInfoEntry 2 }

mscLpEnetStateTable OBJECT-TYPE
   SYNTAX     SEQUENCE OF MscLpEnetStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpEnet 15 }

mscLpEnetStateEntry OBJECT-TYPE
   SYNTAX     MscLpEnetStateEntry
   ACCESS     not-accessible
   STATUS     mandatory
   DESCRIPTION
     "An entry in the mscLpEnetStateTable."
   INDEX {
      mscLpIndex,
      mscLpEnetIndex }
::= { mscLpEnetStateTable 1 }

MscLpEnetStateEntry ::= SEQUENCE {
   mscLpEnetAdminState
      INTEGER,
   mscLpEnetOperationalState
      INTEGER,
   mscLpEnetUsageState
      INTEGER }

mscLpEnetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpEnetStateEntry 1 }

mscLpEnetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpEnetStateEntry 2 }

mscLpEnetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpEnetStateEntry 3 }

mscLpEnetOperStatusTable OBJECT-TYPE
   SYNTAX     SEQUENCE OF MscLpEnetOperStatusEntry
   ACCESS     not-accessible
   STATUS     mandatory
   DESCRIPTION
     "This group includes the Operational Status attribute. This attribute 
      defines the current operational state of this component."
::= { mscLpEnet 16 }

mscLpEnetOperStatusEntry OBJECT-TYPE
   SYNTAX     MscLpEnetOperStatusEntry
   ACCESS     not-accessible
   STATUS     mandatory
   DESCRIPTION
     "An entry in the mscLpEnetOperStatusTable."
   INDEX {
      mscLpIndex,
      mscLpEnetIndex }
::= { mscLpEnetOperStatusTable 1 }

MscLpEnetOperStatusEntry ::= SEQUENCE {
   mscLpEnetSnmpOperStatus
      INTEGER }

mscLpEnetSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpEnetOperStatusEntry 1 }

mscLpEnetOperTable OBJECT-TYPE
   SYNTAX     SEQUENCE OF MscLpEnetOperEntry
   ACCESS     not-accessible
   STATUS     mandatory
   DESCRIPTION
     "This group contains the operational attributes of the Ethernet 
      component."
::= { mscLpEnet 17 }

mscLpEnetOperEntry OBJECT-TYPE
   SYNTAX     MscLpEnetOperEntry
   ACCESS     not-accessible
   STATUS     mandatory
   DESCRIPTION
     "An entry in the mscLpEnetOperTable."
   INDEX {
      mscLpIndex,
      mscLpEnetIndex }
::= { mscLpEnetOperTable 1 }

MscLpEnetOperEntry ::= SEQUENCE {
   mscLpEnetMacAddress
      MacAddress }

mscLpEnetMacAddress OBJECT-TYPE
   SYNTAX     MacAddress (SIZE (6))
   ACCESS     read-only
   STATUS     mandatory
   DESCRIPTION
     "The medium access controller (MAC) address is an address that is only 
      recognized by one station on the network The value of this attribute will 
      be assigned by the system. MAC address is displayed in canonical 
      format."
::= { mscLpEnetOperEntry 1 }

mscLpEnetStatsTable OBJECT-TYPE
   SYNTAX     SEQUENCE OF MscLpEnetStatsEntry
   ACCESS     not-accessible
   STATUS     mandatory
   DESCRIPTION
     "This group contains statistical attributes for the		 Ethernet component."
::= { mscLpEnet 18 }

mscLpEnetStatsEntry OBJECT-TYPE
   SYNTAX     MscLpEnetStatsEntry
   ACCESS     not-accessible
   STATUS     mandatory
   DESCRIPTION
     "An entry in the mscLpEnetStatsTable."
   INDEX {
      mscLpIndex,
      mscLpEnetIndex }
::= { mscLpEnetStatsTable 1 }

MscLpEnetStatsEntry ::= SEQUENCE {
   mscLpEnetAlignmentErrors
      Counter32,
   mscLpEnetFcsErrors
      Counter32,
   mscLpEnetSingleCollisionFrames
      Counter32,
   mscLpEnetMultipleCollisionFrames
      Counter32,
   mscLpEnetSqeTestErrors
      Counter32,
   mscLpEnetDeferredTransmissions
      Counter32,
   mscLpEnetLateCollisions
      Counter32,
   mscLpEnetExcessiveCollisions
      Counter32,
   mscLpEnetMacTransmitErrors
      Counter32,
   mscLpEnetCarrierSenseErrors
      Counter32,
   mscLpEnetFrameTooLongs
      Counter32,
   mscLpEnetMacReceiveErrors
      Counter32 }

mscLpEnetAlignmentErrors OBJECT-TYPE
   SYNTAX     Counter32 
   ACCESS     read-only
   STATUS     mandatory
   DESCRIPTION
     "The alignmentErrors counter indicates the number of frames received 
      which were not an integral number of octets in length. Frames will be 
      checked for alignmentErrors before they are checked for Frame Check 
      Sequence (FCS) errors. If there is an alignment error, the error will only 
      be counted here and not in fcsErrors. This counter wraps around after it 
      exceeds its maximum value."
::= { mscLpEnetStatsEntry 2 }

mscLpEnetFcsErrors OBJECT-TYPE
   SYNTAX     Counter32 
   ACCESS     read-only
   STATUS     mandatory
   DESCRIPTION
     "The fcsErrors, Frame Check Sequence (FCS) error, counter indicates the 
      number of frames received which were an integral number of octets in 
      length and did not pass the FCS check. This counter wraps around after 
      it exceeds its maximum value."
::= { mscLpEnetStatsEntry 3 }

mscLpEnetSingleCollisionFrames OBJECT-TYPE
   SYNTAX     Counter32 
   ACCESS     read-only
   STATUS     mandatory
   DESCRIPTION
     "The singleCollisionFrames counter indicates the number of frames 
      successfully transmitted which experienced exactly one collision. This 
      counter wraps around after it exceeds its maximum value."
::= { mscLpEnetStatsEntry 4 }

mscLpEnetMultipleCollisionFrames OBJECT-TYPE
   SYNTAX     Counter32 
   ACCESS     read-only
   STATUS     mandatory
   DESCRIPTION
     "The multipleCollisionFrames counter indicates the number of frames 
      successfully transmitted which experienced more than one collision. 
      This counter wraps around after it exceeds its maximum value."
::= { mscLpEnetStatsEntry 5 }

mscLpEnetSqeTestErrors OBJECT-TYPE
   SYNTAX     Counter32 
   ACCESS     read-only
   STATUS     mandatory
   DESCRIPTION
     "The sqeTestErrors, Signal Quality Error (SQE) Test errors, counter 
      indicates the number of times the 'SQE Test Error' message has been 
      generated for the station. This counter wraps around after it exceeds its 
      maximum value."
::= { mscLpEnetStatsEntry 6 }

mscLpEnetDeferredTransmissions OBJECT-TYPE
   SYNTAX     Counter32 
   ACCESS     read-only
   STATUS     mandatory
   DESCRIPTION
     "The deferredTransmissions counter indicates the number of frames 
      which experienced a transmission delay because the medium was busy. 
      This counter wraps around after it exceeds its maximum value."
::= { mscLpEnetStatsEntry 7 }

mscLpEnetLateCollisions OBJECT-TYPE
   SYNTAX     Counter32 
   ACCESS     read-only
   STATUS     mandatory
   DESCRIPTION
     "The lateCollisions counter indicates the number of times a collision was 
      detected later than 512 bit-times into the transmission of a packet. This 
      counter wraps around after it exceeds its maximum value."
::= { mscLpEnetStatsEntry 8 }

mscLpEnetExcessiveCollisions OBJECT-TYPE
   SYNTAX     Counter32 
   ACCESS     read-only
   STATUS     mandatory
   DESCRIPTION
     "The excessiveCollisions counter indicates the number of frames which 
      failed to get transmitted due to excessive collisions. This counter wraps 
      around after it exceeds its maximum value."
::= { mscLpEnetStatsEntry 9 }

mscLpEnetMacTransmitErrors OBJECT-TYPE
   SYNTAX     Counter32 
   ACCESS     read-only
   STATUS     mandatory
   DESCRIPTION
     "The Medium Access Controller (MAC) transmit error counter indicates 
      the number of times that a transmission failed due to internal MAC 
      transmit errors. This counter wraps around after it exceeds its maximum 
      value."
::= { mscLpEnetStatsEntry 10 }

mscLpEnetCarrierSenseErrors OBJECT-TYPE
   SYNTAX     Counter32 
   ACCESS     read-only
   STATUS     mandatory
   DESCRIPTION
     "The carrier sense error counter indicates the number of times that the 
      carrier sense condition was lost or never asserted when attempting to 
      transmit a frame. This counter wraps around after it exceeds its 
      maximum value."
::= { mscLpEnetStatsEntry 11 }

mscLpEnetFrameTooLongs OBJECT-TYPE
   SYNTAX     Counter32 
   ACCESS     read-only
   STATUS     mandatory
   DESCRIPTION
     "The frame too long counter indicates the number of frames received 
      which exceeded the maximum frame size. This counter wraps around 
      after it exceeds its maximum value."
::= { mscLpEnetStatsEntry 12 }

mscLpEnetMacReceiveErrors OBJECT-TYPE
   SYNTAX     Counter32 
   ACCESS     read-only
   STATUS     mandatory
   DESCRIPTION
     "The Medium Access Controller (MAC) receive error counter indicates 
      the number of times a receive failed due to internal MAC receive errors. 
      This counter wraps around after it exceeds its maximum value."
::= { mscLpEnetStatsEntry 13 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

mscLpEnetLt OBJECT IDENTIFIER ::= { mscLpEnet 2 }



mscLpEnetLtRowStatusTable OBJECT-TYPE
   SYNTAX     SEQUENCE OF MscLpEnetLtRowStatusEntry
   ACCESS     not-accessible
   STATUS     mandatory
   DESCRIPTION
     "This entry controls the addition and deletion of 
      mscLpEnetLt components."
::= { mscLpEnetLt 1 }

mscLpEnetLtRowStatusEntry OBJECT-TYPE
   SYNTAX     MscLpEnetLtRowStatusEntry
   ACCESS     not-accessible
   STATUS     mandatory
   DESCRIPTION
     "A single entry in the table represents a single 
      mscLpEnetLt component."
   INDEX {
      mscLpIndex,
      mscLpEnetIndex,
      mscLpEnetLtIndex }
::= { mscLpEnetLtRowStatusTable 1 }

MscLpEnetLtRowStatusEntry ::= SEQUENCE {
   mscLpEnetLtRowStatus
      RowStatus,
   mscLpEnetLtComponentName
      DisplayString,
   mscLpEnetLtStorageType
      StorageType,
   mscLpEnetLtIndex
      NonReplicated }

mscLpEnetLtRowStatus OBJECT-TYPE
   SYNTAX     RowStatus 
   ACCESS     read-only
   STATUS     mandatory
   DESCRIPTION
     "This variable is used as the basis for SNMP naming of
      mscLpEnetLt components.
      These components cannot be added nor deleted."
::= { mscLpEnetLtRowStatusEntry 1 }

mscLpEnetLtComponentName OBJECT-TYPE
   SYNTAX     DisplayString 
   ACCESS     read-only
   STATUS     mandatory
   DESCRIPTION
     "This variable provides the component's string name for
      use with the ASCII Console Interface"
::= { mscLpEnetLtRowStatusEntry 2 }

mscLpEnetLtStorageType OBJECT-TYPE
   SYNTAX     StorageType 
   ACCESS     read-only
   STATUS     mandatory
   DESCRIPTION
     "This variable represents the storage type value for the
      mscLpEnetLt tables."
::= { mscLpEnetLtRowStatusEntry 4 }

mscLpEnetLtIndex OBJECT-TYPE
   SYNTAX     NonReplicated 
   ACCESS     not-accessible
   STATUS     mandatory
   DESCRIPTION
     "This variable represents the index for the mscLpEnetLt tables."
::= { mscLpEnetLtRowStatusEntry 10 }

mscLpEnetLtTopTable OBJECT-TYPE
   SYNTAX     SEQUENCE OF MscLpEnetLtTopEntry
   ACCESS     not-accessible
   STATUS     mandatory
   DESCRIPTION
     "This group contains the operational data for the LanTest component 
      and its subcomponents."
::= { mscLpEnetLt 20 }

mscLpEnetLtTopEntry OBJECT-TYPE
   SYNTAX     MscLpEnetLtTopEntry
   ACCESS     not-accessible
   STATUS     mandatory
   DESCRIPTION
     "An entry in the mscLpEnetLtTopTable."
   INDEX {
      mscLpIndex,
      mscLpEnetIndex,
      mscLpEnetLtIndex }
::= { mscLpEnetLtTopTable 1 }

MscLpEnetLtTopEntry ::= SEQUENCE {
   mscLpEnetLtTData
      AsciiString }

mscLpEnetLtTData OBJECT-TYPE
   SYNTAX     AsciiString (SIZE (0..255))
   ACCESS     read-write
   STATUS     mandatory
   DESCRIPTION
     "This attribute is used to display and set attributes."
::= { mscLpEnetLtTopEntry 1 }


-- This component compares frames received from the hardware and 
-- emulator during testing.

mscLpEnetLtFrmCmp OBJECT IDENTIFIER ::= { mscLpEnetLt 2 }



mscLpEnetLtFrmCmpRowStatusTable OBJECT-TYPE
   SYNTAX     SEQUENCE OF MscLpEnetLtFrmCmpRowStatusEntry
   ACCESS     not-accessible
   STATUS     mandatory
   DESCRIPTION
     "This entry controls the addition and deletion of 
      mscLpEnetLtFrmCmp components."
::= { mscLpEnetLtFrmCmp 1 }

mscLpEnetLtFrmCmpRowStatusEntry OBJECT-TYPE
   SYNTAX     MscLpEnetLtFrmCmpRowStatusEntry
   ACCESS     not-accessible
   STATUS     mandatory
   DESCRIPTION
     "A single entry in the table represents a single 
      mscLpEnetLtFrmCmp component."
   INDEX {
      mscLpIndex,
      mscLpEnetIndex,
      mscLpEnetLtIndex,
      mscLpEnetLtFrmCmpIndex }
::= { mscLpEnetLtFrmCmpRowStatusTable 1 }

MscLpEnetLtFrmCmpRowStatusEntry ::= SEQUENCE {
   mscLpEnetLtFrmCmpRowStatus
      RowStatus,
   mscLpEnetLtFrmCmpComponentName
      DisplayString,
   mscLpEnetLtFrmCmpStorageType
      StorageType,
   mscLpEnetLtFrmCmpIndex
      NonReplicated }

mscLpEnetLtFrmCmpRowStatus OBJECT-TYPE
   SYNTAX     RowStatus 
   ACCESS     read-only
   STATUS     mandatory
   DESCRIPTION
     "This variable is used as the basis for SNMP naming of
      mscLpEnetLtFrmCmp components.
      These components cannot be added nor deleted."
::= { mscLpEnetLtFrmCmpRowStatusEntry 1 }

mscLpEnetLtFrmCmpComponentName OBJECT-TYPE
   SYNTAX     DisplayString 
   ACCESS     read-only
   STATUS     mandatory
   DESCRIPTION
     "This variable provides the component's string name for
      use with the ASCII Console Interface"
::= { mscLpEnetLtFrmCmpRowStatusEntry 2 }

mscLpEnetLtFrmCmpStorageType OBJECT-TYPE
   SYNTAX     StorageType 
   ACCESS     read-only
   STATUS     mandatory
   DESCRIPTION
     "This variable represents the storage type value for the
      mscLpEnetLtFrmCmp tables."
::= { mscLpEnetLtFrmCmpRowStatusEntry 4 }

mscLpEnetLtFrmCmpIndex OBJECT-TYPE
   SYNTAX     NonReplicated 
   ACCESS     not-accessible
   STATUS     mandatory
   DESCRIPTION
     "This variable represents the index for the mscLpEnetLtFrmCmp tables."
::= { mscLpEnetLtFrmCmpRowStatusEntry 10 }

mscLpEnetLtFrmCmpTopTable OBJECT-TYPE
   SYNTAX     SEQUENCE OF MscLpEnetLtFrmCmpTopEntry
   ACCESS     not-accessible
   STATUS     mandatory
   DESCRIPTION
     "This group contains the operational data for the LanTest component 
      and its subcomponents."
::= { mscLpEnetLtFrmCmp 10 }

mscLpEnetLtFrmCmpTopEntry OBJECT-TYPE
   SYNTAX     MscLpEnetLtFrmCmpTopEntry
   ACCESS     not-accessible
   STATUS     mandatory
   DESCRIPTION
     "An entry in the mscLpEnetLtFrmCmpTopTable."
   INDEX {
      mscLpIndex,
      mscLpEnetIndex,
      mscLpEnetLtIndex,
      mscLpEnetLtFrmCmpIndex }
::= { mscLpEnetLtFrmCmpTopTable 1 }

MscLpEnetLtFrmCmpTopEntry ::= SEQUENCE {
   mscLpEnetLtFrmCmpTData
      AsciiString }

mscLpEnetLtFrmCmpTData OBJECT-TYPE
   SYNTAX     AsciiString (SIZE (0..255))
   ACCESS     read-write
   STATUS     mandatory
   DESCRIPTION
     "This attribute is used to display and set attributes."
::= { mscLpEnetLtFrmCmpTopEntry 1 }


-- This component receives its input from FrameBuild and places it 
-- upon the hardware which sends it to the appropriate emulator.

mscLpEnetLtFrmCpy OBJECT IDENTIFIER ::= { mscLpEnetLt 3 }



mscLpEnetLtFrmCpyRowStatusTable OBJECT-TYPE
   SYNTAX     SEQUENCE OF MscLpEnetLtFrmCpyRowStatusEntry
   ACCESS     not-accessible
   STATUS     mandatory
   DESCRIPTION
     "This entry controls the addition and deletion of 
      mscLpEnetLtFrmCpy components."
::= { mscLpEnetLtFrmCpy 1 }

mscLpEnetLtFrmCpyRowStatusEntry OBJECT-TYPE
   SYNTAX     MscLpEnetLtFrmCpyRowStatusEntry
   ACCESS     not-accessible
   STATUS     mandatory
   DESCRIPTION
     "A single entry in the table represents a single 
      mscLpEnetLtFrmCpy component."
   INDEX {
      mscLpIndex,
      mscLpEnetIndex,
      mscLpEnetLtIndex,
      mscLpEnetLtFrmCpyIndex }
::= { mscLpEnetLtFrmCpyRowStatusTable 1 }

MscLpEnetLtFrmCpyRowStatusEntry ::= SEQUENCE {
   mscLpEnetLtFrmCpyRowStatus
      RowStatus,
   mscLpEnetLtFrmCpyComponentName
      DisplayString,
   mscLpEnetLtFrmCpyStorageType
      StorageType,
   mscLpEnetLtFrmCpyIndex
      NonReplicated }

mscLpEnetLtFrmCpyRowStatus OBJECT-TYPE
   SYNTAX     RowStatus 
   ACCESS     read-only
   STATUS     mandatory
   DESCRIPTION
     "This variable is used as the basis for SNMP naming of
      mscLpEnetLtFrmCpy components.
      These components cannot be added nor deleted."
::= { mscLpEnetLtFrmCpyRowStatusEntry 1 }

mscLpEnetLtFrmCpyComponentName OBJECT-TYPE
   SYNTAX     DisplayString 
   ACCESS     read-only
   STATUS     mandatory
   DESCRIPTION
     "This variable provides the component's string name for
      use with the ASCII Console Interface"
::= { mscLpEnetLtFrmCpyRowStatusEntry 2 }

mscLpEnetLtFrmCpyStorageType OBJECT-TYPE
   SYNTAX     StorageType 
   ACCESS     read-only
   STATUS     mandatory
   DESCRIPTION
     "This variable represents the storage type value for the
      mscLpEnetLtFrmCpy tables."
::= { mscLpEnetLtFrmCpyRowStatusEntry 4 }

mscLpEnetLtFrmCpyIndex OBJECT-TYPE
   SYNTAX     NonReplicated 
   ACCESS     not-accessible
   STATUS     mandatory
   DESCRIPTION
     "This variable represents the index for the mscLpEnetLtFrmCpy tables."
::= { mscLpEnetLtFrmCpyRowStatusEntry 10 }

mscLpEnetLtFrmCpyTopTable OBJECT-TYPE
   SYNTAX     SEQUENCE OF MscLpEnetLtFrmCpyTopEntry
   ACCESS     not-accessible
   STATUS     mandatory
   DESCRIPTION
     "This group contains the operational data for the LanTest component 
      and its subcomponents."
::= { mscLpEnetLtFrmCpy 10 }

mscLpEnetLtFrmCpyTopEntry OBJECT-TYPE
   SYNTAX     MscLpEnetLtFrmCpyTopEntry
   ACCESS     not-accessible
   STATUS     mandatory
   DESCRIPTION
     "An entry in the mscLpEnetLtFrmCpyTopTable."
   INDEX {
      mscLpIndex,
      mscLpEnetIndex,
      mscLpEnetLtIndex,
      mscLpEnetLtFrmCpyIndex }
::= { mscLpEnetLtFrmCpyTopTable 1 }

MscLpEnetLtFrmCpyTopEntry ::= SEQUENCE {
   mscLpEnetLtFrmCpyTData
      AsciiString }

mscLpEnetLtFrmCpyTData OBJECT-TYPE
   SYNTAX     AsciiString (SIZE (0..255))
   ACCESS     read-write
   STATUS     mandatory
   DESCRIPTION
     "This attribute is used to display and set attributes."
::= { mscLpEnetLtFrmCpyTopEntry 1 }


-- This component controls the emulator and hardware to ensure 
-- frames output from each will match in FrameCompare.

mscLpEnetLtPrtCfg OBJECT IDENTIFIER ::= { mscLpEnetLt 4 }



mscLpEnetLtPrtCfgRowStatusTable OBJECT-TYPE
   SYNTAX     SEQUENCE OF MscLpEnetLtPrtCfgRowStatusEntry
   ACCESS     not-accessible
   STATUS     mandatory
   DESCRIPTION
     "This entry controls the addition and deletion of 
      mscLpEnetLtPrtCfg components."
::= { mscLpEnetLtPrtCfg 1 }

mscLpEnetLtPrtCfgRowStatusEntry OBJECT-TYPE
   SYNTAX     MscLpEnetLtPrtCfgRowStatusEntry
   ACCESS     not-accessible
   STATUS     mandatory
   DESCRIPTION
     "A single entry in the table represents a single 
      mscLpEnetLtPrtCfg component."
   INDEX {
      mscLpIndex,
      mscLpEnetIndex,
      mscLpEnetLtIndex,
      mscLpEnetLtPrtCfgIndex }
::= { mscLpEnetLtPrtCfgRowStatusTable 1 }

MscLpEnetLtPrtCfgRowStatusEntry ::= SEQUENCE {
   mscLpEnetLtPrtCfgRowStatus
      RowStatus,
   mscLpEnetLtPrtCfgComponentName
      DisplayString,
   mscLpEnetLtPrtCfgStorageType
      StorageType,
   mscLpEnetLtPrtCfgIndex
      NonReplicated }

mscLpEnetLtPrtCfgRowStatus OBJECT-TYPE
   SYNTAX     RowStatus 
   ACCESS     read-only
   STATUS     mandatory
   DESCRIPTION
     "This variable is used as the basis for SNMP naming of
      mscLpEnetLtPrtCfg components.
      These components cannot be added nor deleted."
::= { mscLpEnetLtPrtCfgRowStatusEntry 1 }

mscLpEnetLtPrtCfgComponentName OBJECT-TYPE
   SYNTAX     DisplayString 
   ACCESS     read-only
   STATUS     mandatory
   DESCRIPTION
     "This variable provides the component's string name for
      use with the ASCII Console Interface"
::= { mscLpEnetLtPrtCfgRowStatusEntry 2 }

mscLpEnetLtPrtCfgStorageType OBJECT-TYPE
   SYNTAX     StorageType 
   ACCESS     read-only
   STATUS     mandatory
   DESCRIPTION
     "This variable represents the storage type value for the
      mscLpEnetLtPrtCfg tables."
::= { mscLpEnetLtPrtCfgRowStatusEntry 4 }

mscLpEnetLtPrtCfgIndex OBJECT-TYPE
   SYNTAX     NonReplicated 
   ACCESS     not-accessible
   STATUS     mandatory
   DESCRIPTION
     "This variable represents the index for the mscLpEnetLtPrtCfg tables."
::= { mscLpEnetLtPrtCfgRowStatusEntry 10 }

mscLpEnetLtPrtCfgTopTable OBJECT-TYPE
   SYNTAX     SEQUENCE OF MscLpEnetLtPrtCfgTopEntry
   ACCESS     not-accessible
   STATUS     mandatory
   DESCRIPTION
     "This group contains the operational data for the LanTest component 
      and its subcomponents."
::= { mscLpEnetLtPrtCfg 10 }

mscLpEnetLtPrtCfgTopEntry OBJECT-TYPE
   SYNTAX     MscLpEnetLtPrtCfgTopEntry
   ACCESS     not-accessible
   STATUS     mandatory
   DESCRIPTION
     "An entry in the mscLpEnetLtPrtCfgTopTable."
   INDEX {
      mscLpIndex,
      mscLpEnetIndex,
      mscLpEnetLtIndex,
      mscLpEnetLtPrtCfgIndex }
::= { mscLpEnetLtPrtCfgTopTable 1 }

MscLpEnetLtPrtCfgTopEntry ::= SEQUENCE {
   mscLpEnetLtPrtCfgTData
      AsciiString }

mscLpEnetLtPrtCfgTData OBJECT-TYPE
   SYNTAX     AsciiString (SIZE (0..255))
   ACCESS     read-write
   STATUS     mandatory
   DESCRIPTION
     "This attribute is used to display and set attributes."
::= { mscLpEnetLtPrtCfgTopEntry 1 }


-- LanTest Framebuild
-- This component controls the building of all frames built and sent by 
-- the LanTest component. Each component under FrameBuild builds 
-- a portion of a packet or frame.

mscLpEnetLtFb OBJECT IDENTIFIER ::= { mscLpEnetLt 5 }



mscLpEnetLtFbRowStatusTable OBJECT-TYPE
   SYNTAX     SEQUENCE OF MscLpEnetLtFbRowStatusEntry
   ACCESS     not-accessible
   STATUS     mandatory
   DESCRIPTION
     "This entry controls the addition and deletion of 
      mscLpEnetLtFb components."
::= { mscLpEnetLtFb 1 }

mscLpEnetLtFbRowStatusEntry OBJECT-TYPE
   SYNTAX     MscLpEnetLtFbRowStatusEntry
   ACCESS     not-accessible
   STATUS     mandatory
   DESCRIPTION
     "A single entry in the table represents a single 
      mscLpEnetLtFb component."
   INDEX {
      mscLpIndex,
      mscLpEnetIndex,
      mscLpEnetLtIndex,
      mscLpEnetLtFbIndex }
::= { mscLpEnetLtFbRowStatusTable 1 }

MscLpEnetLtFbRowStatusEntry ::= SEQUENCE {
   mscLpEnetLtFbRowStatus
      RowStatus,
   mscLpEnetLtFbComponentName
      DisplayString,
   mscLpEnetLtFbStorageType
      StorageType,
   mscLpEnetLtFbIndex
      NonReplicated }

mscLpEnetLtFbRowStatus OBJECT-TYPE
   SYNTAX     RowStatus 
   ACCESS     read-only
   STATUS     mandatory
   DESCRIPTION
     "This variable is used as the basis for SNMP naming of
      mscLpEnetLtFb components.
      These components cannot be added nor deleted."
::= { mscLpEnetLtFbRowStatusEntry 1 }

mscLpEnetLtFbComponentName OBJECT-TYPE
   SYNTAX     DisplayString 
   ACCESS     read-only
   STATUS     mandatory
   DESCRIPTION
     "This variable provides the component's string name for
      use with the ASCII Console Interface"
::= { mscLpEnetLtFbRowStatusEntry 2 }

mscLpEnetLtFbStorageType OBJECT-TYPE
   SYNTAX     StorageType 
   ACCESS     read-only
   STATUS     mandatory
   DESCRIPTION
     "This variable represents the storage type value for the
      mscLpEnetLtFb tables."
::= { mscLpEnetLtFbRowStatusEntry 4 }

mscLpEnetLtFbIndex OBJECT-TYPE
   SYNTAX     NonReplicated 
   ACCESS     not-accessible
   STATUS     mandatory
   DESCRIPTION
     "This variable represents the index for the mscLpEnetLtFb tables."
::= { mscLpEnetLtFbRowStatusEntry 10 }

mscLpEnetLtFbTopTable OBJECT-TYPE
   SYNTAX     SEQUENCE OF MscLpEnetLtFbTopEntry
   ACCESS     not-accessible
   STATUS     mandatory
   DESCRIPTION
     "This group contains the operational data for the LanTest component 
      and its subcomponents."
::= { mscLpEnetLtFb 20 }

mscLpEnetLtFbTopEntry OBJECT-TYPE
   SYNTAX     MscLpEnetLtFbTopEntry
   ACCESS     not-accessible
   STATUS     mandatory
   DESCRIPTION
     "An entry in the mscLpEnetLtFbTopTable."
   INDEX {
      mscLpIndex,
      mscLpEnetIndex,
      mscLpEnetLtIndex,
      mscLpEnetLtFbIndex }
::= { mscLpEnetLtFbTopTable 1 }

MscLpEnetLtFbTopEntry ::= SEQUENCE {
   mscLpEnetLtFbTData
      AsciiString }

mscLpEnetLtFbTData OBJECT-TYPE
   SYNTAX     AsciiString (SIZE (0..255))
   ACCESS     read-write
   STATUS     mandatory
   DESCRIPTION
     "This attribute is used to display and set attributes."
::= { mscLpEnetLtFbTopEntry 1 }


-- LanTest TransmitInfo
-- This component builds a transmit header which is attached to all 
-- frames transmitted on LAN interfaces.

mscLpEnetLtFbTxInfo OBJECT IDENTIFIER ::= { mscLpEnetLtFb 2 }



mscLpEnetLtFbTxInfoRowStatusTable OBJECT-TYPE
   SYNTAX     SEQUENCE OF MscLpEnetLtFbTxInfoRowStatusEntry
   ACCESS     not-accessible
   STATUS     mandatory
   DESCRIPTION
     "This entry controls the addition and deletion of 
      mscLpEnetLtFbTxInfo components."
::= { mscLpEnetLtFbTxInfo 1 }

mscLpEnetLtFbTxInfoRowStatusEntry OBJECT-TYPE
   SYNTAX     MscLpEnetLtFbTxInfoRowStatusEntry
   ACCESS     not-accessible
   STATUS     mandatory
   DESCRIPTION
     "A single entry in the table represents a single 
      mscLpEnetLtFbTxInfo component."
   INDEX {
      mscLpIndex,
      mscLpEnetIndex,
      mscLpEnetLtIndex,
      mscLpEnetLtFbIndex,
      mscLpEnetLtFbTxInfoIndex }
::= { mscLpEnetLtFbTxInfoRowStatusTable 1 }

MscLpEnetLtFbTxInfoRowStatusEntry ::= SEQUENCE {
   mscLpEnetLtFbTxInfoRowStatus
      RowStatus,
   mscLpEnetLtFbTxInfoComponentName
      DisplayString,
   mscLpEnetLtFbTxInfoStorageType
      StorageType,
   mscLpEnetLtFbTxInfoIndex
      NonReplicated }

mscLpEnetLtFbTxInfoRowStatus OBJECT-TYPE
   SYNTAX     RowStatus 
   ACCESS     read-only
   STATUS     mandatory
   DESCRIPTION
     "This variable is used as the basis for SNMP naming of
      mscLpEnetLtFbTxInfo components.
      These components cannot be added nor deleted."
::= { mscLpEnetLtFbTxInfoRowStatusEntry 1 }

mscLpEnetLtFbTxInfoComponentName OBJECT-TYPE
   SYNTAX     DisplayString 
   ACCESS     read-only
   STATUS     mandatory
   DESCRIPTION
     "This variable provides the component's string name for
      use with the ASCII Console Interface"
::= { mscLpEnetLtFbTxInfoRowStatusEntry 2 }

mscLpEnetLtFbTxInfoStorageType OBJECT-TYPE
   SYNTAX     StorageType 
   ACCESS     read-only
   STATUS     mandatory
   DESCRIPTION
     "This variable represents the storage type value for the
      mscLpEnetLtFbTxInfo tables."
::= { mscLpEnetLtFbTxInfoRowStatusEntry 4 }

mscLpEnetLtFbTxInfoIndex OBJECT-TYPE
   SYNTAX     NonReplicated 
   ACCESS     not-accessible
   STATUS     mandatory
   DESCRIPTION
     "This variable represents the index for the mscLpEnetLtFbTxInfo tables."
::= { mscLpEnetLtFbTxInfoRowStatusEntry 10 }

mscLpEnetLtFbTxInfoTopTable OBJECT-TYPE
   SYNTAX     SEQUENCE OF MscLpEnetLtFbTxInfoTopEntry
   ACCESS     not-accessible
   STATUS     mandatory
   DESCRIPTION
     "This group contains the operational data for the LanTest component 
      and its subcomponents."
::= { mscLpEnetLtFbTxInfo 10 }

mscLpEnetLtFbTxInfoTopEntry OBJECT-TYPE
   SYNTAX     MscLpEnetLtFbTxInfoTopEntry
   ACCESS     not-accessible
   STATUS     mandatory
   DESCRIPTION
     "An entry in the mscLpEnetLtFbTxInfoTopTable."
   INDEX {
      mscLpIndex,
      mscLpEnetIndex,
      mscLpEnetLtIndex,
      mscLpEnetLtFbIndex,
      mscLpEnetLtFbTxInfoIndex }
::= { mscLpEnetLtFbTxInfoTopTable 1 }

MscLpEnetLtFbTxInfoTopEntry ::= SEQUENCE {
   mscLpEnetLtFbTxInfoTData
      AsciiString }

mscLpEnetLtFbTxInfoTData OBJECT-TYPE
   SYNTAX     AsciiString (SIZE (0..255))
   ACCESS     read-write
   STATUS     mandatory
   DESCRIPTION
     "This attribute is used to display and set attributes."
::= { mscLpEnetLtFbTxInfoTopEntry 1 }


-- LanTest FddiMac
-- This component builds an FDDI MAC header which is attached to 
-- all FDDI frames.

mscLpEnetLtFbFddiMac OBJECT IDENTIFIER ::= { mscLpEnetLtFb 3 }



mscLpEnetLtFbFddiMacRowStatusTable OBJECT-TYPE
   SYNTAX     SEQUENCE OF MscLpEnetLtFbFddiMacRowStatusEntry
   ACCESS     not-accessible
   STATUS     mandatory
   DESCRIPTION
     "This entry controls the addition and deletion of 
      mscLpEnetLtFbFddiMac components."
::= { mscLpEnetLtFbFddiMac 1 }

mscLpEnetLtFbFddiMacRowStatusEntry OBJECT-TYPE
   SYNTAX     MscLpEnetLtFbFddiMacRowStatusEntry
   ACCESS     not-accessible
   STATUS     mandatory
   DESCRIPTION
     "A single entry in the table represents a single 
      mscLpEnetLtFbFddiMac component."
   INDEX {
      mscLpIndex,
      mscLpEnetIndex,
      mscLpEnetLtIndex,
      mscLpEnetLtFbIndex,
      mscLpEnetLtFbFddiMacIndex }
::= { mscLpEnetLtFbFddiMacRowStatusTable 1 }

MscLpEnetLtFbFddiMacRowStatusEntry ::= SEQUENCE {
   mscLpEnetLtFbFddiMacRowStatus
      RowStatus,
   mscLpEnetLtFbFddiMacComponentName
      DisplayString,
   mscLpEnetLtFbFddiMacStorageType
      StorageType,
   mscLpEnetLtFbFddiMacIndex
      NonReplicated }

mscLpEnetLtFbFddiMacRowStatus OBJECT-TYPE
   SYNTAX     RowStatus 
   ACCESS     read-only
   STATUS     mandatory
   DESCRIPTION
     "This variable is used as the basis for SNMP naming of
      mscLpEnetLtFbFddiMac components.
      These components cannot be added nor deleted."
::= { mscLpEnetLtFbFddiMacRowStatusEntry 1 }

mscLpEnetLtFbFddiMacComponentName OBJECT-TYPE
   SYNTAX     DisplayString 
   ACCESS     read-only
   STATUS     mandatory
   DESCRIPTION
     "This variable provides the component's string name for
      use with the ASCII Console Interface"
::= { mscLpEnetLtFbFddiMacRowStatusEntry 2 }

mscLpEnetLtFbFddiMacStorageType OBJECT-TYPE
   SYNTAX     StorageType 
   ACCESS     read-only
   STATUS     mandatory
   DESCRIPTION
     "This variable represents the storage type value for the
      mscLpEnetLtFbFddiMac tables."
::= { mscLpEnetLtFbFddiMacRowStatusEntry 4 }

mscLpEnetLtFbFddiMacIndex OBJECT-TYPE
   SYNTAX     NonReplicated 
   ACCESS     not-accessible
   STATUS     mandatory
   DESCRIPTION
     "This variable represents the index for the mscLpEnetLtFbFddiMac tables."
::= { mscLpEnetLtFbFddiMacRowStatusEntry 10 }

mscLpEnetLtFbFddiMacTopTable OBJECT-TYPE
   SYNTAX     SEQUENCE OF MscLpEnetLtFbFddiMacTopEntry
   ACCESS     not-accessible
   STATUS     mandatory
   DESCRIPTION
     "This group contains the operational data for the LanTest component 
      and its subcomponents."
::= { mscLpEnetLtFbFddiMac 10 }

mscLpEnetLtFbFddiMacTopEntry OBJECT-TYPE
   SYNTAX     MscLpEnetLtFbFddiMacTopEntry
   ACCESS     not-accessible
   STATUS     mandatory
   DESCRIPTION
     "An entry in the mscLpEnetLtFbFddiMacTopTable."
   INDEX {
      mscLpIndex,
      mscLpEnetIndex,
      mscLpEnetLtIndex,
      mscLpEnetLtFbIndex,
      mscLpEnetLtFbFddiMacIndex }
::= { mscLpEnetLtFbFddiMacTopTable 1 }

MscLpEnetLtFbFddiMacTopEntry ::= SEQUENCE {
   mscLpEnetLtFbFddiMacTData
      AsciiString }

mscLpEnetLtFbFddiMacTData OBJECT-TYPE
   SYNTAX     AsciiString (SIZE (0..255))
   ACCESS     read-write
   STATUS     mandatory
   DESCRIPTION
     "This attribute is used to display and set attributes."
::= { mscLpEnetLtFbFddiMacTopEntry 1 }


-- LanTest EthernetMac
-- This component builds an Ethernet MAC header which is attached 
-- to all Ethernet frames.

mscLpEnetLtFbMacEnet OBJECT IDENTIFIER ::= { mscLpEnetLtFb 4 }



mscLpEnetLtFbMacEnetRowStatusTable OBJECT-TYPE
   SYNTAX     SEQUENCE OF MscLpEnetLtFbMacEnetRowStatusEntry
   ACCESS     not-accessible
   STATUS     mandatory
   DESCRIPTION
     "This entry controls the addition and deletion of 
      mscLpEnetLtFbMacEnet components."
::= { mscLpEnetLtFbMacEnet 1 }

mscLpEnetLtFbMacEnetRowStatusEntry OBJECT-TYPE
   SYNTAX     MscLpEnetLtFbMacEnetRowStatusEntry
   ACCESS     not-accessible
   STATUS     mandatory
   DESCRIPTION
     "A single entry in the table represents a single 
      mscLpEnetLtFbMacEnet component."
   INDEX {
      mscLpIndex,
      mscLpEnetIndex,
      mscLpEnetLtIndex,
      mscLpEnetLtFbIndex,
      mscLpEnetLtFbMacEnetIndex }
::= { mscLpEnetLtFbMacEnetRowStatusTable 1 }

MscLpEnetLtFbMacEnetRowStatusEntry ::= SEQUENCE {
   mscLpEnetLtFbMacEnetRowStatus
      RowStatus,
   mscLpEnetLtFbMacEnetComponentName
      DisplayString,
   mscLpEnetLtFbMacEnetStorageType
      StorageType,
   mscLpEnetLtFbMacEnetIndex
      NonReplicated }

mscLpEnetLtFbMacEnetRowStatus OBJECT-TYPE
   SYNTAX     RowStatus 
   ACCESS     read-only
   STATUS     mandatory
   DESCRIPTION
     "This variable is used as the basis for SNMP naming of
      mscLpEnetLtFbMacEnet components.
      These components cannot be added nor deleted."
::= { mscLpEnetLtFbMacEnetRowStatusEntry 1 }

mscLpEnetLtFbMacEnetComponentName OBJECT-TYPE
   SYNTAX     DisplayString 
   ACCESS     read-only
   STATUS     mandatory
   DESCRIPTION
     "This variable provides the component's string name for
      use with the ASCII Console Interface"
::= { mscLpEnetLtFbMacEnetRowStatusEntry 2 }

mscLpEnetLtFbMacEnetStorageType OBJECT-TYPE
   SYNTAX     StorageType 
   ACCESS     read-only
   STATUS     mandatory
   DESCRIPTION
     "This variable represents the storage type value for the
      mscLpEnetLtFbMacEnet tables."
::= { mscLpEnetLtFbMacEnetRowStatusEntry 4 }

mscLpEnetLtFbMacEnetIndex OBJECT-TYPE
   SYNTAX     NonReplicated 
   ACCESS     not-accessible
   STATUS     mandatory
   DESCRIPTION
     "This variable represents the index for the mscLpEnetLtFbMacEnet tables."
::= { mscLpEnetLtFbMacEnetRowStatusEntry 10 }

mscLpEnetLtFbMacEnetTopTable OBJECT-TYPE
   SYNTAX     SEQUENCE OF MscLpEnetLtFbMacEnetTopEntry
   ACCESS     not-accessible
   STATUS     mandatory
   DESCRIPTION
     "This group contains the operational data for the LanTest component 
      and its subcomponents."
::= { mscLpEnetLtFbMacEnet 10 }

mscLpEnetLtFbMacEnetTopEntry OBJECT-TYPE
   SYNTAX     MscLpEnetLtFbMacEnetTopEntry
   ACCESS     not-accessible
   STATUS     mandatory
   DESCRIPTION
     "An entry in the mscLpEnetLtFbMacEnetTopTable."
   INDEX {
      mscLpIndex,
      mscLpEnetIndex,
      mscLpEnetLtIndex,
      mscLpEnetLtFbIndex,
      mscLpEnetLtFbMacEnetIndex }
::= { mscLpEnetLtFbMacEnetTopTable 1 }

MscLpEnetLtFbMacEnetTopEntry ::= SEQUENCE {
   mscLpEnetLtFbMacEnetTData
      AsciiString }

mscLpEnetLtFbMacEnetTData OBJECT-TYPE
   SYNTAX     AsciiString (SIZE (0..255))
   ACCESS     read-write
   STATUS     mandatory
   DESCRIPTION
     "This attribute is used to display and set attributes."
::= { mscLpEnetLtFbMacEnetTopEntry 1 }


-- LanTest TokenRingMac
-- This component builds a Token Ring MAC header which is attached 
-- to all Token Ring frames.

mscLpEnetLtFbMacTr OBJECT IDENTIFIER ::= { mscLpEnetLtFb 5 }



mscLpEnetLtFbMacTrRowStatusTable OBJECT-TYPE
   SYNTAX     SEQUENCE OF MscLpEnetLtFbMacTrRowStatusEntry
   ACCESS     not-accessible
   STATUS     mandatory
   DESCRIPTION
     "This entry controls the addition and deletion of 
      mscLpEnetLtFbMacTr components."
::= { mscLpEnetLtFbMacTr 1 }

mscLpEnetLtFbMacTrRowStatusEntry OBJECT-TYPE
   SYNTAX     MscLpEnetLtFbMacTrRowStatusEntry
   ACCESS     not-accessible
   STATUS     mandatory
   DESCRIPTION
     "A single entry in the table represents a single 
      mscLpEnetLtFbMacTr component."
   INDEX {
      mscLpIndex,
      mscLpEnetIndex,
      mscLpEnetLtIndex,
      mscLpEnetLtFbIndex,
      mscLpEnetLtFbMacTrIndex }
::= { mscLpEnetLtFbMacTrRowStatusTable 1 }

MscLpEnetLtFbMacTrRowStatusEntry ::= SEQUENCE {
   mscLpEnetLtFbMacTrRowStatus
      RowStatus,
   mscLpEnetLtFbMacTrComponentName
      DisplayString,
   mscLpEnetLtFbMacTrStorageType
      StorageType,
   mscLpEnetLtFbMacTrIndex
      NonReplicated }

mscLpEnetLtFbMacTrRowStatus OBJECT-TYPE
   SYNTAX     RowStatus 
   ACCESS     read-only
   STATUS     mandatory
   DESCRIPTION
     "This variable is used as the basis for SNMP naming of
      mscLpEnetLtFbMacTr components.
      These components cannot be added nor deleted."
::= { mscLpEnetLtFbMacTrRowStatusEntry 1 }

mscLpEnetLtFbMacTrComponentName OBJECT-TYPE
   SYNTAX     DisplayString 
   ACCESS     read-only
   STATUS     mandatory
   DESCRIPTION
     "This variable provides the component's string name for
      use with the ASCII Console Interface"
::= { mscLpEnetLtFbMacTrRowStatusEntry 2 }

mscLpEnetLtFbMacTrStorageType OBJECT-TYPE
   SYNTAX     StorageType 
   ACCESS     read-only
   STATUS     mandatory
   DESCRIPTION
     "This variable represents the storage type value for the
      mscLpEnetLtFbMacTr tables."
::= { mscLpEnetLtFbMacTrRowStatusEntry 4 }

mscLpEnetLtFbMacTrIndex OBJECT-TYPE
   SYNTAX     NonReplicated 
   ACCESS     not-accessible
   STATUS     mandatory
   DESCRIPTION
     "This variable represents the index for the mscLpEnetLtFbMacTr tables."
::= { mscLpEnetLtFbMacTrRowStatusEntry 10 }

mscLpEnetLtFbMacTrTopTable OBJECT-TYPE
   SYNTAX     SEQUENCE OF MscLpEnetLtFbMacTrTopEntry
   ACCESS     not-accessible
   STATUS     mandatory
   DESCRIPTION
     "This group contains the operational data for the LanTest component 
      and its subcomponents."
::= { mscLpEnetLtFbMacTr 10 }

mscLpEnetLtFbMacTrTopEntry OBJECT-TYPE
   SYNTAX     MscLpEnetLtFbMacTrTopEntry
   ACCESS     not-accessible
   STATUS     mandatory
   DESCRIPTION
     "An entry in the mscLpEnetLtFbMacTrTopTable."
   INDEX {
      mscLpIndex,
      mscLpEnetIndex,
      mscLpEnetLtIndex,
      mscLpEnetLtFbIndex,
      mscLpEnetLtFbMacTrIndex }
::= { mscLpEnetLtFbMacTrTopTable 1 }

MscLpEnetLtFbMacTrTopEntry ::= SEQUENCE {
   mscLpEnetLtFbMacTrTData
      AsciiString }

mscLpEnetLtFbMacTrTData OBJECT-TYPE
   SYNTAX     AsciiString (SIZE (0..255))
   ACCESS     read-write
   STATUS     mandatory
   DESCRIPTION
     "This attribute is used to display and set attributes."
::= { mscLpEnetLtFbMacTrTopEntry 1 }


-- This component adds a data field to frame.

mscLpEnetLtFbData OBJECT IDENTIFIER ::= { mscLpEnetLtFb 6 }



mscLpEnetLtFbDataRowStatusTable OBJECT-TYPE
   SYNTAX     SEQUENCE OF MscLpEnetLtFbDataRowStatusEntry
   ACCESS     not-accessible
   STATUS     mandatory
   DESCRIPTION
     "This entry controls the addition and deletion of 
      mscLpEnetLtFbData components."
::= { mscLpEnetLtFbData 1 }

mscLpEnetLtFbDataRowStatusEntry OBJECT-TYPE
   SYNTAX     MscLpEnetLtFbDataRowStatusEntry
   ACCESS     not-accessible
   STATUS     mandatory
   DESCRIPTION
     "A single entry in the table represents a single 
      mscLpEnetLtFbData component."
   INDEX {
      mscLpIndex,
      mscLpEnetIndex,
      mscLpEnetLtIndex,
      mscLpEnetLtFbIndex,
      mscLpEnetLtFbDataIndex }
::= { mscLpEnetLtFbDataRowStatusTable 1 }

MscLpEnetLtFbDataRowStatusEntry ::= SEQUENCE {
   mscLpEnetLtFbDataRowStatus
      RowStatus,
   mscLpEnetLtFbDataComponentName
      DisplayString,
   mscLpEnetLtFbDataStorageType
      StorageType,
   mscLpEnetLtFbDataIndex
      NonReplicated }

mscLpEnetLtFbDataRowStatus OBJECT-TYPE
   SYNTAX     RowStatus 
   ACCESS     read-only
   STATUS     mandatory
   DESCRIPTION
     "This variable is used as the basis for SNMP naming of
      mscLpEnetLtFbData components.
      These components cannot be added nor deleted."
::= { mscLpEnetLtFbDataRowStatusEntry 1 }

mscLpEnetLtFbDataComponentName OBJECT-TYPE
   SYNTAX     DisplayString 
   ACCESS     read-only
   STATUS     mandatory
   DESCRIPTION
     "This variable provides the component's string name for
      use with the ASCII Console Interface"
::= { mscLpEnetLtFbDataRowStatusEntry 2 }

mscLpEnetLtFbDataStorageType OBJECT-TYPE
   SYNTAX     StorageType 
   ACCESS     read-only
   STATUS     mandatory
   DESCRIPTION
     "This variable represents the storage type value for the
      mscLpEnetLtFbData tables."
::= { mscLpEnetLtFbDataRowStatusEntry 4 }

mscLpEnetLtFbDataIndex OBJECT-TYPE
   SYNTAX     NonReplicated 
   ACCESS     not-accessible
   STATUS     mandatory
   DESCRIPTION
     "This variable represents the index for the mscLpEnetLtFbData tables."
::= { mscLpEnetLtFbDataRowStatusEntry 10 }

mscLpEnetLtFbDataTopTable OBJECT-TYPE
   SYNTAX     SEQUENCE OF MscLpEnetLtFbDataTopEntry
   ACCESS     not-accessible
   STATUS     mandatory
   DESCRIPTION
     "This group contains the operational data for the LanTest component 
      and its subcomponents."
::= { mscLpEnetLtFbData 10 }

mscLpEnetLtFbDataTopEntry OBJECT-TYPE
   SYNTAX     MscLpEnetLtFbDataTopEntry
   ACCESS     not-accessible
   STATUS     mandatory
   DESCRIPTION
     "An entry in the mscLpEnetLtFbDataTopTable."
   INDEX {
      mscLpIndex,
      mscLpEnetIndex,
      mscLpEnetLtIndex,
      mscLpEnetLtFbIndex,
      mscLpEnetLtFbDataIndex }
::= { mscLpEnetLtFbDataTopTable 1 }

MscLpEnetLtFbDataTopEntry ::= SEQUENCE {
   mscLpEnetLtFbDataTData
      AsciiString }

mscLpEnetLtFbDataTData OBJECT-TYPE
   SYNTAX     AsciiString (SIZE (0..255))
   ACCESS     read-write
   STATUS     mandatory
   DESCRIPTION
     "This attribute is used to display and set attributes."
::= { mscLpEnetLtFbDataTopEntry 1 }


-- LanTest IpHeader
-- This component adds an IP header to a frame or packet.

mscLpEnetLtFbIpH OBJECT IDENTIFIER ::= { mscLpEnetLtFb 7 }



mscLpEnetLtFbIpHRowStatusTable OBJECT-TYPE
   SYNTAX     SEQUENCE OF MscLpEnetLtFbIpHRowStatusEntry
   ACCESS     not-accessible
   STATUS     mandatory
   DESCRIPTION
     "This entry controls the addition and deletion of 
      mscLpEnetLtFbIpH components."
::= { mscLpEnetLtFbIpH 1 }

mscLpEnetLtFbIpHRowStatusEntry OBJECT-TYPE
   SYNTAX     MscLpEnetLtFbIpHRowStatusEntry
   ACCESS     not-accessible
   STATUS     mandatory
   DESCRIPTION
     "A single entry in the table represents a single 
      mscLpEnetLtFbIpH component."
   INDEX {
      mscLpIndex,
      mscLpEnetIndex,
      mscLpEnetLtIndex,
      mscLpEnetLtFbIndex,
      mscLpEnetLtFbIpHIndex }
::= { mscLpEnetLtFbIpHRowStatusTable 1 }

MscLpEnetLtFbIpHRowStatusEntry ::= SEQUENCE {
   mscLpEnetLtFbIpHRowStatus
      RowStatus,
   mscLpEnetLtFbIpHComponentName
      DisplayString,
   mscLpEnetLtFbIpHStorageType
      StorageType,
   mscLpEnetLtFbIpHIndex
      NonReplicated }

mscLpEnetLtFbIpHRowStatus OBJECT-TYPE
   SYNTAX     RowStatus 
   ACCESS     read-only
   STATUS     mandatory
   DESCRIPTION
     "This variable is used as the basis for SNMP naming of
      mscLpEnetLtFbIpH components.
      These components cannot be added nor deleted."
::= { mscLpEnetLtFbIpHRowStatusEntry 1 }

mscLpEnetLtFbIpHComponentName OBJECT-TYPE
   SYNTAX     DisplayString 
   ACCESS     read-only
   STATUS     mandatory
   DESCRIPTION
     "This variable provides the component's string name for
      use with the ASCII Console Interface"
::= { mscLpEnetLtFbIpHRowStatusEntry 2 }

mscLpEnetLtFbIpHStorageType OBJECT-TYPE
   SYNTAX     StorageType 
   ACCESS     read-only
   STATUS     mandatory
   DESCRIPTION
     "This variable represents the storage type value for the
      mscLpEnetLtFbIpH tables."
::= { mscLpEnetLtFbIpHRowStatusEntry 4 }

mscLpEnetLtFbIpHIndex OBJECT-TYPE
   SYNTAX     NonReplicated 
   ACCESS     not-accessible
   STATUS     mandatory
   DESCRIPTION
     "This variable represents the index for the mscLpEnetLtFbIpH tables."
::= { mscLpEnetLtFbIpHRowStatusEntry 10 }

mscLpEnetLtFbIpHTopTable OBJECT-TYPE
   SYNTAX     SEQUENCE OF MscLpEnetLtFbIpHTopEntry
   ACCESS     not-accessible
   STATUS     mandatory
   DESCRIPTION
     "This group contains the operational data for the LanTest component 
      and its subcomponents."
::= { mscLpEnetLtFbIpH 10 }

mscLpEnetLtFbIpHTopEntry OBJECT-TYPE
   SYNTAX     MscLpEnetLtFbIpHTopEntry
   ACCESS     not-accessible
   STATUS     mandatory
   DESCRIPTION
     "An entry in the mscLpEnetLtFbIpHTopTable."
   INDEX {
      mscLpIndex,
      mscLpEnetIndex,
      mscLpEnetLtIndex,
      mscLpEnetLtFbIndex,
      mscLpEnetLtFbIpHIndex }
::= { mscLpEnetLtFbIpHTopTable 1 }

MscLpEnetLtFbIpHTopEntry ::= SEQUENCE {
   mscLpEnetLtFbIpHTData
      AsciiString }

mscLpEnetLtFbIpHTData OBJECT-TYPE
   SYNTAX     AsciiString (SIZE (0..255))
   ACCESS     read-write
   STATUS     mandatory
   DESCRIPTION
     "This attribute is used to display and set attributes."
::= { mscLpEnetLtFbIpHTopEntry 1 }


-- LanTest LlcHeader
-- This component adds an LLC 802.2 or Ethernet header to a frame 
-- or packet.

mscLpEnetLtFbLlch OBJECT IDENTIFIER ::= { mscLpEnetLtFb 8 }



mscLpEnetLtFbLlchRowStatusTable OBJECT-TYPE
   SYNTAX     SEQUENCE OF MscLpEnetLtFbLlchRowStatusEntry
   ACCESS     not-accessible
   STATUS     mandatory
   DESCRIPTION
     "This entry controls the addition and deletion of 
      mscLpEnetLtFbLlch components."
::= { mscLpEnetLtFbLlch 1 }

mscLpEnetLtFbLlchRowStatusEntry OBJECT-TYPE
   SYNTAX     MscLpEnetLtFbLlchRowStatusEntry
   ACCESS     not-accessible
   STATUS     mandatory
   DESCRIPTION
     "A single entry in the table represents a single 
      mscLpEnetLtFbLlch component."
   INDEX {
      mscLpIndex,
      mscLpEnetIndex,
      mscLpEnetLtIndex,
      mscLpEnetLtFbIndex,
      mscLpEnetLtFbLlchIndex }
::= { mscLpEnetLtFbLlchRowStatusTable 1 }

MscLpEnetLtFbLlchRowStatusEntry ::= SEQUENCE {
   mscLpEnetLtFbLlchRowStatus
      RowStatus,
   mscLpEnetLtFbLlchComponentName
      DisplayString,
   mscLpEnetLtFbLlchStorageType
      StorageType,
   mscLpEnetLtFbLlchIndex
      NonReplicated }

mscLpEnetLtFbLlchRowStatus OBJECT-TYPE
   SYNTAX     RowStatus 
   ACCESS     read-only
   STATUS     mandatory
   DESCRIPTION
     "This variable is used as the basis for SNMP naming of
      mscLpEnetLtFbLlch components.
      These components cannot be added nor deleted."
::= { mscLpEnetLtFbLlchRowStatusEntry 1 }

mscLpEnetLtFbLlchComponentName OBJECT-TYPE
   SYNTAX     DisplayString 
   ACCESS     read-only
   STATUS     mandatory
   DESCRIPTION
     "This variable provides the component's string name for
      use with the ASCII Console Interface"
::= { mscLpEnetLtFbLlchRowStatusEntry 2 }

mscLpEnetLtFbLlchStorageType OBJECT-TYPE
   SYNTAX     StorageType 
   ACCESS     read-only
   STATUS     mandatory
   DESCRIPTION
     "This variable represents the storage type value for the
      mscLpEnetLtFbLlch tables."
::= { mscLpEnetLtFbLlchRowStatusEntry 4 }

mscLpEnetLtFbLlchIndex OBJECT-TYPE
   SYNTAX     NonReplicated 
   ACCESS     not-accessible
   STATUS     mandatory
   DESCRIPTION
     "This variable represents the index for the mscLpEnetLtFbLlch tables."
::= { mscLpEnetLtFbLlchRowStatusEntry 10 }

mscLpEnetLtFbLlchTopTable OBJECT-TYPE
   SYNTAX     SEQUENCE OF MscLpEnetLtFbLlchTopEntry
   ACCESS     not-accessible
   STATUS     mandatory
   DESCRIPTION
     "This group contains the operational data for the LanTest component 
      and its subcomponents."
::= { mscLpEnetLtFbLlch 10 }

mscLpEnetLtFbLlchTopEntry OBJECT-TYPE
   SYNTAX     MscLpEnetLtFbLlchTopEntry
   ACCESS     not-accessible
   STATUS     mandatory
   DESCRIPTION
     "An entry in the mscLpEnetLtFbLlchTopTable."
   INDEX {
      mscLpIndex,
      mscLpEnetIndex,
      mscLpEnetLtIndex,
      mscLpEnetLtFbIndex,
      mscLpEnetLtFbLlchIndex }
::= { mscLpEnetLtFbLlchTopTable 1 }

MscLpEnetLtFbLlchTopEntry ::= SEQUENCE {
   mscLpEnetLtFbLlchTData
      AsciiString }

mscLpEnetLtFbLlchTData OBJECT-TYPE
   SYNTAX     AsciiString (SIZE (0..255))
   ACCESS     read-write
   STATUS     mandatory
   DESCRIPTION
     "This attribute is used to display and set attributes."
::= { mscLpEnetLtFbLlchTopEntry 1 }


-- This component adds an AppleTalk header to a frame or packet.

mscLpEnetLtFbAppleH OBJECT IDENTIFIER ::= { mscLpEnetLtFb 9 }



mscLpEnetLtFbAppleHRowStatusTable OBJECT-TYPE
   SYNTAX     SEQUENCE OF MscLpEnetLtFbAppleHRowStatusEntry
   ACCESS     not-accessible
   STATUS     mandatory
   DESCRIPTION
     "This entry controls the addition and deletion of 
      mscLpEnetLtFbAppleH components."
::= { mscLpEnetLtFbAppleH 1 }

mscLpEnetLtFbAppleHRowStatusEntry OBJECT-TYPE
   SYNTAX     MscLpEnetLtFbAppleHRowStatusEntry
   ACCESS     not-accessible
   STATUS     mandatory
   DESCRIPTION
     "A single entry in the table represents a single 
      mscLpEnetLtFbAppleH component."
   INDEX {
      mscLpIndex,
      mscLpEnetIndex,
      mscLpEnetLtIndex,
      mscLpEnetLtFbIndex,
      mscLpEnetLtFbAppleHIndex }
::= { mscLpEnetLtFbAppleHRowStatusTable 1 }

MscLpEnetLtFbAppleHRowStatusEntry ::= SEQUENCE {
   mscLpEnetLtFbAppleHRowStatus
      RowStatus,
   mscLpEnetLtFbAppleHComponentName
      DisplayString,
   mscLpEnetLtFbAppleHStorageType
      StorageType,
   mscLpEnetLtFbAppleHIndex
      NonReplicated }

mscLpEnetLtFbAppleHRowStatus OBJECT-TYPE
   SYNTAX     RowStatus 
   ACCESS     read-only
   STATUS     mandatory
   DESCRIPTION
     "This variable is used as the basis for SNMP naming of
      mscLpEnetLtFbAppleH components.
      These components cannot be added nor deleted."
::= { mscLpEnetLtFbAppleHRowStatusEntry 1 }

mscLpEnetLtFbAppleHComponentName OBJECT-TYPE
   SYNTAX     DisplayString 
   ACCESS     read-only
   STATUS     mandatory
   DESCRIPTION
     "This variable provides the component's string name for
      use with the ASCII Console Interface"
::= { mscLpEnetLtFbAppleHRowStatusEntry 2 }

mscLpEnetLtFbAppleHStorageType OBJECT-TYPE
   SYNTAX     StorageType 
   ACCESS     read-only
   STATUS     mandatory
   DESCRIPTION
     "This variable represents the storage type value for the
      mscLpEnetLtFbAppleH tables."
::= { mscLpEnetLtFbAppleHRowStatusEntry 4 }

mscLpEnetLtFbAppleHIndex OBJECT-TYPE
   SYNTAX     NonReplicated 
   ACCESS     not-accessible
   STATUS     mandatory
   DESCRIPTION
     "This variable represents the index for the mscLpEnetLtFbAppleH tables."
::= { mscLpEnetLtFbAppleHRowStatusEntry 10 }

mscLpEnetLtFbAppleHTopTable OBJECT-TYPE
   SYNTAX     SEQUENCE OF MscLpEnetLtFbAppleHTopEntry
   ACCESS     not-accessible
   STATUS     mandatory
   DESCRIPTION
     "This group contains the operational data for the LanTest component 
      and its subcomponents."
::= { mscLpEnetLtFbAppleH 10 }

mscLpEnetLtFbAppleHTopEntry OBJECT-TYPE
   SYNTAX     MscLpEnetLtFbAppleHTopEntry
   ACCESS     not-accessible
   STATUS     mandatory
   DESCRIPTION
     "An entry in the mscLpEnetLtFbAppleHTopTable."
   INDEX {
      mscLpIndex,
      mscLpEnetIndex,
      mscLpEnetLtIndex,
      mscLpEnetLtFbIndex,
      mscLpEnetLtFbAppleHIndex }
::= { mscLpEnetLtFbAppleHTopTable 1 }

MscLpEnetLtFbAppleHTopEntry ::= SEQUENCE {
   mscLpEnetLtFbAppleHTData
      AsciiString }

mscLpEnetLtFbAppleHTData OBJECT-TYPE
   SYNTAX     AsciiString (SIZE (0..255))
   ACCESS     read-write
   STATUS     mandatory
   DESCRIPTION
     "This attribute is used to display and set attributes."
::= { mscLpEnetLtFbAppleHTopEntry 1 }


-- This component adds an IPX header to a frame or packet.

mscLpEnetLtFbIpxH OBJECT IDENTIFIER ::= { mscLpEnetLtFb 10 }



mscLpEnetLtFbIpxHRowStatusTable OBJECT-TYPE
   SYNTAX     SEQUENCE OF MscLpEnetLtFbIpxHRowStatusEntry
   ACCESS     not-accessible
   STATUS     mandatory
   DESCRIPTION
     "This entry controls the addition and deletion of 
      mscLpEnetLtFbIpxH components."
::= { mscLpEnetLtFbIpxH 1 }

mscLpEnetLtFbIpxHRowStatusEntry OBJECT-TYPE
   SYNTAX     MscLpEnetLtFbIpxHRowStatusEntry
   ACCESS     not-accessible
   STATUS     mandatory
   DESCRIPTION
     "A single entry in the table represents a single 
      mscLpEnetLtFbIpxH component."
   INDEX {
      mscLpIndex,
      mscLpEnetIndex,
      mscLpEnetLtIndex,
      mscLpEnetLtFbIndex,
      mscLpEnetLtFbIpxHIndex }
::= { mscLpEnetLtFbIpxHRowStatusTable 1 }

MscLpEnetLtFbIpxHRowStatusEntry ::= SEQUENCE {
   mscLpEnetLtFbIpxHRowStatus
      RowStatus,
   mscLpEnetLtFbIpxHComponentName
      DisplayString,
   mscLpEnetLtFbIpxHStorageType
      StorageType,
   mscLpEnetLtFbIpxHIndex
      NonReplicated }

mscLpEnetLtFbIpxHRowStatus OBJECT-TYPE
   SYNTAX     RowStatus 
   ACCESS     read-only
   STATUS     mandatory
   DESCRIPTION
     "This variable is used as the basis for SNMP naming of
      mscLpEnetLtFbIpxH components.
      These components cannot be added nor deleted."
::= { mscLpEnetLtFbIpxHRowStatusEntry 1 }

mscLpEnetLtFbIpxHComponentName OBJECT-TYPE
   SYNTAX     DisplayString 
   ACCESS     read-only
   STATUS     mandatory
   DESCRIPTION
     "This variable provides the component's string name for
      use with the ASCII Console Interface"
::= { mscLpEnetLtFbIpxHRowStatusEntry 2 }

mscLpEnetLtFbIpxHStorageType OBJECT-TYPE
   SYNTAX     StorageType 
   ACCESS     read-only
   STATUS     mandatory
   DESCRIPTION
     "This variable represents the storage type value for the
      mscLpEnetLtFbIpxH tables."
::= { mscLpEnetLtFbIpxHRowStatusEntry 4 }

mscLpEnetLtFbIpxHIndex OBJECT-TYPE
   SYNTAX     NonReplicated 
   ACCESS     not-accessible
   STATUS     mandatory
   DESCRIPTION
     "This variable represents the index for the mscLpEnetLtFbIpxH tables."
::= { mscLpEnetLtFbIpxHRowStatusEntry 10 }

mscLpEnetLtFbIpxHTopTable OBJECT-TYPE
   SYNTAX     SEQUENCE OF MscLpEnetLtFbIpxHTopEntry
   ACCESS     not-accessible
   STATUS     mandatory
   DESCRIPTION
     "This group contains the operational data for the LanTest component 
      and its subcomponents."
::= { mscLpEnetLtFbIpxH 10 }

mscLpEnetLtFbIpxHTopEntry OBJECT-TYPE
   SYNTAX     MscLpEnetLtFbIpxHTopEntry
   ACCESS     not-accessible
   STATUS     mandatory
   DESCRIPTION
     "An entry in the mscLpEnetLtFbIpxHTopTable."
   INDEX {
      mscLpIndex,
      mscLpEnetIndex,
      mscLpEnetLtIndex,
      mscLpEnetLtFbIndex,
      mscLpEnetLtFbIpxHIndex }
::= { mscLpEnetLtFbIpxHTopTable 1 }

MscLpEnetLtFbIpxHTopEntry ::= SEQUENCE {
   mscLpEnetLtFbIpxHTData
      AsciiString }

mscLpEnetLtFbIpxHTData OBJECT-TYPE
   SYNTAX     AsciiString (SIZE (0..255))
   ACCESS     read-write
   STATUS     mandatory
   DESCRIPTION
     "This attribute is used to display and set attributes."
::= { mscLpEnetLtFbIpxHTopEntry 1 }


-- LanTest Control
-- This component controls the overall testing by telling the 
-- FrameBuild component to start and check the FrameCompare 
-- component to see if the test is complete.

mscLpEnetLtCntl OBJECT IDENTIFIER ::= { mscLpEnetLt 6 }



mscLpEnetLtCntlRowStatusTable OBJECT-TYPE
   SYNTAX     SEQUENCE OF MscLpEnetLtCntlRowStatusEntry
   ACCESS     not-accessible
   STATUS     mandatory
   DESCRIPTION
     "This entry controls the addition and deletion of 
      mscLpEnetLtCntl components."
::= { mscLpEnetLtCntl 1 }

mscLpEnetLtCntlRowStatusEntry OBJECT-TYPE
   SYNTAX     MscLpEnetLtCntlRowStatusEntry
   ACCESS     not-accessible
   STATUS     mandatory
   DESCRIPTION
     "A single entry in the table represents a single 
      mscLpEnetLtCntl component."
   INDEX {
      mscLpIndex,
      mscLpEnetIndex,
      mscLpEnetLtIndex,
      mscLpEnetLtCntlIndex }
::= { mscLpEnetLtCntlRowStatusTable 1 }

MscLpEnetLtCntlRowStatusEntry ::= SEQUENCE {
   mscLpEnetLtCntlRowStatus
      RowStatus,
   mscLpEnetLtCntlComponentName
      DisplayString,
   mscLpEnetLtCntlStorageType
      StorageType,
   mscLpEnetLtCntlIndex
      NonReplicated }

mscLpEnetLtCntlRowStatus OBJECT-TYPE
   SYNTAX     RowStatus 
   ACCESS     read-only
   STATUS     mandatory
   DESCRIPTION
     "This variable is used as the basis for SNMP naming of
      mscLpEnetLtCntl components.
      These components cannot be added nor deleted."
::= { mscLpEnetLtCntlRowStatusEntry 1 }

mscLpEnetLtCntlComponentName OBJECT-TYPE
   SYNTAX     DisplayString 
   ACCESS     read-only
   STATUS     mandatory
   DESCRIPTION
     "This variable provides the component's string name for
      use with the ASCII Console Interface"
::= { mscLpEnetLtCntlRowStatusEntry 2 }

mscLpEnetLtCntlStorageType OBJECT-TYPE
   SYNTAX     StorageType 
   ACCESS     read-only
   STATUS     mandatory
   DESCRIPTION
     "This variable represents the storage type value for the
      mscLpEnetLtCntl tables."
::= { mscLpEnetLtCntlRowStatusEntry 4 }

mscLpEnetLtCntlIndex OBJECT-TYPE
   SYNTAX     NonReplicated 
   ACCESS     not-accessible
   STATUS     mandatory
   DESCRIPTION
     "This variable represents the index for the mscLpEnetLtCntl tables."
::= { mscLpEnetLtCntlRowStatusEntry 10 }

mscLpEnetLtCntlTopTable OBJECT-TYPE
   SYNTAX     SEQUENCE OF MscLpEnetLtCntlTopEntry
   ACCESS     not-accessible
   STATUS     mandatory
   DESCRIPTION
     "This group contains the operational data for the LanTest component 
      and its subcomponents."
::= { mscLpEnetLtCntl 10 }

mscLpEnetLtCntlTopEntry OBJECT-TYPE
   SYNTAX     MscLpEnetLtCntlTopEntry
   ACCESS     not-accessible
   STATUS     mandatory
   DESCRIPTION
     "An entry in the mscLpEnetLtCntlTopTable."
   INDEX {
      mscLpIndex,
      mscLpEnetIndex,
      mscLpEnetLtIndex,
      mscLpEnetLtCntlIndex }
::= { mscLpEnetLtCntlTopTable 1 }

MscLpEnetLtCntlTopEntry ::= SEQUENCE {
   mscLpEnetLtCntlTData
      AsciiString }

mscLpEnetLtCntlTData OBJECT-TYPE
   SYNTAX     AsciiString (SIZE (0..255))
   ACCESS     read-write
   STATUS     mandatory
   DESCRIPTION
     "This attribute is used to display and set attributes."
::= { mscLpEnetLtCntlTopEntry 1 }


-- Lp/n Fddi/n Test, or
-- Lp/n Ethernet/n Test, or
-- Lp/n TokenRing/n Test, or
-- Lp/n IlsForwarder/n Test
-- The Test component is used to do StartUp port test for LAN cards.

mscLpEnetTest OBJECT IDENTIFIER ::= { mscLpEnet 5 }



mscLpEnetTestRowStatusTable OBJECT-TYPE
   SYNTAX     SEQUENCE OF MscLpEnetTestRowStatusEntry
   ACCESS     not-accessible
   STATUS     mandatory
   DESCRIPTION
     "This entry controls the addition and deletion of 
      mscLpEnetTest components."
::= { mscLpEnetTest 1 }

mscLpEnetTestRowStatusEntry OBJECT-TYPE
   SYNTAX     MscLpEnetTestRowStatusEntry
   ACCESS     not-accessible
   STATUS     mandatory
   DESCRIPTION
     "A single entry in the table represents a single 
      mscLpEnetTest component."
   INDEX {
      mscLpIndex,
      mscLpEnetIndex,
      mscLpEnetTestIndex }
::= { mscLpEnetTestRowStatusTable 1 }

MscLpEnetTestRowStatusEntry ::= SEQUENCE {
   mscLpEnetTestRowStatus
      RowStatus,
   mscLpEnetTestComponentName
      DisplayString,
   mscLpEnetTestStorageType
      StorageType,
   mscLpEnetTestIndex
      NonReplicated }

mscLpEnetTestRowStatus OBJECT-TYPE
   SYNTAX     RowStatus 
   ACCESS     read-only
   STATUS     mandatory
   DESCRIPTION
     "This variable is used as the basis for SNMP naming of
      mscLpEnetTest components.
      These components cannot be added nor deleted."
::= { mscLpEnetTestRowStatusEntry 1 }

mscLpEnetTestComponentName OBJECT-TYPE
   SYNTAX     DisplayString 
   ACCESS     read-only
   STATUS     mandatory
   DESCRIPTION
     "This variable provides the component's string name for
      use with the ASCII Console Interface"
::= { mscLpEnetTestRowStatusEntry 2 }

mscLpEnetTestStorageType OBJECT-TYPE
   SYNTAX     StorageType 
   ACCESS     read-only
   STATUS     mandatory
   DESCRIPTION
     "This variable represents the storage type value for the
      mscLpEnetTest tables."
::= { mscLpEnetTestRowStatusEntry 4 }

mscLpEnetTestIndex OBJECT-TYPE
   SYNTAX     NonReplicated 
   ACCESS     not-accessible
   STATUS     mandatory
   DESCRIPTION
     "This variable represents the index for the mscLpEnetTest tables."
::= { mscLpEnetTestRowStatusEntry 10 }

mscLpEnetTestPTOTable OBJECT-TYPE
   SYNTAX     SEQUENCE OF MscLpEnetTestPTOEntry
   ACCESS     not-accessible
   STATUS     mandatory
   DESCRIPTION
     "This group contains the operational data for the LanPortTest 
      component."
::= { mscLpEnetTest 10 }

mscLpEnetTestPTOEntry OBJECT-TYPE
   SYNTAX     MscLpEnetTestPTOEntry
   ACCESS     not-accessible
   STATUS     mandatory
   DESCRIPTION
     "An entry in the mscLpEnetTestPTOTable."
   INDEX {
      mscLpIndex,
      mscLpEnetIndex,
      mscLpEnetTestIndex }
::= { mscLpEnetTestPTOTable 1 }

MscLpEnetTestPTOEntry ::= SEQUENCE {
   mscLpEnetTestType
      INTEGER,
   mscLpEnetTestFrmSize
      Unsigned32,
   mscLpEnetTestDuration
      Unsigned32 }

mscLpEnetTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { mscLpEnetTestPTOEntry 1 }

mscLpEnetTestFrmSize OBJECT-TYPE
   SYNTAX     Unsigned32 (4..4096)
   ACCESS     read-write
   STATUS     mandatory
   DESCRIPTION
     "This attribute defines the size of the test data frames in number of 
      bytes."
   DEFVAL     { 1024 }
::= { mscLpEnetTestPTOEntry 2 }

mscLpEnetTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpEnetTestPTOEntry 3 }

mscLpEnetTestResultsTable OBJECT-TYPE
   SYNTAX     SEQUENCE OF MscLpEnetTestResultsEntry
   ACCESS     not-accessible
   STATUS     mandatory
   DESCRIPTION
     "This group contains all the statistics related attributes of the Test 
      component."
::= { mscLpEnetTest 11 }

mscLpEnetTestResultsEntry OBJECT-TYPE
   SYNTAX     MscLpEnetTestResultsEntry
   ACCESS     not-accessible
   STATUS     mandatory
   DESCRIPTION
     "An entry in the mscLpEnetTestResultsTable."
   INDEX {
      mscLpIndex,
      mscLpEnetIndex,
      mscLpEnetTestIndex }
::= { mscLpEnetTestResultsTable 1 }

MscLpEnetTestResultsEntry ::= SEQUENCE {
   mscLpEnetTestElapsedTime
      Counter32,
   mscLpEnetTestTimeRemaining
      Unsigned32,
   mscLpEnetTestCauseOfTermination
      INTEGER,
   mscLpEnetTestFrmTx
      PassportCounter64,
   mscLpEnetTestBitsTx
      PassportCounter64,
   mscLpEnetTestFrmRx
      PassportCounter64,
   mscLpEnetTestBitsRx
      PassportCounter64,
   mscLpEnetTestErroredFrmRx
      PassportCounter64 }

mscLpEnetTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpEnetTestResultsEntry 4 }

mscLpEnetTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpEnetTestResultsEntry 5 }

mscLpEnetTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { mscLpEnetTestResultsEntry 6 }

mscLpEnetTestFrmTx OBJECT-TYPE
   SYNTAX     PassportCounter64 
   ACCESS     read-only
   STATUS     mandatory
   DESCRIPTION
     "This attribute is the total number of frames sent during the test 
      period. This counter is not expected to reach its maximum value."
::= { mscLpEnetTestResultsEntry 7 }

mscLpEnetTestBitsTx OBJECT-TYPE
   SYNTAX     PassportCounter64 
   ACCESS     read-only
   STATUS     mandatory
   DESCRIPTION
     "This attribute is the total number of bits sent during the test period. 
      This counter is not expected to reach its maximum value."
::= { mscLpEnetTestResultsEntry 8 }

mscLpEnetTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpEnetTestResultsEntry 9 }

mscLpEnetTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { mscLpEnetTestResultsEntry 10 }

mscLpEnetTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { mscLpEnetTestResultsEntry 11 }


-- Lp/n Fddi/n
-- This component defines an instance of a FDDI station attached to a ring. 
-- One instance of this component must be created for each hardware 
-- interface. Each station must be provisioned prior to inserting into the 
-- ring.

mscLpFi OBJECT IDENTIFIER ::= { mscLp 4 }



mscLpFiRowStatusTable OBJECT-TYPE
   SYNTAX     SEQUENCE OF MscLpFiRowStatusEntry
   ACCESS     not-accessible
   STATUS     mandatory
   DESCRIPTION
     "This entry controls the addition and deletion of 
      mscLpFi components."
::= { mscLpFi 1 }

mscLpFiRowStatusEntry OBJECT-TYPE
   SYNTAX     MscLpFiRowStatusEntry
   ACCESS     not-accessible
   STATUS     mandatory
   DESCRIPTION
     "A single entry in the table represents a single 
      mscLpFi component."
   INDEX {
      mscLpIndex,
      mscLpFiIndex }
::= { mscLpFiRowStatusTable 1 }

MscLpFiRowStatusEntry ::= SEQUENCE {
   mscLpFiRowStatus
      RowStatus,
   mscLpFiComponentName
      DisplayString,
   mscLpFiStorageType
      StorageType,
   mscLpFiIndex
      Integer32 }

mscLpFiRowStatus OBJECT-TYPE
   SYNTAX     RowStatus 
   ACCESS     read-write
   STATUS     mandatory
   DESCRIPTION
     "This variable is used as the basis for SNMP naming of
      mscLpFi components.
      These components can be added and deleted."
::= { mscLpFiRowStatusEntry 1 }

mscLpFiComponentName OBJECT-TYPE
   SYNTAX     DisplayString 
   ACCESS     read-only
   STATUS     mandatory
   DESCRIPTION
     "This variable provides the component's string name for
      use with the ASCII Console Interface"
::= { mscLpFiRowStatusEntry 2 }

mscLpFiStorageType OBJECT-TYPE
   SYNTAX     StorageType 
   ACCESS     read-only
   STATUS     mandatory
   DESCRIPTION
     "This variable represents the storage type value for the
      mscLpFi tables."
::= { mscLpFiRowStatusEntry 4 }

mscLpFiIndex OBJECT-TYPE
   SYNTAX     Integer32 (0)
   ACCESS     not-accessible
   STATUS     mandatory
   DESCRIPTION
     "This variable represents the index for the mscLpFi tables."
::= { mscLpFiRowStatusEntry 10 }

mscLpFiCidDataTable OBJECT-TYPE
   SYNTAX     SEQUENCE OF MscLpFiCidDataEntry
   ACCESS     not-accessible
   STATUS     mandatory
   DESCRIPTION
     "This group contains the attribute for a component's Customer 
      Identifier (CID). Refer to the attribute description for a detailed 
      explanation of CIDs."
::= { mscLpFi 10 }

mscLpFiCidDataEntry OBJECT-TYPE
   SYNTAX     MscLpFiCidDataEntry
   ACCESS     not-accessible
   STATUS     mandatory
   DESCRIPTION
     "An entry in the mscLpFiCidDataTable."
   INDEX {
      mscLpIndex,
      mscLpFiIndex }
::= { mscLpFiCidDataTable 1 }

MscLpFiCidDataEntry ::= SEQUENCE {
   mscLpFiCustomerIdentifier
      Unsigned32 }

mscLpFiCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpFiCidDataEntry 1 }

mscLpFiIfEntryTable OBJECT-TYPE
   SYNTAX     SEQUENCE OF MscLpFiIfEntryEntry
   ACCESS     not-accessible
   STATUS     mandatory
   DESCRIPTION
     "This group contains the provisionable attributes for the ifEntry."
::= { mscLpFi 11 }

mscLpFiIfEntryEntry OBJECT-TYPE
   SYNTAX     MscLpFiIfEntryEntry
   ACCESS     not-accessible
   STATUS     mandatory
   DESCRIPTION
     "An entry in the mscLpFiIfEntryTable."
   INDEX {
      mscLpIndex,
      mscLpFiIndex }
::= { mscLpFiIfEntryTable 1 }

MscLpFiIfEntryEntry ::= SEQUENCE {
   mscLpFiIfAdminStatus
      INTEGER,
   mscLpFiIfIndex
      InterfaceIndex }

mscLpFiIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpFiIfEntryEntry 1 }

mscLpFiIfIndex OBJECT-TYPE
   SYNTAX     InterfaceIndex (1..65535)
   ACCESS     read-only
   STATUS     mandatory
   DESCRIPTION
     "This is the index for the IfEntry. Its value is automatically initialized 
      during the provisioning process."
::= { mscLpFiIfEntryEntry 2 }

mscLpFiSmtProvTable OBJECT-TYPE
   SYNTAX     SEQUENCE OF MscLpFiSmtProvEntry
   ACCESS     not-accessible
   STATUS     mandatory
   DESCRIPTION
     "This group contains the provisionable Station Management (SMT) 
      attributes of the Fddi component."
::= { mscLpFi 12 }

mscLpFiSmtProvEntry OBJECT-TYPE
   SYNTAX     MscLpFiSmtProvEntry
   ACCESS     not-accessible
   STATUS     mandatory
   DESCRIPTION
     "An entry in the mscLpFiSmtProvTable."
   INDEX {
      mscLpIndex,
      mscLpFiIndex }
::= { mscLpFiSmtProvTable 1 }

MscLpFiSmtProvEntry ::= SEQUENCE {
   mscLpFiUserData
      AsciiString,
   mscLpFiAcceptAa
      INTEGER,
   mscLpFiAcceptBb
      INTEGER,
   mscLpFiAcceptAs
      INTEGER,
   mscLpFiAcceptBs
      INTEGER,
   mscLpFiAcceptAm
      INTEGER,
   mscLpFiAcceptBm
      INTEGER,
   mscLpFiUseThruBa
      INTEGER,
   mscLpFiNeighborNotifyInterval
      Unsigned32,
   mscLpFiStatusReportPolicy
      INTEGER,
   mscLpFiTraceMaxExpirationTimer
      FddiTimeMilli,
   mscLpFiApplicationFramerName
      Link }

mscLpFiUserData OBJECT-TYPE
   SYNTAX     AsciiString (SIZE (0..32))
   ACCESS     read-write
   STATUS     mandatory
   DESCRIPTION
     "The user data field is used to identify the FDDI interface on the ring. 
      The user data contains a message with a maximum of 32 characters."
   DEFVAL     { '46444449'H }  -- "FDDI"
::= { mscLpFiSmtProvEntry 1 }

mscLpFiAcceptAa OBJECT-TYPE
   SYNTAX     INTEGER  {
                 enabled(1),
                 disabled(2) }
   ACCESS     read-write
   STATUS     mandatory
   DESCRIPTION
     "The acceptAa attribute defines the station type A to station type A 
      connection policy. If enabled, the connection will be accepted. If 
      disabled, the connection will be rejected."
   DEFVAL     { disabled }
::= { mscLpFiSmtProvEntry 2 }

mscLpFiAcceptBb OBJECT-TYPE
   SYNTAX     INTEGER  {
                 enabled(1),
                 disabled(2) }
   ACCESS     read-write
   STATUS     mandatory
   DESCRIPTION
     "The acceptBb attribute defines the station type B to station type B 
      connection policy. If enabled, the connection will be accepted. If 
      disabled, the connection will be rejected."
   DEFVAL     { disabled }
::= { mscLpFiSmtProvEntry 3 }

mscLpFiAcceptAs OBJECT-TYPE
   SYNTAX     INTEGER  {
                 enabled(1),
                 disabled(2) }
   ACCESS     read-write
   STATUS     mandatory
   DESCRIPTION
     "The acceptAs attribute defines the station type A to station type S 
      connection policy. If enabled, the connection will be accepted. If 
      disabled, the connection will be rejected."
   DEFVAL     { disabled }
::= { mscLpFiSmtProvEntry 4 }

mscLpFiAcceptBs OBJECT-TYPE
   SYNTAX     INTEGER  {
                 enabled(1),
                 disabled(2) }
   ACCESS     read-write
   STATUS     mandatory
   DESCRIPTION
     "The acceptBs attribute defines the station type B to station type S 
      connection policy. If enabled, the connection will be accepted. If 
      disabled, the connection will be rejected."
   DEFVAL     { disabled }
::= { mscLpFiSmtProvEntry 5 }

mscLpFiAcceptAm OBJECT-TYPE
   SYNTAX     INTEGER  {
                 enabled(1),
                 disabled(2) }
   ACCESS     read-write
   STATUS     mandatory
   DESCRIPTION
     "The acceptAm attribute defines the station type A to station type M 
      connection policy. If enabled, the connection will be accepted. If 
      disabled, the connection will be rejected."
   DEFVAL     { enabled }
::= { mscLpFiSmtProvEntry 6 }

mscLpFiAcceptBm OBJECT-TYPE
   SYNTAX     INTEGER  {
                 enabled(1),
                 disabled(2) }
   ACCESS     read-write
   STATUS     mandatory
   DESCRIPTION
     "The acceptBm attribute defines the station type B to station type M 
      connection policy. If enabled, the connection will be accepted. If 
      disabled, the connection will be rejected."
   DEFVAL     { enabled }
::= { mscLpFiSmtProvEntry 7 }

mscLpFiUseThruBa OBJECT-TYPE
   SYNTAX     INTEGER  {
                 enabled(1),
                 disabled(2) }
   ACCESS     read-write
   STATUS     mandatory
   DESCRIPTION
     "The useThruBa attribute is used to configure the requested path of the 
      associated station. If enabled, only the secondary preferred path is 
      permitted. If disabled, only the primary preferred path is permitted."
   DEFVAL     { disabled }
::= { mscLpFiSmtProvEntry 8 }

mscLpFiNeighborNotifyInterval OBJECT-TYPE
   SYNTAX     Unsigned32 (2..30)
   ACCESS     read-write
   STATUS     mandatory
   DESCRIPTION
     "The neighborNotifyInterval attribute contains the amount of time, 
      expressed in seconds, between neighbor notification frames."
   DEFVAL     { 30 }
::= { mscLpFiSmtProvEntry 10 }

mscLpFiStatusReportPolicy OBJECT-TYPE
   SYNTAX     INTEGER  {
                 true(1),
                 false(2) }
   ACCESS     read-write
   STATUS     mandatory
   DESCRIPTION
     "The statusReportPolicy attribute indicates whether or not the station will 
      generate status reporting frames for its implemented events and 
      conditions. If true, the station will generate the status frames. If false, 
      the station will not generate the status frames."
   DEFVAL     { true }
::= { mscLpFiSmtProvEntry 11 }

mscLpFiTraceMaxExpirationTimer OBJECT-TYPE
   SYNTAX     FddiTimeMilli (0..1000000)
   ACCESS     read-write
   STATUS     mandatory
   DESCRIPTION
     "The traceMaxExpirationTimer attribute is used to configure the 
      maximum propagation time, expressed in milliseconds, for a trace on a 
      FDDI topology. This value places a lower bound on the detection time 
      for an unrecovered ring."
   DEFVAL     { 7000 }
::= { mscLpFiSmtProvEntry 12 }

mscLpFiApplicationFramerName OBJECT-TYPE
   SYNTAX     Link 
   ACCESS     read-write
   STATUS     mandatory
   DESCRIPTION
     "This attribute contains the component name of a Framer which is 
      associated with the Fddi component. This defines which 
      LanApplication/n Framer will be using this Fddi interface."
::= { mscLpFiSmtProvEntry 13 }

mscLpFiMacProvTable OBJECT-TYPE
   SYNTAX     SEQUENCE OF MscLpFiMacProvEntry
   ACCESS     not-accessible
   STATUS     mandatory
   DESCRIPTION
     "This group contains the provisionable MAC attributes of the Fddi 
      component."
::= { mscLpFi 13 }

mscLpFiMacProvEntry OBJECT-TYPE
   SYNTAX     MscLpFiMacProvEntry
   ACCESS     not-accessible
   STATUS     mandatory
   DESCRIPTION
     "An entry in the mscLpFiMacProvTable."
   INDEX {
      mscLpIndex,
      mscLpFiIndex }
::= { mscLpFiMacProvTable 1 }

MscLpFiMacProvEntry ::= SEQUENCE {
   mscLpFiTokenRequestTimer
      FddiTimeNano,
   mscLpFiTokenMaxTimer
      FddiTimeNano,
   mscLpFiValidTransmissionTimer
      FddiTimeNano }

mscLpFiTokenRequestTimer OBJECT-TYPE
   SYNTAX     FddiTimeNano (20480..1340000000)
   ACCESS     read-write
   STATUS     mandatory
   DESCRIPTION
     "The tokenRequestTimer value contains the token request value assigned 
      to the associated medium access controller (MAC).
      
      Warning:
      Changes to this attribute can have adverse effects on the performance of 
      the FDDI ring. Therefore it is recommended that this parameter only be 
      modified by personnel with a thorough understanding of the 
      consequences that may result from changes to this attribute."
   DEFVAL     { 165290000 }
::= { mscLpFiMacProvEntry 1 }

mscLpFiTokenMaxTimer OBJECT-TYPE
   SYNTAX     FddiTimeNano (40960..1342200000)
   ACCESS     read-write
   STATUS     mandatory
   DESCRIPTION
     "The tokenMaxTimer value is the maximum timer value the negotiated 
      token rotation time may assume.
      
      Warning:
      Changes to this attribute can have adverse effects on the performance of 
      the FDDI ring. Therefore it is recommended that this parameter only be 
      modified by personnel with a thorough understanding of the 
      consequences that may result from changes to this attribute."
   DEFVAL     { 167770000 }
::= { mscLpFiMacProvEntry 2 }

mscLpFiValidTransmissionTimer OBJECT-TYPE
   SYNTAX     FddiTimeNano (40960..1342200000)
   ACCESS     read-write
   STATUS     mandatory
   DESCRIPTION
     "The validTransmissionTimer (Tvx) value specifies the amount of time 
      required for a valid transmission. The station must receive a valid 
      transmission once every Tvx. 
      
      Warning:
      Changes to this attribute can have adverse effects on the performance of 
      the FDDI ring. Therefore it is recommended that this parameter only be 
      modified by personnel with a thorough understanding of the 
      consequences that may result from changes to this attribute."
   DEFVAL     { 2621400 }
::= { mscLpFiMacProvEntry 3 }

mscLpFiAdminInfoTable OBJECT-TYPE
   SYNTAX     SEQUENCE OF MscLpFiAdminInfoEntry
   ACCESS     not-accessible
   STATUS     mandatory
   DESCRIPTION
     "This group contains the attributes pertaining to the vendor of the 
      equipment."
::= { mscLpFi 14 }

mscLpFiAdminInfoEntry OBJECT-TYPE
   SYNTAX     MscLpFiAdminInfoEntry
   ACCESS     not-accessible
   STATUS     mandatory
   DESCRIPTION
     "An entry in the mscLpFiAdminInfoTable."
   INDEX {
      mscLpIndex,
      mscLpFiIndex }
::= { mscLpFiAdminInfoTable 1 }

MscLpFiAdminInfoEntry ::= SEQUENCE {
   mscLpFiVendor
      AsciiString,
   mscLpFiCommentText
      AsciiString }

mscLpFiVendor OBJECT-TYPE
   SYNTAX     AsciiString (SIZE (0..20))
   ACCESS     read-write
   STATUS     mandatory
   DESCRIPTION
     "This is the name of the vendor supplying the facility."
::= { mscLpFiAdminInfoEntry 1 }

mscLpFiCommentText OBJECT-TYPE
   SYNTAX     AsciiString (SIZE (0..60))
   ACCESS     read-write
   STATUS     mandatory
   DESCRIPTION
     "Any miscellaneous text about the facility."
::= { mscLpFiAdminInfoEntry 2 }

mscLpFiStateTable OBJECT-TYPE
   SYNTAX     SEQUENCE OF MscLpFiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpFi 16 }

mscLpFiStateEntry OBJECT-TYPE
   SYNTAX     MscLpFiStateEntry
   ACCESS     not-accessible
   STATUS     mandatory
   DESCRIPTION
     "An entry in the mscLpFiStateTable."
   INDEX {
      mscLpIndex,
      mscLpFiIndex }
::= { mscLpFiStateTable 1 }

MscLpFiStateEntry ::= SEQUENCE {
   mscLpFiAdminState
      INTEGER,
   mscLpFiOperationalState
      INTEGER,
   mscLpFiUsageState
      INTEGER }

mscLpFiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpFiStateEntry 1 }

mscLpFiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpFiStateEntry 2 }

mscLpFiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpFiStateEntry 3 }

mscLpFiOperStatusTable OBJECT-TYPE
   SYNTAX     SEQUENCE OF MscLpFiOperStatusEntry
   ACCESS     not-accessible
   STATUS     mandatory
   DESCRIPTION
     "This group includes the Operational Status attribute. This attribute 
      defines the current operational state of this component."
::= { mscLpFi 17 }

mscLpFiOperStatusEntry OBJECT-TYPE
   SYNTAX     MscLpFiOperStatusEntry
   ACCESS     not-accessible
   STATUS     mandatory
   DESCRIPTION
     "An entry in the mscLpFiOperStatusTable."
   INDEX {
      mscLpIndex,
      mscLpFiIndex }
::= { mscLpFiOperStatusTable 1 }

MscLpFiOperStatusEntry ::= SEQUENCE {
   mscLpFiSnmpOperStatus
      INTEGER }

mscLpFiSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpFiOperStatusEntry 1 }

mscLpFiSmtOperTable OBJECT-TYPE
   SYNTAX     SEQUENCE OF MscLpFiSmtOperEntry
   ACCESS     not-accessible
   STATUS     mandatory
   DESCRIPTION
     "This group contains the operational station management (SMT) 
      attributes of the Fddi component."
::= { mscLpFi 18 }

mscLpFiSmtOperEntry OBJECT-TYPE
   SYNTAX     MscLpFiSmtOperEntry
   ACCESS     not-accessible
   STATUS     mandatory
   DESCRIPTION
     "An entry in the mscLpFiSmtOperTable."
   INDEX {
      mscLpIndex,
      mscLpFiIndex }
::= { mscLpFiSmtOperTable 1 }

MscLpFiSmtOperEntry ::= SEQUENCE {
   mscLpFiVersion
      AsciiString,
   mscLpFiBypassPresent
      INTEGER,
   mscLpFiEcmState
      INTEGER,
   mscLpFiCfState
      INTEGER }

mscLpFiVersion OBJECT-TYPE
   SYNTAX     AsciiString (SIZE (0..32))
   ACCESS     read-only
   STATUS     mandatory
   DESCRIPTION
     "The version attribute contains a copy of the currently supported version 
      numbers of the management information base (MIB) and the station 
      management (SMT)."
::= { mscLpFiSmtOperEntry 1 }

mscLpFiBypassPresent OBJECT-TYPE
   SYNTAX     INTEGER  {
                 true(1),
                 false(2) }
   ACCESS     read-only
   STATUS     mandatory
   DESCRIPTION
     "The bypassPresent attribute indicates whether the optical bypass switch 
      is present on its AB port pair. If true, the optical bypass switch is 
      present. If false, it is not present."
::= { mscLpFiSmtOperEntry 14 }

mscLpFiEcmState OBJECT-TYPE
   SYNTAX     INTEGER  {
                 out(1),
                 in(2),
                 trace(3),
                 leave(4),
                 pathTest(5),
                 insert(6),
                 check(7),
                 deinsert(8) }
   ACCESS     read-only
   STATUS     mandatory
   DESCRIPTION
     "The ecmState, Entity Coordination Manager (ECM), state indicates the 
      current state of the ECM state machine."
::= { mscLpFiSmtOperEntry 15 }

mscLpFiCfState OBJECT-TYPE
   SYNTAX     INTEGER  {
                 isolated(1),
                 localA(2),
                 localB(3),
                 localAB(4),
                 localS(5),
                 wrapA(6),
                 wrapB(7),
                 wrapAB(8),
                 wrapS(9),
                 cWrapA(10),
                 cWrapB(11),
                 cWrapS(12),
                 thru(13) }
   ACCESS     read-only
   STATUS     mandatory
   DESCRIPTION
     "The cfState attribute indicates the current state of the configuration 
      management (CFM) state machine."
::= { mscLpFiSmtOperEntry 16 }

mscLpFiMacOperTable OBJECT-TYPE
   SYNTAX     SEQUENCE OF MscLpFiMacOperEntry
   ACCESS     not-accessible
   STATUS     mandatory
   DESCRIPTION
     "This group contains the operational Medium Access Controller (MAC) 
      attributes of the of the Fddi component."
::= { mscLpFi 19 }

mscLpFiMacOperEntry OBJECT-TYPE
   SYNTAX     MscLpFiMacOperEntry
   ACCESS     not-accessible
   STATUS     mandatory
   DESCRIPTION
     "An entry in the mscLpFiMacOperTable."
   INDEX {
      mscLpIndex,
      mscLpFiIndex }
::= { mscLpFiMacOperTable 1 }

MscLpFiMacOperEntry ::= SEQUENCE {
   mscLpFiRingLatency
      Gauge32,
   mscLpFiMacAddress
      FddiMACLongAddressType,
   mscLpFiUpstreamNeighbor
      FddiMACLongAddressType,
   mscLpFiDownstreamNeighbor
      FddiMACLongAddressType,
   mscLpFiOldUpstreamNeighbor
      FddiMACLongAddressType,
   mscLpFiOldDownstreamNeighbor
      FddiMACLongAddressType,
   mscLpFiDupAddressTest
      INTEGER,
   mscLpFiTokenNegotiatedTimer
      FddiTimeNano,
   mscLpFiFrameCounts
      Counter32,
   mscLpFiCopiedCounts
      Counter32,
   mscLpFiTransmitCounts
      Counter32,
   mscLpFiErrorCounts
      Counter32,
   mscLpFiLostCounts
      Counter32,
   mscLpFiRmtState
      INTEGER,
   mscLpFiFrameErrorFlag
      INTEGER }

mscLpFiRingLatency OBJECT-TYPE
   SYNTAX     Gauge32 (1280..1342000000)
   ACCESS     read-only
   STATUS     mandatory
   DESCRIPTION
     "The ringLatency attribute contains the measured ring latency of the ring 
      the station is attached to."
::= { mscLpFiMacOperEntry 1 }

mscLpFiMacAddress OBJECT-TYPE
   SYNTAX     FddiMACLongAddressType (SIZE (6))
   ACCESS     read-only
   STATUS     mandatory
   DESCRIPTION
     "The medium access controller (MAC) address is an address that is 
      recognized by only one station on the attached ring. The value of this 
      attribute is assigned by the system. This attribute is displayed in 
      canonical format. The non-canonical version of this address is indicated 
      in ncMacAddress."
::= { mscLpFiMacOperEntry 10 }

mscLpFiUpstreamNeighbor OBJECT-TYPE
   SYNTAX     FddiMACLongAddressType (SIZE (6))
   ACCESS     read-only
   STATUS     mandatory
   DESCRIPTION
     "The upstreamNeighbor attribute contains the MAC address associated 
      with the upstream neighbor station on the ring. This attribute is 
      displayed in canonical format. The non-canonical version of this address 
      is indicated in ncUpstreamNeighbor."
::= { mscLpFiMacOperEntry 11 }

mscLpFiDownstreamNeighbor OBJECT-TYPE
   SYNTAX     FddiMACLongAddressType (SIZE (6))
   ACCESS     read-only
   STATUS     mandatory
   DESCRIPTION
     "The downstreamNeighbor attribute contains the MAC address 
      associated with the downstream station on the ring. This attribute is 
      displayed in canonical format. The non-canonical version of this address 
      is indicated in ncDownstreamNeighbor."
::= { mscLpFiMacOperEntry 12 }

mscLpFiOldUpstreamNeighbor OBJECT-TYPE
   SYNTAX     FddiMACLongAddressType (SIZE (6))
   ACCESS     read-only
   STATUS     mandatory
   DESCRIPTION
     "The oldUpstreamNeighbor attribute contains the previous value of the 
      MAC address associated with the upstream station on the ring. This 
      attribute is displayed in canonical format. The non-canonical version of 
      this address is indicated in ncOldUpstreamNeighbor."
::= { mscLpFiMacOperEntry 13 }

mscLpFiOldDownstreamNeighbor OBJECT-TYPE
   SYNTAX     FddiMACLongAddressType (SIZE (6))
   ACCESS     read-only
   STATUS     mandatory
   DESCRIPTION
     "The oldDownstreamNeighbor attribute contains the previous value of 
      the MAC address associated with the downstream station on the ring. 
      This attribute is displayed in canonical format. The non-canonical 
      version of this address is indicated in ncOldDownstreamNeighbor."
::= { mscLpFiMacOperEntry 14 }

mscLpFiDupAddressTest OBJECT-TYPE
   SYNTAX     INTEGER  {
                 notDone(1),
                 pass(2),
                 fail(3) }
   ACCESS     read-only
   STATUS     mandatory
   DESCRIPTION
     "The dupAddressTest attribute indicates the condition results of the 
      duplicate address test. If notDone, the test has not been executed. If 
      pass, the test has successfully executed. If fail, the test has failed."
::= { mscLpFiMacOperEntry 15 }

mscLpFiTokenNegotiatedTimer OBJECT-TYPE
   SYNTAX     FddiTimeNano (80..1340000000)
   ACCESS     read-only
   STATUS     mandatory
   DESCRIPTION
     "The tokenNegotiatedTimer specifies the negotiated token rotation time."
   DEFVAL     { 167772000 }
::= { mscLpFiMacOperEntry 18 }

mscLpFiFrameCounts OBJECT-TYPE
   SYNTAX     Counter32 
   ACCESS     read-only
   STATUS     mandatory
   DESCRIPTION
     "The frameCounts attribute contains the number of frames that have been 
      received by the station. This counter will wrap around after it reaches its 
      maximum value."
::= { mscLpFiMacOperEntry 19 }

mscLpFiCopiedCounts OBJECT-TYPE
   SYNTAX     Counter32 
   ACCESS     read-only
   STATUS     mandatory
   DESCRIPTION
     "The copiedCounts attribute contains the number of frames successfully 
      copied into this station's receive buffers, not including MAC control 
      frames. This counter will wrap around after it reaches its maximum 
      value."
::= { mscLpFiMacOperEntry 20 }

mscLpFiTransmitCounts OBJECT-TYPE
   SYNTAX     Counter32 
   ACCESS     read-only
   STATUS     mandatory
   DESCRIPTION
     "The transmitCounts attribute contains the number of frames transmitted 
      by this station, not including MAC control frames. This counter will 
      wrap around after it reaches its maximum value."
::= { mscLpFiMacOperEntry 21 }

mscLpFiErrorCounts OBJECT-TYPE
   SYNTAX     Counter32 
   ACCESS     read-only
   STATUS     mandatory
   DESCRIPTION
     "The errorCounts attribute contains the number of error frames first 
      detected by this station. This counter will wrap around after it reaches its 
      maximum value."
::= { mscLpFiMacOperEntry 22 }

mscLpFiLostCounts OBJECT-TYPE
   SYNTAX     Counter32 
   ACCESS     read-only
   STATUS     mandatory
   DESCRIPTION
     "The lostCounts attribute contains the number of instances that the station 
      has detected a format error during frame reception such that the frame 
      was stripped. This counter will wrap around after it reaches its 
      maximum value."
::= { mscLpFiMacOperEntry 23 }

mscLpFiRmtState OBJECT-TYPE
   SYNTAX     INTEGER  {
                 isolated(1),
                 nonOp(2),
                 ringOp(3),
                 detect(4),
                 nonOpDup(5),
                 ringOpDup(6),
                 directed(7),
                 trace(8) }
   ACCESS     read-only
   STATUS     mandatory
   DESCRIPTION
     "The rmtState, ring management (RMT), state indicates the current state 
      of the RMT state machine."
::= { mscLpFiMacOperEntry 25 }

mscLpFiFrameErrorFlag OBJECT-TYPE
   SYNTAX     INTEGER  {
                 true(1),
                 false(2) }
   ACCESS     read-only
   STATUS     mandatory
   DESCRIPTION
     "The frameErrorFlag attribute indicates the MAC frame error condition 
      status. If true, a MAC frame error is present. If false, a MAC frame 
      error condition is not present."
::= { mscLpFiMacOperEntry 28 }

mscLpFiMacCOperTable OBJECT-TYPE
   SYNTAX     SEQUENCE OF MscLpFiMacCOperEntry
   ACCESS     not-accessible
   STATUS     mandatory
   DESCRIPTION
     "This group contains the operational attributes of the Medium Access 
      Controller (MAC) Counters Table of the Fddi component."
::= { mscLpFi 20 }

mscLpFiMacCOperEntry OBJECT-TYPE
   SYNTAX     MscLpFiMacCOperEntry
   ACCESS     not-accessible
   STATUS     mandatory
   DESCRIPTION
     "An entry in the mscLpFiMacCOperTable."
   INDEX {
      mscLpIndex,
      mscLpFiIndex }
::= { mscLpFiMacCOperTable 1 }

MscLpFiMacCOperEntry ::= SEQUENCE {
   mscLpFiTokenCounts
      Counter32,
   mscLpFiTvxExpiredCounts
      Counter32,
   mscLpFiNotCopiedCounts
      Counter32,
   mscLpFiLateCounts
      Counter32,
   mscLpFiRingOpCounts
      Counter32 }

mscLpFiTokenCounts OBJECT-TYPE
   SYNTAX     Counter32 
   ACCESS     read-only
   STATUS     mandatory
   DESCRIPTION
     "The tokenCounts attribute contains the number of times the station has 
      received a token. This counter will wrap around after it reaches its 
      maximum value."
::= { mscLpFiMacCOperEntry 1 }

mscLpFiTvxExpiredCounts OBJECT-TYPE
   SYNTAX     Counter32 
   ACCESS     read-only
   STATUS     mandatory
   DESCRIPTION
     "The tvxExpiredCounts, Transmission Valid eXpired (TVX), attribute 
      contains the number of times that TVX timer has expired. This counter 
      may increment as stations go on and off the ring. A rapidly increasing 
      value may indicate a problem. This counter will wrap around after it 
      reaches its maximum value."
::= { mscLpFiMacCOperEntry 2 }

mscLpFiNotCopiedCounts OBJECT-TYPE
   SYNTAX     Counter32 
   ACCESS     read-only
   STATUS     mandatory
   DESCRIPTION
     "The notCopiedCounts attribute contains the number of times that the 
      station has detected a frame addressed to itself but did not copy it due to 
      local buffer congestion. This counter will wrap around after it reaches its 
      maximum value."
::= { mscLpFiMacCOperEntry 3 }

mscLpFiLateCounts OBJECT-TYPE
   SYNTAX     Counter32 
   ACCESS     read-only
   STATUS     mandatory
   DESCRIPTION
     "The lateCounts attribute contains the number of token rotation time 
      (TRT) expirations since the station was reset or a token was received. 
      This counter may increment as stations go on and off the ring. A rapidly 
      increasing value may indicate a problem. This counter will wrap around 
      after it reaches its maximum value."
::= { mscLpFiMacCOperEntry 4 }

mscLpFiRingOpCounts OBJECT-TYPE
   SYNTAX     Counter32 
   ACCESS     read-only
   STATUS     mandatory
   DESCRIPTION
     "The ringOpCounts attribute contains the number of times the station has 
      made the transition from the ring not operational state to the ring 
      operational state."
::= { mscLpFiMacCOperEntry 5 }

mscLpFiNcMacOperTable OBJECT-TYPE
   SYNTAX     SEQUENCE OF MscLpFiNcMacOperEntry
   ACCESS     not-accessible
   STATUS     mandatory
   DESCRIPTION
     "This group contains the operational attributes of the Fddi component 
      related to non-canonical MAC addresses."
::= { mscLpFi 26 }

mscLpFiNcMacOperEntry OBJECT-TYPE
   SYNTAX     MscLpFiNcMacOperEntry
   ACCESS     not-accessible
   STATUS     mandatory
   DESCRIPTION
     "An entry in the mscLpFiNcMacOperTable."
   INDEX {
      mscLpIndex,
      mscLpFiIndex }
::= { mscLpFiNcMacOperTable 1 }

MscLpFiNcMacOperEntry ::= SEQUENCE {
   mscLpFiNcMacAddress
      MacAddress,
   mscLpFiNcUpstreamNeighbor
      MacAddress,
   mscLpFiNcDownstreamNeighbor
      MacAddress,
   mscLpFiNcOldUpstreamNeighbor
      MacAddress,
   mscLpFiNcOldDownstreamNeighbor
      MacAddress }

mscLpFiNcMacAddress OBJECT-TYPE
   SYNTAX     MacAddress (SIZE (6))
   ACCESS     read-only
   STATUS     mandatory
   DESCRIPTION
     "The medium access controller (MAC) address is an address that is 
      recognized by only one station on the attached ring. The value of this 
      attribute is assigned by the system. This attribute is displayed in non-
      canonical format. The canonical version of this address is indicated in 
      macAddress."
::= { mscLpFiNcMacOperEntry 1 }

mscLpFiNcUpstreamNeighbor OBJECT-TYPE
   SYNTAX     MacAddress (SIZE (6))
   ACCESS     read-only
   STATUS     mandatory
   DESCRIPTION
     "The ncUpstreamNeighbor attribute contains the MAC address 
      associated with the upstream neighbor station on the ring. This attribute 
      is displayed in non-canonical format. The canonical version of this 
      address is indicated in upstreamNeighbor."
::= { mscLpFiNcMacOperEntry 2 }

mscLpFiNcDownstreamNeighbor OBJECT-TYPE
   SYNTAX     MacAddress (SIZE (6))
   ACCESS     read-only
   STATUS     mandatory
   DESCRIPTION
     "The ncDownstreamNeighbor attribute contains the MAC address 
      associated with the downstream station on the ring. This attribute is 
      displayed in non-canonical format. The canonical version of this address 
      is indicated in downstreamNeighbor"
::= { mscLpFiNcMacOperEntry 3 }

mscLpFiNcOldUpstreamNeighbor OBJECT-TYPE
   SYNTAX     MacAddress (SIZE (6))
   ACCESS     read-only
   STATUS     mandatory
   DESCRIPTION
     "The ncOldUpstreamNeighbor attribute contains the previous value of the 
      MAC address associated with the upstream station on the ring. This 
      attribute is displayed in non-canonical format. The canonical version of 
      this address is indicated in oldUpstreamNeighbor."
::= { mscLpFiNcMacOperEntry 4 }

mscLpFiNcOldDownstreamNeighbor OBJECT-TYPE
   SYNTAX     MacAddress (SIZE (6))
   ACCESS     read-only
   STATUS     mandatory
   DESCRIPTION
     "The ncOldDownstreamNeighbor attribute contains the previous value of 
      the MAC address associated with the downstream station on the ring. 
      This attribute is displayed in non-canonical format. The canonical 
      version of this address is indicated in oldDownstreamNeighbor."
::= { mscLpFiNcMacOperEntry 5 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

mscLpFiLt OBJECT IDENTIFIER ::= { mscLpFi 2 }



mscLpFiLtRowStatusTable OBJECT-TYPE
   SYNTAX     SEQUENCE OF MscLpFiLtRowStatusEntry
   ACCESS     not-accessible
   STATUS     mandatory
   DESCRIPTION
     "This entry controls the addition and deletion of 
      mscLpFiLt components."
::= { mscLpFiLt 1 }

mscLpFiLtRowStatusEntry OBJECT-TYPE
   SYNTAX     MscLpFiLtRowStatusEntry
   ACCESS     not-accessible
   STATUS     mandatory
   DESCRIPTION
     "A single entry in the table represents a single 
      mscLpFiLt component."
   INDEX {
      mscLpIndex,
      mscLpFiIndex,
      mscLpFiLtIndex }
::= { mscLpFiLtRowStatusTable 1 }

MscLpFiLtRowStatusEntry ::= SEQUENCE {
   mscLpFiLtRowStatus
      RowStatus,
   mscLpFiLtComponentName
      DisplayString,
   mscLpFiLtStorageType
      StorageType,
   mscLpFiLtIndex
      NonReplicated }

mscLpFiLtRowStatus OBJECT-TYPE
   SYNTAX     RowStatus 
   ACCESS     read-only
   STATUS     mandatory
   DESCRIPTION
     "This variable is used as the basis for SNMP naming of
      mscLpFiLt components.
      These components cannot be added nor deleted."
::= { mscLpFiLtRowStatusEntry 1 }

mscLpFiLtComponentName OBJECT-TYPE
   SYNTAX     DisplayString 
   ACCESS     read-only
   STATUS     mandatory
   DESCRIPTION
     "This variable provides the component's string name for
      use with the ASCII Console Interface"
::= { mscLpFiLtRowStatusEntry 2 }

mscLpFiLtStorageType OBJECT-TYPE
   SYNTAX     StorageType 
   ACCESS     read-only
   STATUS     mandatory
   DESCRIPTION
     "This variable represents the storage type value for the
      mscLpFiLt tables."
::= { mscLpFiLtRowStatusEntry 4 }

mscLpFiLtIndex OBJECT-TYPE
   SYNTAX     NonReplicated 
   ACCESS     not-accessible
   STATUS     mandatory
   DESCRIPTION
     "This variable represents the index for the mscLpFiLt tables."
::= { mscLpFiLtRowStatusEntry 10 }

mscLpFiLtTopTable OBJECT-TYPE
   SYNTAX     SEQUENCE OF MscLpFiLtTopEntry
   ACCESS     not-accessible
   STATUS     mandatory
   DESCRIPTION
     "This group contains the operational data for the LanTest component 
      and its subcomponents."
::= { mscLpFiLt 20 }

mscLpFiLtTopEntry OBJECT-TYPE
   SYNTAX     MscLpFiLtTopEntry
   ACCESS     not-accessible
   STATUS     mandatory
   DESCRIPTION
     "An entry in the mscLpFiLtTopTable."
   INDEX {
      mscLpIndex,
      mscLpFiIndex,
      mscLpFiLtIndex }
::= { mscLpFiLtTopTable 1 }

MscLpFiLtTopEntry ::= SEQUENCE {
   mscLpFiLtTData
      AsciiString }

mscLpFiLtTData OBJECT-TYPE
   SYNTAX     AsciiString (SIZE (0..255))
   ACCESS     read-write
   STATUS     mandatory
   DESCRIPTION
     "This attribute is used to display and set attributes."
::= { mscLpFiLtTopEntry 1 }


-- This component compares frames received from the hardware and 
-- emulator during testing.

mscLpFiLtFrmCmp OBJECT IDENTIFIER ::= { mscLpFiLt 2 }



mscLpFiLtFrmCmpRowStatusTable OBJECT-TYPE
   SYNTAX     SEQUENCE OF MscLpFiLtFrmCmpRowStatusEntry
   ACCESS     not-accessible
   STATUS     mandatory
   DESCRIPTION
     "This entry controls the addition and deletion of 
      mscLpFiLtFrmCmp components."
::= { mscLpFiLtFrmCmp 1 }

mscLpFiLtFrmCmpRowStatusEntry OBJECT-TYPE
   SYNTAX     MscLpFiLtFrmCmpRowStatusEntry
   ACCESS     not-accessible
   STATUS     mandatory
   DESCRIPTION
     "A single entry in the table represents a single 
      mscLpFiLtFrmCmp component."
   INDEX {
      mscLpIndex,
      mscLpFiIndex,
      mscLpFiLtIndex,
      mscLpFiLtFrmCmpIndex }
::= { mscLpFiLtFrmCmpRowStatusTable 1 }

MscLpFiLtFrmCmpRowStatusEntry ::= SEQUENCE {
   mscLpFiLtFrmCmpRowStatus
      RowStatus,
   mscLpFiLtFrmCmpComponentName
      DisplayString,
   mscLpFiLtFrmCmpStorageType
      StorageType,
   mscLpFiLtFrmCmpIndex
      NonReplicated }

mscLpFiLtFrmCmpRowStatus OBJECT-TYPE
   SYNTAX     RowStatus 
   ACCESS     read-only
   STATUS     mandatory
   DESCRIPTION
     "This variable is used as the basis for SNMP naming of
      mscLpFiLtFrmCmp components.
      These components cannot be added nor deleted."
::= { mscLpFiLtFrmCmpRowStatusEntry 1 }

mscLpFiLtFrmCmpComponentName OBJECT-TYPE
   SYNTAX     DisplayString 
   ACCESS     read-only
   STATUS     mandatory
   DESCRIPTION
     "This variable provides the component's string name for
      use with the ASCII Console Interface"
::= { mscLpFiLtFrmCmpRowStatusEntry 2 }

mscLpFiLtFrmCmpStorageType OBJECT-TYPE
   SYNTAX     StorageType 
   ACCESS     read-only
   STATUS     mandatory
   DESCRIPTION
     "This variable represents the storage type value for the
      mscLpFiLtFrmCmp tables."
::= { mscLpFiLtFrmCmpRowStatusEntry 4 }

mscLpFiLtFrmCmpIndex OBJECT-TYPE
   SYNTAX     NonReplicated 
   ACCESS     not-accessible
   STATUS     mandatory
   DESCRIPTION
     "This variable represents the index for the mscLpFiLtFrmCmp tables."
::= { mscLpFiLtFrmCmpRowStatusEntry 10 }

mscLpFiLtFrmCmpTopTable OBJECT-TYPE
   SYNTAX     SEQUENCE OF MscLpFiLtFrmCmpTopEntry
   ACCESS     not-accessible
   STATUS     mandatory
   DESCRIPTION
     "This group contains the operational data for the LanTest component 
      and its subcomponents."
::= { mscLpFiLtFrmCmp 10 }

mscLpFiLtFrmCmpTopEntry OBJECT-TYPE
   SYNTAX     MscLpFiLtFrmCmpTopEntry
   ACCESS     not-accessible
   STATUS     mandatory
   DESCRIPTION
     "An entry in the mscLpFiLtFrmCmpTopTable."
   INDEX {
      mscLpIndex,
      mscLpFiIndex,
      mscLpFiLtIndex,
      mscLpFiLtFrmCmpIndex }
::= { mscLpFiLtFrmCmpTopTable 1 }

MscLpFiLtFrmCmpTopEntry ::= SEQUENCE {
   mscLpFiLtFrmCmpTData
      AsciiString }

mscLpFiLtFrmCmpTData OBJECT-TYPE
   SYNTAX     AsciiString (SIZE (0..255))
   ACCESS     read-write
   STATUS     mandatory
   DESCRIPTION
     "This attribute is used to display and set attributes."
::= { mscLpFiLtFrmCmpTopEntry 1 }


-- This component receives its input from FrameBuild and places it 
-- upon the hardware which sends it to the appropriate emulator.

mscLpFiLtFrmCpy OBJECT IDENTIFIER ::= { mscLpFiLt 3 }



mscLpFiLtFrmCpyRowStatusTable OBJECT-TYPE
   SYNTAX     SEQUENCE OF MscLpFiLtFrmCpyRowStatusEntry
   ACCESS     not-accessible
   STATUS     mandatory
   DESCRIPTION
     "This entry controls the addition and deletion of 
      mscLpFiLtFrmCpy components."
::= { mscLpFiLtFrmCpy 1 }

mscLpFiLtFrmCpyRowStatusEntry OBJECT-TYPE
   SYNTAX     MscLpFiLtFrmCpyRowStatusEntry
   ACCESS     not-accessible
   STATUS     mandatory
   DESCRIPTION
     "A single entry in the table represents a single 
      mscLpFiLtFrmCpy component."
   INDEX {
      mscLpIndex,
      mscLpFiIndex,
      mscLpFiLtIndex,
      mscLpFiLtFrmCpyIndex }
::= { mscLpFiLtFrmCpyRowStatusTable 1 }

MscLpFiLtFrmCpyRowStatusEntry ::= SEQUENCE {
   mscLpFiLtFrmCpyRowStatus
      RowStatus,
   mscLpFiLtFrmCpyComponentName
      DisplayString,
   mscLpFiLtFrmCpyStorageType
      StorageType,
   mscLpFiLtFrmCpyIndex
      NonReplicated }

mscLpFiLtFrmCpyRowStatus OBJECT-TYPE
   SYNTAX     RowStatus 
   ACCESS     read-only
   STATUS     mandatory
   DESCRIPTION
     "This variable is used as the basis for SNMP naming of
      mscLpFiLtFrmCpy components.
      These components cannot be added nor deleted."
::= { mscLpFiLtFrmCpyRowStatusEntry 1 }

mscLpFiLtFrmCpyComponentName OBJECT-TYPE
   SYNTAX     DisplayString 
   ACCESS     read-only
   STATUS     mandatory
   DESCRIPTION
     "This variable provides the component's string name for
      use with the ASCII Console Interface"
::= { mscLpFiLtFrmCpyRowStatusEntry 2 }

mscLpFiLtFrmCpyStorageType OBJECT-TYPE
   SYNTAX     StorageType 
   ACCESS     read-only
   STATUS     mandatory
   DESCRIPTION
     "This variable represents the storage type value for the
      mscLpFiLtFrmCpy tables."
::= { mscLpFiLtFrmCpyRowStatusEntry 4 }

mscLpFiLtFrmCpyIndex OBJECT-TYPE
   SYNTAX     NonReplicated 
   ACCESS     not-accessible
   STATUS     mandatory
   DESCRIPTION
     "This variable represents the index for the mscLpFiLtFrmCpy tables."
::= { mscLpFiLtFrmCpyRowStatusEntry 10 }

mscLpFiLtFrmCpyTopTable OBJECT-TYPE
   SYNTAX     SEQUENCE OF MscLpFiLtFrmCpyTopEntry
   ACCESS     not-accessible
   STATUS     mandatory
   DESCRIPTION
     "This group contains the operational data for the LanTest component 
      and its subcomponents."
::= { mscLpFiLtFrmCpy 10 }

mscLpFiLtFrmCpyTopEntry OBJECT-TYPE
   SYNTAX     MscLpFiLtFrmCpyTopEntry
   ACCESS     not-accessible
   STATUS     mandatory
   DESCRIPTION
     "An entry in the mscLpFiLtFrmCpyTopTable."
   INDEX {
      mscLpIndex,
      mscLpFiIndex,
      mscLpFiLtIndex,
      mscLpFiLtFrmCpyIndex }
::= { mscLpFiLtFrmCpyTopTable 1 }

MscLpFiLtFrmCpyTopEntry ::= SEQUENCE {
   mscLpFiLtFrmCpyTData
      AsciiString }

mscLpFiLtFrmCpyTData OBJECT-TYPE
   SYNTAX     AsciiString (SIZE (0..255))
   ACCESS     read-write
   STATUS     mandatory
   DESCRIPTION
     "This attribute is used to display and set attributes."
::= { mscLpFiLtFrmCpyTopEntry 1 }


-- This component controls the emulator and hardware to ensure 
-- frames output from each will match in FrameCompare.

mscLpFiLtPrtCfg OBJECT IDENTIFIER ::= { mscLpFiLt 4 }



mscLpFiLtPrtCfgRowStatusTable OBJECT-TYPE
   SYNTAX     SEQUENCE OF MscLpFiLtPrtCfgRowStatusEntry
   ACCESS     not-accessible
   STATUS     mandatory
   DESCRIPTION
     "This entry controls the addition and deletion of 
      mscLpFiLtPrtCfg components."
::= { mscLpFiLtPrtCfg 1 }

mscLpFiLtPrtCfgRowStatusEntry OBJECT-TYPE
   SYNTAX     MscLpFiLtPrtCfgRowStatusEntry
   ACCESS     not-accessible
   STATUS     mandatory
   DESCRIPTION
     "A single entry in the table represents a single 
      mscLpFiLtPrtCfg component."
   INDEX {
      mscLpIndex,
      mscLpFiIndex,
      mscLpFiLtIndex,
      mscLpFiLtPrtCfgIndex }
::= { mscLpFiLtPrtCfgRowStatusTable 1 }

MscLpFiLtPrtCfgRowStatusEntry ::= SEQUENCE {
   mscLpFiLtPrtCfgRowStatus
      RowStatus,
   mscLpFiLtPrtCfgComponentName
      DisplayString,
   mscLpFiLtPrtCfgStorageType
      StorageType,
   mscLpFiLtPrtCfgIndex
      NonReplicated }

mscLpFiLtPrtCfgRowStatus OBJECT-TYPE
   SYNTAX     RowStatus 
   ACCESS     read-only
   STATUS     mandatory
   DESCRIPTION
     "This variable is used as the basis for SNMP naming of
      mscLpFiLtPrtCfg components.
      These components cannot be added nor deleted."
::= { mscLpFiLtPrtCfgRowStatusEntry 1 }

mscLpFiLtPrtCfgComponentName OBJECT-TYPE
   SYNTAX     DisplayString 
   ACCESS     read-only
   STATUS     mandatory
   DESCRIPTION
     "This variable provides the component's string name for
      use with the ASCII Console Interface"
::= { mscLpFiLtPrtCfgRowStatusEntry 2 }

mscLpFiLtPrtCfgStorageType OBJECT-TYPE
   SYNTAX     StorageType 
   ACCESS     read-only
   STATUS     mandatory
   DESCRIPTION
     "This variable represents the storage type value for the
      mscLpFiLtPrtCfg tables."
::= { mscLpFiLtPrtCfgRowStatusEntry 4 }

mscLpFiLtPrtCfgIndex OBJECT-TYPE
   SYNTAX     NonReplicated 
   ACCESS     not-accessible
   STATUS     mandatory
   DESCRIPTION
     "This variable represents the index for the mscLpFiLtPrtCfg tables."
::= { mscLpFiLtPrtCfgRowStatusEntry 10 }

mscLpFiLtPrtCfgTopTable OBJECT-TYPE
   SYNTAX     SEQUENCE OF MscLpFiLtPrtCfgTopEntry
   ACCESS     not-accessible
   STATUS     mandatory
   DESCRIPTION
     "This group contains the operational data for the LanTest component 
      and its subcomponents."
::= { mscLpFiLtPrtCfg 10 }

mscLpFiLtPrtCfgTopEntry OBJECT-TYPE
   SYNTAX     MscLpFiLtPrtCfgTopEntry
   ACCESS     not-accessible
   STATUS     mandatory
   DESCRIPTION
     "An entry in the mscLpFiLtPrtCfgTopTable."
   INDEX {
      mscLpIndex,
      mscLpFiIndex,
      mscLpFiLtIndex,
      mscLpFiLtPrtCfgIndex }
::= { mscLpFiLtPrtCfgTopTable 1 }

MscLpFiLtPrtCfgTopEntry ::= SEQUENCE {
   mscLpFiLtPrtCfgTData
      AsciiString }

mscLpFiLtPrtCfgTData OBJECT-TYPE
   SYNTAX     AsciiString (SIZE (0..255))
   ACCESS     read-write
   STATUS     mandatory
   DESCRIPTION
     "This attribute is used to display and set attributes."
::= { mscLpFiLtPrtCfgTopEntry 1 }


-- LanTest Framebuild
-- This component controls the building of all frames built and sent by 
-- the LanTest component. Each component under FrameBuild builds 
-- a portion of a packet or frame.

mscLpFiLtFb OBJECT IDENTIFIER ::= { mscLpFiLt 5 }



mscLpFiLtFbRowStatusTable OBJECT-TYPE
   SYNTAX     SEQUENCE OF MscLpFiLtFbRowStatusEntry
   ACCESS     not-accessible
   STATUS     mandatory
   DESCRIPTION
     "This entry controls the addition and deletion of 
      mscLpFiLtFb components."
::= { mscLpFiLtFb 1 }

mscLpFiLtFbRowStatusEntry OBJECT-TYPE
   SYNTAX     MscLpFiLtFbRowStatusEntry
   ACCESS     not-accessible
   STATUS     mandatory
   DESCRIPTION
     "A single entry in the table represents a single 
      mscLpFiLtFb component."
   INDEX {
      mscLpIndex,
      mscLpFiIndex,
      mscLpFiLtIndex,
      mscLpFiLtFbIndex }
::= { mscLpFiLtFbRowStatusTable 1 }

MscLpFiLtFbRowStatusEntry ::= SEQUENCE {
   mscLpFiLtFbRowStatus
      RowStatus,
   mscLpFiLtFbComponentName
      DisplayString,
   mscLpFiLtFbStorageType
      StorageType,
   mscLpFiLtFbIndex
      NonReplicated }

mscLpFiLtFbRowStatus OBJECT-TYPE
   SYNTAX     RowStatus 
   ACCESS     read-only
   STATUS     mandatory
   DESCRIPTION
     "This variable is used as the basis for SNMP naming of
      mscLpFiLtFb components.
      These components cannot be added nor deleted."
::= { mscLpFiLtFbRowStatusEntry 1 }

mscLpFiLtFbComponentName OBJECT-TYPE
   SYNTAX     DisplayString 
   ACCESS     read-only
   STATUS     mandatory
   DESCRIPTION
     "This variable provides the component's string name for
      use with the ASCII Console Interface"
::= { mscLpFiLtFbRowStatusEntry 2 }

mscLpFiLtFbStorageType OBJECT-TYPE
   SYNTAX     StorageType 
   ACCESS     read-only
   STATUS     mandatory
   DESCRIPTION
     "This variable represents the storage type value for the
      mscLpFiLtFb tables."
::= { mscLpFiLtFbRowStatusEntry 4 }

mscLpFiLtFbIndex OBJECT-TYPE
   SYNTAX     NonReplicated 
   ACCESS     not-accessible
   STATUS     mandatory
   DESCRIPTION
     "This variable represents the index for the mscLpFiLtFb tables."
::= { mscLpFiLtFbRowStatusEntry 10 }

mscLpFiLtFbTopTable OBJECT-TYPE
   SYNTAX     SEQUENCE OF MscLpFiLtFbTopEntry
   ACCESS     not-accessible
   STATUS     mandatory
   DESCRIPTION
     "This group contains the operational data for the LanTest component 
      and its subcomponents."
::= { mscLpFiLtFb 20 }

mscLpFiLtFbTopEntry OBJECT-TYPE
   SYNTAX     MscLpFiLtFbTopEntry
   ACCESS     not-accessible
   STATUS     mandatory
   DESCRIPTION
     "An entry in the mscLpFiLtFbTopTable."
   INDEX {
      mscLpIndex,
      mscLpFiIndex,
      mscLpFiLtIndex,
      mscLpFiLtFbIndex }
::= { mscLpFiLtFbTopTable 1 }

MscLpFiLtFbTopEntry ::= SEQUENCE {
   mscLpFiLtFbTData
      AsciiString }

mscLpFiLtFbTData OBJECT-TYPE
   SYNTAX     AsciiString (SIZE (0..255))
   ACCESS     read-write
   STATUS     mandatory
   DESCRIPTION
     "This attribute is used to display and set attributes."
::= { mscLpFiLtFbTopEntry 1 }


-- LanTest TransmitInfo
-- This component builds a transmit header which is attached to all 
-- frames transmitted on LAN interfaces.

mscLpFiLtFbTxInfo OBJECT IDENTIFIER ::= { mscLpFiLtFb 2 }



mscLpFiLtFbTxInfoRowStatusTable OBJECT-TYPE
   SYNTAX     SEQUENCE OF MscLpFiLtFbTxInfoRowStatusEntry
   ACCESS     not-accessible
   STATUS     mandatory
   DESCRIPTION
     "This entry controls the addition and deletion of 
      mscLpFiLtFbTxInfo components."
::= { mscLpFiLtFbTxInfo 1 }

mscLpFiLtFbTxInfoRowStatusEntry OBJECT-TYPE
   SYNTAX     MscLpFiLtFbTxInfoRowStatusEntry
   ACCESS     not-accessible
   STATUS     mandatory
   DESCRIPTION
     "A single entry in the table represents a single 
      mscLpFiLtFbTxInfo component."
   INDEX {
      mscLpIndex,
      mscLpFiIndex,
      mscLpFiLtIndex,
      mscLpFiLtFbIndex,
      mscLpFiLtFbTxInfoIndex }
::= { mscLpFiLtFbTxInfoRowStatusTable 1 }

MscLpFiLtFbTxInfoRowStatusEntry ::= SEQUENCE {
   mscLpFiLtFbTxInfoRowStatus
      RowStatus,
   mscLpFiLtFbTxInfoComponentName
      DisplayString,
   mscLpFiLtFbTxInfoStorageType
      StorageType,
   mscLpFiLtFbTxInfoIndex
      NonReplicated }

mscLpFiLtFbTxInfoRowStatus OBJECT-TYPE
   SYNTAX     RowStatus 
   ACCESS     read-only
   STATUS     mandatory
   DESCRIPTION
     "This variable is used as the basis for SNMP naming of
      mscLpFiLtFbTxInfo components.
      These components cannot be added nor deleted."
::= { mscLpFiLtFbTxInfoRowStatusEntry 1 }

mscLpFiLtFbTxInfoComponentName OBJECT-TYPE
   SYNTAX     DisplayString 
   ACCESS     read-only
   STATUS     mandatory
   DESCRIPTION
     "This variable provides the component's string name for
      use with the ASCII Console Interface"
::= { mscLpFiLtFbTxInfoRowStatusEntry 2 }

mscLpFiLtFbTxInfoStorageType OBJECT-TYPE
   SYNTAX     StorageType 
   ACCESS     read-only
   STATUS     mandatory
   DESCRIPTION
     "This variable represents the storage type value for the
      mscLpFiLtFbTxInfo tables."
::= { mscLpFiLtFbTxInfoRowStatusEntry 4 }

mscLpFiLtFbTxInfoIndex OBJECT-TYPE
   SYNTAX     NonReplicated 
   ACCESS     not-accessible
   STATUS     mandatory
   DESCRIPTION
     "This variable represents the index for the mscLpFiLtFbTxInfo tables."
::= { mscLpFiLtFbTxInfoRowStatusEntry 10 }

mscLpFiLtFbTxInfoTopTable OBJECT-TYPE
   SYNTAX     SEQUENCE OF MscLpFiLtFbTxInfoTopEntry
   ACCESS     not-accessible
   STATUS     mandatory
   DESCRIPTION
     "This group contains the operational data for the LanTest component 
      and its subcomponents."
::= { mscLpFiLtFbTxInfo 10 }

mscLpFiLtFbTxInfoTopEntry OBJECT-TYPE
   SYNTAX     MscLpFiLtFbTxInfoTopEntry
   ACCESS     not-accessible
   STATUS     mandatory
   DESCRIPTION
     "An entry in the mscLpFiLtFbTxInfoTopTable."
   INDEX {
      mscLpIndex,
      mscLpFiIndex,
      mscLpFiLtIndex,
      mscLpFiLtFbIndex,
      mscLpFiLtFbTxInfoIndex }
::= { mscLpFiLtFbTxInfoTopTable 1 }

MscLpFiLtFbTxInfoTopEntry ::= SEQUENCE {
   mscLpFiLtFbTxInfoTData
      AsciiString }

mscLpFiLtFbTxInfoTData OBJECT-TYPE
   SYNTAX     AsciiString (SIZE (0..255))
   ACCESS     read-write
   STATUS     mandatory
   DESCRIPTION
     "This attribute is used to display and set attributes."
::= { mscLpFiLtFbTxInfoTopEntry 1 }


-- LanTest FddiMac
-- This component builds an FDDI MAC header which is attached to 
-- all FDDI frames.

mscLpFiLtFbFddiMac OBJECT IDENTIFIER ::= { mscLpFiLtFb 3 }



mscLpFiLtFbFddiMacRowStatusTable OBJECT-TYPE
   SYNTAX     SEQUENCE OF MscLpFiLtFbFddiMacRowStatusEntry
   ACCESS     not-accessible
   STATUS     mandatory
   DESCRIPTION
     "This entry controls the addition and deletion of 
      mscLpFiLtFbFddiMac components."
::= { mscLpFiLtFbFddiMac 1 }

mscLpFiLtFbFddiMacRowStatusEntry OBJECT-TYPE
   SYNTAX     MscLpFiLtFbFddiMacRowStatusEntry
   ACCESS     not-accessible
   STATUS     mandatory
   DESCRIPTION
     "A single entry in the table represents a single 
      mscLpFiLtFbFddiMac component."
   INDEX {
      mscLpIndex,
      mscLpFiIndex,
      mscLpFiLtIndex,
      mscLpFiLtFbIndex,
      mscLpFiLtFbFddiMacIndex }
::= { mscLpFiLtFbFddiMacRowStatusTable 1 }

MscLpFiLtFbFddiMacRowStatusEntry ::= SEQUENCE {
   mscLpFiLtFbFddiMacRowStatus
      RowStatus,
   mscLpFiLtFbFddiMacComponentName
      DisplayString,
   mscLpFiLtFbFddiMacStorageType
      StorageType,
   mscLpFiLtFbFddiMacIndex
      NonReplicated }

mscLpFiLtFbFddiMacRowStatus OBJECT-TYPE
   SYNTAX     RowStatus 
   ACCESS     read-only
   STATUS     mandatory
   DESCRIPTION
     "This variable is used as the basis for SNMP naming of
      mscLpFiLtFbFddiMac components.
      These components cannot be added nor deleted."
::= { mscLpFiLtFbFddiMacRowStatusEntry 1 }

mscLpFiLtFbFddiMacComponentName OBJECT-TYPE
   SYNTAX     DisplayString 
   ACCESS     read-only
   STATUS     mandatory
   DESCRIPTION
     "This variable provides the component's string name for
      use with the ASCII Console Interface"
::= { mscLpFiLtFbFddiMacRowStatusEntry 2 }

mscLpFiLtFbFddiMacStorageType OBJECT-TYPE
   SYNTAX     StorageType 
   ACCESS     read-only
   STATUS     mandatory
   DESCRIPTION
     "This variable represents the storage type value for the
      mscLpFiLtFbFddiMac tables."
::= { mscLpFiLtFbFddiMacRowStatusEntry 4 }

mscLpFiLtFbFddiMacIndex OBJECT-TYPE
   SYNTAX     NonReplicated 
   ACCESS     not-accessible
   STATUS     mandatory
   DESCRIPTION
     "This variable represents the index for the mscLpFiLtFbFddiMac tables."
::= { mscLpFiLtFbFddiMacRowStatusEntry 10 }

mscLpFiLtFbFddiMacTopTable OBJECT-TYPE
   SYNTAX     SEQUENCE OF MscLpFiLtFbFddiMacTopEntry
   ACCESS     not-accessible
   STATUS     mandatory
   DESCRIPTION
     "This group contains the operational data for the LanTest component 
      and its subcomponents."
::= { mscLpFiLtFbFddiMac 10 }

mscLpFiLtFbFddiMacTopEntry OBJECT-TYPE
   SYNTAX     MscLpFiLtFbFddiMacTopEntry
   ACCESS     not-accessible
   STATUS     mandatory
   DESCRIPTION
     "An entry in the mscLpFiLtFbFddiMacTopTable."
   INDEX {
      mscLpIndex,
      mscLpFiIndex,
      mscLpFiLtIndex,
      mscLpFiLtFbIndex,
      mscLpFiLtFbFddiMacIndex }
::= { mscLpFiLtFbFddiMacTopTable 1 }

MscLpFiLtFbFddiMacTopEntry ::= SEQUENCE {
   mscLpFiLtFbFddiMacTData
      AsciiString }

mscLpFiLtFbFddiMacTData OBJECT-TYPE
   SYNTAX     AsciiString (SIZE (0..255))
   ACCESS     read-write
   STATUS     mandatory
   DESCRIPTION
     "This attribute is used to display and set attributes."
::= { mscLpFiLtFbFddiMacTopEntry 1 }


-- LanTest EthernetMac
-- This component builds an Ethernet MAC header which is attached 
-- to all Ethernet frames.

mscLpFiLtFbMacEnet OBJECT IDENTIFIER ::= { mscLpFiLtFb 4 }



mscLpFiLtFbMacEnetRowStatusTable OBJECT-TYPE
   SYNTAX     SEQUENCE OF MscLpFiLtFbMacEnetRowStatusEntry
   ACCESS     not-accessible
   STATUS     mandatory
   DESCRIPTION
     "This entry controls the addition and deletion of 
      mscLpFiLtFbMacEnet components."
::= { mscLpFiLtFbMacEnet 1 }

mscLpFiLtFbMacEnetRowStatusEntry OBJECT-TYPE
   SYNTAX     MscLpFiLtFbMacEnetRowStatusEntry
   ACCESS     not-accessible
   STATUS     mandatory
   DESCRIPTION
     "A single entry in the table represents a single 
      mscLpFiLtFbMacEnet component."
   INDEX {
      mscLpIndex,
      mscLpFiIndex,
      mscLpFiLtIndex,
      mscLpFiLtFbIndex,
      mscLpFiLtFbMacEnetIndex }
::= { mscLpFiLtFbMacEnetRowStatusTable 1 }

MscLpFiLtFbMacEnetRowStatusEntry ::= SEQUENCE {
   mscLpFiLtFbMacEnetRowStatus
      RowStatus,
   mscLpFiLtFbMacEnetComponentName
      DisplayString,
   mscLpFiLtFbMacEnetStorageType
      StorageType,
   mscLpFiLtFbMacEnetIndex
      NonReplicated }

mscLpFiLtFbMacEnetRowStatus OBJECT-TYPE
   SYNTAX     RowStatus 
   ACCESS     read-only
   STATUS     mandatory
   DESCRIPTION
     "This variable is used as the basis for SNMP naming of
      mscLpFiLtFbMacEnet components.
      These components cannot be added nor deleted."
::= { mscLpFiLtFbMacEnetRowStatusEntry 1 }

mscLpFiLtFbMacEnetComponentName OBJECT-TYPE
   SYNTAX     DisplayString 
   ACCESS     read-only
   STATUS     mandatory
   DESCRIPTION
     "This variable provides the component's string name for
      use with the ASCII Console Interface"
::= { mscLpFiLtFbMacEnetRowStatusEntry 2 }

mscLpFiLtFbMacEnetStorageType OBJECT-TYPE
   SYNTAX     StorageType 
   ACCESS     read-only
   STATUS     mandatory
   DESCRIPTION
     "This variable represents the storage type value for the
      mscLpFiLtFbMacEnet tables."
::= { mscLpFiLtFbMacEnetRowStatusEntry 4 }

mscLpFiLtFbMacEnetIndex OBJECT-TYPE
   SYNTAX     NonReplicated 
   ACCESS     not-accessible
   STATUS     mandatory
   DESCRIPTION
     "This variable represents the index for the mscLpFiLtFbMacEnet tables."
::= { mscLpFiLtFbMacEnetRowStatusEntry 10 }

mscLpFiLtFbMacEnetTopTable OBJECT-TYPE
   SYNTAX     SEQUENCE OF MscLpFiLtFbMacEnetTopEntry
   ACCESS     not-accessible
   STATUS     mandatory
   DESCRIPTION
     "This group contains the operational data for the LanTest component 
      and its subcomponents."
::= { mscLpFiLtFbMacEnet 10 }

mscLpFiLtFbMacEnetTopEntry OBJECT-TYPE
   SYNTAX     MscLpFiLtFbMacEnetTopEntry
   ACCESS     not-accessible
   STATUS     mandatory
   DESCRIPTION
     "An entry in the mscLpFiLtFbMacEnetTopTable."
   INDEX {
      mscLpIndex,
      mscLpFiIndex,
      mscLpFiLtIndex,
      mscLpFiLtFbIndex,
      mscLpFiLtFbMacEnetIndex }
::= { mscLpFiLtFbMacEnetTopTable 1 }

MscLpFiLtFbMacEnetTopEntry ::= SEQUENCE {
   mscLpFiLtFbMacEnetTData
      AsciiString }

mscLpFiLtFbMacEnetTData OBJECT-TYPE
   SYNTAX     AsciiString (SIZE (0..255))
   ACCESS     read-write
   STATUS     mandatory
   DESCRIPTION
     "This attribute is used to display and set attributes."
::= { mscLpFiLtFbMacEnetTopEntry 1 }


-- LanTest TokenRingMac
-- This component builds a Token Ring MAC header which is attached 
-- to all Token Ring frames.

mscLpFiLtFbMacTr OBJECT IDENTIFIER ::= { mscLpFiLtFb 5 }



mscLpFiLtFbMacTrRowStatusTable OBJECT-TYPE
   SYNTAX     SEQUENCE OF MscLpFiLtFbMacTrRowStatusEntry
   ACCESS     not-accessible
   STATUS     mandatory
   DESCRIPTION
     "This entry controls the addition and deletion of 
      mscLpFiLtFbMacTr components."
::= { mscLpFiLtFbMacTr 1 }

mscLpFiLtFbMacTrRowStatusEntry OBJECT-TYPE
   SYNTAX     MscLpFiLtFbMacTrRowStatusEntry
   ACCESS     not-accessible
   STATUS     mandatory
   DESCRIPTION
     "A single entry in the table represents a single 
      mscLpFiLtFbMacTr component."
   INDEX {
      mscLpIndex,
      mscLpFiIndex,
      mscLpFiLtIndex,
      mscLpFiLtFbIndex,
      mscLpFiLtFbMacTrIndex }
::= { mscLpFiLtFbMacTrRowStatusTable 1 }

MscLpFiLtFbMacTrRowStatusEntry ::= SEQUENCE {
   mscLpFiLtFbMacTrRowStatus
      RowStatus,
   mscLpFiLtFbMacTrComponentName
      DisplayString,
   mscLpFiLtFbMacTrStorageType
      StorageType,
   mscLpFiLtFbMacTrIndex
      NonReplicated }

mscLpFiLtFbMacTrRowStatus OBJECT-TYPE
   SYNTAX     RowStatus 
   ACCESS     read-only
   STATUS     mandatory
   DESCRIPTION
     "This variable is used as the basis for SNMP naming of
      mscLpFiLtFbMacTr components.
      These components cannot be added nor deleted."
::= { mscLpFiLtFbMacTrRowStatusEntry 1 }

mscLpFiLtFbMacTrComponentName OBJECT-TYPE
   SYNTAX     DisplayString 
   ACCESS     read-only
   STATUS     mandatory
   DESCRIPTION
     "This variable provides the component's string name for
      use with the ASCII Console Interface"
::= { mscLpFiLtFbMacTrRowStatusEntry 2 }

mscLpFiLtFbMacTrStorageType OBJECT-TYPE
   SYNTAX     StorageType 
   ACCESS     read-only
   STATUS     mandatory
   DESCRIPTION
     "This variable represents the storage type value for the
      mscLpFiLtFbMacTr tables."
::= { mscLpFiLtFbMacTrRowStatusEntry 4 }

mscLpFiLtFbMacTrIndex OBJECT-TYPE
   SYNTAX     NonReplicated 
   ACCESS     not-accessible
   STATUS     mandatory
   DESCRIPTION
     "This variable represents the index for the mscLpFiLtFbMacTr tables."
::= { mscLpFiLtFbMacTrRowStatusEntry 10 }

mscLpFiLtFbMacTrTopTable OBJECT-TYPE
   SYNTAX     SEQUENCE OF MscLpFiLtFbMacTrTopEntry
   ACCESS     not-accessible
   STATUS     mandatory
   DESCRIPTION
     "This group contains the operational data for the LanTest component 
      and its subcomponents."
::= { mscLpFiLtFbMacTr 10 }

mscLpFiLtFbMacTrTopEntry OBJECT-TYPE
   SYNTAX     MscLpFiLtFbMacTrTopEntry
   ACCESS     not-accessible
   STATUS     mandatory
   DESCRIPTION
     "An entry in the mscLpFiLtFbMacTrTopTable."
   INDEX {
      mscLpIndex,
      mscLpFiIndex,
      mscLpFiLtIndex,
      mscLpFiLtFbIndex,
      mscLpFiLtFbMacTrIndex }
::= { mscLpFiLtFbMacTrTopTable 1 }

MscLpFiLtFbMacTrTopEntry ::= SEQUENCE {
   mscLpFiLtFbMacTrTData
      AsciiString }

mscLpFiLtFbMacTrTData OBJECT-TYPE
   SYNTAX     AsciiString (SIZE (0..255))
   ACCESS     read-write
   STATUS     mandatory
   DESCRIPTION
     "This attribute is used to display and set attributes."
::= { mscLpFiLtFbMacTrTopEntry 1 }


-- This component adds a data field to frame.

mscLpFiLtFbData OBJECT IDENTIFIER ::= { mscLpFiLtFb 6 }



mscLpFiLtFbDataRowStatusTable OBJECT-TYPE
   SYNTAX     SEQUENCE OF MscLpFiLtFbDataRowStatusEntry
   ACCESS     not-accessible
   STATUS     mandatory
   DESCRIPTION
     "This entry controls the addition and deletion of 
      mscLpFiLtFbData components."
::= { mscLpFiLtFbData 1 }

mscLpFiLtFbDataRowStatusEntry OBJECT-TYPE
   SYNTAX     MscLpFiLtFbDataRowStatusEntry
   ACCESS     not-accessible
   STATUS     mandatory
   DESCRIPTION
     "A single entry in the table represents a single 
      mscLpFiLtFbData component."
   INDEX {
      mscLpIndex,
      mscLpFiIndex,
      mscLpFiLtIndex,
      mscLpFiLtFbIndex,
      mscLpFiLtFbDataIndex }
::= { mscLpFiLtFbDataRowStatusTable 1 }

MscLpFiLtFbDataRowStatusEntry ::= SEQUENCE {
   mscLpFiLtFbDataRowStatus
      RowStatus,
   mscLpFiLtFbDataComponentName
      DisplayString,
   mscLpFiLtFbDataStorageType
      StorageType,
   mscLpFiLtFbDataIndex
      NonReplicated }

mscLpFiLtFbDataRowStatus OBJECT-TYPE
   SYNTAX     RowStatus 
   ACCESS     read-only
   STATUS     mandatory
   DESCRIPTION
     "This variable is used as the basis for SNMP naming of
      mscLpFiLtFbData components.
      These components cannot be added nor deleted."
::= { mscLpFiLtFbDataRowStatusEntry 1 }

mscLpFiLtFbDataComponentName OBJECT-TYPE
   SYNTAX     DisplayString 
   ACCESS     read-only
   STATUS     mandatory
   DESCRIPTION
     "This variable provides the component's string name for
      use with the ASCII Console Interface"
::= { mscLpFiLtFbDataRowStatusEntry 2 }

mscLpFiLtFbDataStorageType OBJECT-TYPE
   SYNTAX     StorageType 
   ACCESS     read-only
   STATUS     mandatory
   DESCRIPTION
     "This variable represents the storage type value for the
      mscLpFiLtFbData tables."
::= { mscLpFiLtFbDataRowStatusEntry 4 }

mscLpFiLtFbDataIndex OBJECT-TYPE
   SYNTAX     NonReplicated 
   ACCESS     not-accessible
   STATUS     mandatory
   DESCRIPTION
     "This variable represents the index for the mscLpFiLtFbData tables."
::= { mscLpFiLtFbDataRowStatusEntry 10 }

mscLpFiLtFbDataTopTable OBJECT-TYPE
   SYNTAX     SEQUENCE OF MscLpFiLtFbDataTopEntry
   ACCESS     not-accessible
   STATUS     mandatory
   DESCRIPTION
     "This group contains the operational data for the LanTest component 
      and its subcomponents."
::= { mscLpFiLtFbData 10 }

mscLpFiLtFbDataTopEntry OBJECT-TYPE
   SYNTAX     MscLpFiLtFbDataTopEntry
   ACCESS     not-accessible
   STATUS     mandatory
   DESCRIPTION
     "An entry in the mscLpFiLtFbDataTopTable."
   INDEX {
      mscLpIndex,
      mscLpFiIndex,
      mscLpFiLtIndex,
      mscLpFiLtFbIndex,
      mscLpFiLtFbDataIndex }
::= { mscLpFiLtFbDataTopTable 1 }

MscLpFiLtFbDataTopEntry ::= SEQUENCE {
   mscLpFiLtFbDataTData
      AsciiString }

mscLpFiLtFbDataTData OBJECT-TYPE
   SYNTAX     AsciiString (SIZE (0..255))
   ACCESS     read-write
   STATUS     mandatory
   DESCRIPTION
     "This attribute is used to display and set attributes."
::= { mscLpFiLtFbDataTopEntry 1 }


-- LanTest IpHeader
-- This component adds an IP header to a frame or packet.

mscLpFiLtFbIpH OBJECT IDENTIFIER ::= { mscLpFiLtFb 7 }



mscLpFiLtFbIpHRowStatusTable OBJECT-TYPE
   SYNTAX     SEQUENCE OF MscLpFiLtFbIpHRowStatusEntry
   ACCESS     not-accessible
   STATUS     mandatory
   DESCRIPTION
     "This entry controls the addition and deletion of 
      mscLpFiLtFbIpH components."
::= { mscLpFiLtFbIpH 1 }

mscLpFiLtFbIpHRowStatusEntry OBJECT-TYPE
   SYNTAX     MscLpFiLtFbIpHRowStatusEntry
   ACCESS     not-accessible
   STATUS     mandatory
   DESCRIPTION
     "A single entry in the table represents a single 
      mscLpFiLtFbIpH component."
   INDEX {
      mscLpIndex,
      mscLpFiIndex,
      mscLpFiLtIndex,
      mscLpFiLtFbIndex,
      mscLpFiLtFbIpHIndex }
::= { mscLpFiLtFbIpHRowStatusTable 1 }

MscLpFiLtFbIpHRowStatusEntry ::= SEQUENCE {
   mscLpFiLtFbIpHRowStatus
      RowStatus,
   mscLpFiLtFbIpHComponentName
      DisplayString,
   mscLpFiLtFbIpHStorageType
      StorageType,
   mscLpFiLtFbIpHIndex
      NonReplicated }

mscLpFiLtFbIpHRowStatus OBJECT-TYPE
   SYNTAX     RowStatus 
   ACCESS     read-only
   STATUS     mandatory
   DESCRIPTION
     "This variable is used as the basis for SNMP naming of
      mscLpFiLtFbIpH components.
      These components cannot be added nor deleted."
::= { mscLpFiLtFbIpHRowStatusEntry 1 }

mscLpFiLtFbIpHComponentName OBJECT-TYPE
   SYNTAX     DisplayString 
   ACCESS     read-only
   STATUS     mandatory
   DESCRIPTION
     "This variable provides the component's string name for
      use with the ASCII Console Interface"
::= { mscLpFiLtFbIpHRowStatusEntry 2 }

mscLpFiLtFbIpHStorageType OBJECT-TYPE
   SYNTAX     StorageType 
   ACCESS     read-only
   STATUS     mandatory
   DESCRIPTION
     "This variable represents the storage type value for the
      mscLpFiLtFbIpH tables."
::= { mscLpFiLtFbIpHRowStatusEntry 4 }

mscLpFiLtFbIpHIndex OBJECT-TYPE
   SYNTAX     NonReplicated 
   ACCESS     not-accessible
   STATUS     mandatory
   DESCRIPTION
     "This variable represents the index for the mscLpFiLtFbIpH tables."
::= { mscLpFiLtFbIpHRowStatusEntry 10 }

mscLpFiLtFbIpHTopTable OBJECT-TYPE
   SYNTAX     SEQUENCE OF MscLpFiLtFbIpHTopEntry
   ACCESS     not-accessible
   STATUS     mandatory
   DESCRIPTION
     "This group contains the operational data for the LanTest component 
      and its subcomponents."
::= { mscLpFiLtFbIpH 10 }

mscLpFiLtFbIpHTopEntry OBJECT-TYPE
   SYNTAX     MscLpFiLtFbIpHTopEntry
   ACCESS     not-accessible
   STATUS     mandatory
   DESCRIPTION
     "An entry in the mscLpFiLtFbIpHTopTable."
   INDEX {
      mscLpIndex,
      mscLpFiIndex,
      mscLpFiLtIndex,
      mscLpFiLtFbIndex,
      mscLpFiLtFbIpHIndex }
::= { mscLpFiLtFbIpHTopTable 1 }

MscLpFiLtFbIpHTopEntry ::= SEQUENCE {
   mscLpFiLtFbIpHTData
      AsciiString }

mscLpFiLtFbIpHTData OBJECT-TYPE
   SYNTAX     AsciiString (SIZE (0..255))
   ACCESS     read-write
   STATUS     mandatory
   DESCRIPTION
     "This attribute is used to display and set attributes."
::= { mscLpFiLtFbIpHTopEntry 1 }


-- LanTest LlcHeader
-- This component adds an LLC 802.2 or Ethernet header to a frame 
-- or packet.

mscLpFiLtFbLlch OBJECT IDENTIFIER ::= { mscLpFiLtFb 8 }



mscLpFiLtFbLlchRowStatusTable OBJECT-TYPE
   SYNTAX     SEQUENCE OF MscLpFiLtFbLlchRowStatusEntry
   ACCESS     not-accessible
   STATUS     mandatory
   DESCRIPTION
     "This entry controls the addition and deletion of 
      mscLpFiLtFbLlch components."
::= { mscLpFiLtFbLlch 1 }

mscLpFiLtFbLlchRowStatusEntry OBJECT-TYPE
   SYNTAX     MscLpFiLtFbLlchRowStatusEntry
   ACCESS     not-accessible
   STATUS     mandatory
   DESCRIPTION
     "A single entry in the table represents a single 
      mscLpFiLtFbLlch component."
   INDEX {
      mscLpIndex,
      mscLpFiIndex,
      mscLpFiLtIndex,
      mscLpFiLtFbIndex,
      mscLpFiLtFbLlchIndex }
::= { mscLpFiLtFbLlchRowStatusTable 1 }

MscLpFiLtFbLlchRowStatusEntry ::= SEQUENCE {
   mscLpFiLtFbLlchRowStatus
      RowStatus,
   mscLpFiLtFbLlchComponentName
      DisplayString,
   mscLpFiLtFbLlchStorageType
      StorageType,
   mscLpFiLtFbLlchIndex
      NonReplicated }

mscLpFiLtFbLlchRowStatus OBJECT-TYPE
   SYNTAX     RowStatus 
   ACCESS     read-only
   STATUS     mandatory
   DESCRIPTION
     "This variable is used as the basis for SNMP naming of
      mscLpFiLtFbLlch components.
      These components cannot be added nor deleted."
::= { mscLpFiLtFbLlchRowStatusEntry 1 }

mscLpFiLtFbLlchComponentName OBJECT-TYPE
   SYNTAX     DisplayString 
   ACCESS     read-only
   STATUS     mandatory
   DESCRIPTION
     "This variable provides the component's string name for
      use with the ASCII Console Interface"
::= { mscLpFiLtFbLlchRowStatusEntry 2 }

mscLpFiLtFbLlchStorageType OBJECT-TYPE
   SYNTAX     StorageType 
   ACCESS     read-only
   STATUS     mandatory
   DESCRIPTION
     "This variable represents the storage type value for the
      mscLpFiLtFbLlch tables."
::= { mscLpFiLtFbLlchRowStatusEntry 4 }

mscLpFiLtFbLlchIndex OBJECT-TYPE
   SYNTAX     NonReplicated 
   ACCESS     not-accessible
   STATUS     mandatory
   DESCRIPTION
     "This variable represents the index for the mscLpFiLtFbLlch tables."
::= { mscLpFiLtFbLlchRowStatusEntry 10 }

mscLpFiLtFbLlchTopTable OBJECT-TYPE
   SYNTAX     SEQUENCE OF MscLpFiLtFbLlchTopEntry
   ACCESS     not-accessible
   STATUS     mandatory
   DESCRIPTION
     "This group contains the operational data for the LanTest component 
      and its subcomponents."
::= { mscLpFiLtFbLlch 10 }

mscLpFiLtFbLlchTopEntry OBJECT-TYPE
   SYNTAX     MscLpFiLtFbLlchTopEntry
   ACCESS     not-accessible
   STATUS     mandatory
   DESCRIPTION
     "An entry in the mscLpFiLtFbLlchTopTable."
   INDEX {
      mscLpIndex,
      mscLpFiIndex,
      mscLpFiLtIndex,
      mscLpFiLtFbIndex,
      mscLpFiLtFbLlchIndex }
::= { mscLpFiLtFbLlchTopTable 1 }

MscLpFiLtFbLlchTopEntry ::= SEQUENCE {
   mscLpFiLtFbLlchTData
      AsciiString }

mscLpFiLtFbLlchTData OBJECT-TYPE
   SYNTAX     AsciiString (SIZE (0..255))
   ACCESS     read-write
   STATUS     mandatory
   DESCRIPTION
     "This attribute is used to display and set attributes."
::= { mscLpFiLtFbLlchTopEntry 1 }


-- This component adds an AppleTalk header to a frame or packet.

mscLpFiLtFbAppleH OBJECT IDENTIFIER ::= { mscLpFiLtFb 9 }



mscLpFiLtFbAppleHRowStatusTable OBJECT-TYPE
   SYNTAX     SEQUENCE OF MscLpFiLtFbAppleHRowStatusEntry
   ACCESS     not-accessible
   STATUS     mandatory
   DESCRIPTION
     "This entry controls the addition and deletion of 
      mscLpFiLtFbAppleH components."
::= { mscLpFiLtFbAppleH 1 }

mscLpFiLtFbAppleHRowStatusEntry OBJECT-TYPE
   SYNTAX     MscLpFiLtFbAppleHRowStatusEntry
   ACCESS     not-accessible
   STATUS     mandatory
   DESCRIPTION
     "A single entry in the table represents a single 
      mscLpFiLtFbAppleH component."
   INDEX {
      mscLpIndex,
      mscLpFiIndex,
      mscLpFiLtIndex,
      mscLpFiLtFbIndex,
      mscLpFiLtFbAppleHIndex }
::= { mscLpFiLtFbAppleHRowStatusTable 1 }

MscLpFiLtFbAppleHRowStatusEntry ::= SEQUENCE {
   mscLpFiLtFbAppleHRowStatus
      RowStatus,
   mscLpFiLtFbAppleHComponentName
      DisplayString,
   mscLpFiLtFbAppleHStorageType
      StorageType,
   mscLpFiLtFbAppleHIndex
      NonReplicated }

mscLpFiLtFbAppleHRowStatus OBJECT-TYPE
   SYNTAX     RowStatus 
   ACCESS     read-only
   STATUS     mandatory
   DESCRIPTION
     "This variable is used as the basis for SNMP naming of
      mscLpFiLtFbAppleH components.
      These components cannot be added nor deleted."
::= { mscLpFiLtFbAppleHRowStatusEntry 1 }

mscLpFiLtFbAppleHComponentName OBJECT-TYPE
   SYNTAX     DisplayString 
   ACCESS     read-only
   STATUS     mandatory
   DESCRIPTION
     "This variable provides the component's string name for
      use with the ASCII Console Interface"
::= { mscLpFiLtFbAppleHRowStatusEntry 2 }

mscLpFiLtFbAppleHStorageType OBJECT-TYPE
   SYNTAX     StorageType 
   ACCESS     read-only
   STATUS     mandatory
   DESCRIPTION
     "This variable represents the storage type value for the
      mscLpFiLtFbAppleH tables."
::= { mscLpFiLtFbAppleHRowStatusEntry 4 }

mscLpFiLtFbAppleHIndex OBJECT-TYPE
   SYNTAX     NonReplicated 
   ACCESS     not-accessible
   STATUS     mandatory
   DESCRIPTION
     "This variable represents the index for the mscLpFiLtFbAppleH tables."
::= { mscLpFiLtFbAppleHRowStatusEntry 10 }

mscLpFiLtFbAppleHTopTable OBJECT-TYPE
   SYNTAX     SEQUENCE OF MscLpFiLtFbAppleHTopEntry
   ACCESS     not-accessible
   STATUS     mandatory
   DESCRIPTION
     "This group contains the operational data for the LanTest component 
      and its subcomponents."
::= { mscLpFiLtFbAppleH 10 }

mscLpFiLtFbAppleHTopEntry OBJECT-TYPE
   SYNTAX     MscLpFiLtFbAppleHTopEntry
   ACCESS     not-accessible
   STATUS     mandatory
   DESCRIPTION
     "An entry in the mscLpFiLtFbAppleHTopTable."
   INDEX {
      mscLpIndex,
      mscLpFiIndex,
      mscLpFiLtIndex,
      mscLpFiLtFbIndex,
      mscLpFiLtFbAppleHIndex }
::= { mscLpFiLtFbAppleHTopTable 1 }

MscLpFiLtFbAppleHTopEntry ::= SEQUENCE {
   mscLpFiLtFbAppleHTData
      AsciiString }

mscLpFiLtFbAppleHTData OBJECT-TYPE
   SYNTAX     AsciiString (SIZE (0..255))
   ACCESS     read-write
   STATUS     mandatory
   DESCRIPTION
     "This attribute is used to display and set attributes."
::= { mscLpFiLtFbAppleHTopEntry 1 }


-- This component adds an IPX header to a frame or packet.

mscLpFiLtFbIpxH OBJECT IDENTIFIER ::= { mscLpFiLtFb 10 }



mscLpFiLtFbIpxHRowStatusTable OBJECT-TYPE
   SYNTAX     SEQUENCE OF MscLpFiLtFbIpxHRowStatusEntry
   ACCESS     not-accessible
   STATUS     mandatory
   DESCRIPTION
     "This entry controls the addition and deletion of 
      mscLpFiLtFbIpxH components."
::= { mscLpFiLtFbIpxH 1 }

mscLpFiLtFbIpxHRowStatusEntry OBJECT-TYPE
   SYNTAX     MscLpFiLtFbIpxHRowStatusEntry
   ACCESS     not-accessible
   STATUS     mandatory
   DESCRIPTION
     "A single entry in the table represents a single 
      mscLpFiLtFbIpxH component."
   INDEX {
      mscLpIndex,
      mscLpFiIndex,
      mscLpFiLtIndex,
      mscLpFiLtFbIndex,
      mscLpFiLtFbIpxHIndex }
::= { mscLpFiLtFbIpxHRowStatusTable 1 }

MscLpFiLtFbIpxHRowStatusEntry ::= SEQUENCE {
   mscLpFiLtFbIpxHRowStatus
      RowStatus,
   mscLpFiLtFbIpxHComponentName
      DisplayString,
   mscLpFiLtFbIpxHStorageType
      StorageType,
   mscLpFiLtFbIpxHIndex
      NonReplicated }

mscLpFiLtFbIpxHRowStatus OBJECT-TYPE
   SYNTAX     RowStatus 
   ACCESS     read-only
   STATUS     mandatory
   DESCRIPTION
     "This variable is used as the basis for SNMP naming of
      mscLpFiLtFbIpxH components.
      These components cannot be added nor deleted."
::= { mscLpFiLtFbIpxHRowStatusEntry 1 }

mscLpFiLtFbIpxHComponentName OBJECT-TYPE
   SYNTAX     DisplayString 
   ACCESS     read-only
   STATUS     mandatory
   DESCRIPTION
     "This variable provides the component's string name for
      use with the ASCII Console Interface"
::= { mscLpFiLtFbIpxHRowStatusEntry 2 }

mscLpFiLtFbIpxHStorageType OBJECT-TYPE
   SYNTAX     StorageType 
   ACCESS     read-only
   STATUS     mandatory
   DESCRIPTION
     "This variable represents the storage type value for the
      mscLpFiLtFbIpxH tables."
::= { mscLpFiLtFbIpxHRowStatusEntry 4 }

mscLpFiLtFbIpxHIndex OBJECT-TYPE
   SYNTAX     NonReplicated 
   ACCESS     not-accessible
   STATUS     mandatory
   DESCRIPTION
     "This variable represents the index for the mscLpFiLtFbIpxH tables."
::= { mscLpFiLtFbIpxHRowStatusEntry 10 }

mscLpFiLtFbIpxHTopTable OBJECT-TYPE
   SYNTAX     SEQUENCE OF MscLpFiLtFbIpxHTopEntry
   ACCESS     not-accessible
   STATUS     mandatory
   DESCRIPTION
     "This group contains the operational data for the LanTest component 
      and its subcomponents."
::= { mscLpFiLtFbIpxH 10 }

mscLpFiLtFbIpxHTopEntry OBJECT-TYPE
   SYNTAX     MscLpFiLtFbIpxHTopEntry
   ACCESS     not-accessible
   STATUS     mandatory
   DESCRIPTION
     "An entry in the mscLpFiLtFbIpxHTopTable."
   INDEX {
      mscLpIndex,
      mscLpFiIndex,
      mscLpFiLtIndex,
      mscLpFiLtFbIndex,
      mscLpFiLtFbIpxHIndex }
::= { mscLpFiLtFbIpxHTopTable 1 }

MscLpFiLtFbIpxHTopEntry ::= SEQUENCE {
   mscLpFiLtFbIpxHTData
      AsciiString }

mscLpFiLtFbIpxHTData OBJECT-TYPE
   SYNTAX     AsciiString (SIZE (0..255))
   ACCESS     read-write
   STATUS     mandatory
   DESCRIPTION
     "This attribute is used to display and set attributes."
::= { mscLpFiLtFbIpxHTopEntry 1 }


-- LanTest Control
-- This component controls the overall testing by telling the 
-- FrameBuild component to start and check the FrameCompare 
-- component to see if the test is complete.

mscLpFiLtCntl OBJECT IDENTIFIER ::= { mscLpFiLt 6 }



mscLpFiLtCntlRowStatusTable OBJECT-TYPE
   SYNTAX     SEQUENCE OF MscLpFiLtCntlRowStatusEntry
   ACCESS     not-accessible
   STATUS     mandatory
   DESCRIPTION
     "This entry controls the addition and deletion of 
      mscLpFiLtCntl components."
::= { mscLpFiLtCntl 1 }

mscLpFiLtCntlRowStatusEntry OBJECT-TYPE
   SYNTAX     MscLpFiLtCntlRowStatusEntry
   ACCESS     not-accessible
   STATUS     mandatory
   DESCRIPTION
     "A single entry in the table represents a single 
      mscLpFiLtCntl component."
   INDEX {
      mscLpIndex,
      mscLpFiIndex,
      mscLpFiLtIndex,
      mscLpFiLtCntlIndex }
::= { mscLpFiLtCntlRowStatusTable 1 }

MscLpFiLtCntlRowStatusEntry ::= SEQUENCE {
   mscLpFiLtCntlRowStatus
      RowStatus,
   mscLpFiLtCntlComponentName
      DisplayString,
   mscLpFiLtCntlStorageType
      StorageType,
   mscLpFiLtCntlIndex
      NonReplicated }

mscLpFiLtCntlRowStatus OBJECT-TYPE
   SYNTAX     RowStatus 
   ACCESS     read-only
   STATUS     mandatory
   DESCRIPTION
     "This variable is used as the basis for SNMP naming of
      mscLpFiLtCntl components.
      These components cannot be added nor deleted."
::= { mscLpFiLtCntlRowStatusEntry 1 }

mscLpFiLtCntlComponentName OBJECT-TYPE
   SYNTAX     DisplayString 
   ACCESS     read-only
   STATUS     mandatory
   DESCRIPTION
     "This variable provides the component's string name for
      use with the ASCII Console Interface"
::= { mscLpFiLtCntlRowStatusEntry 2 }

mscLpFiLtCntlStorageType OBJECT-TYPE
   SYNTAX     StorageType 
   ACCESS     read-only
   STATUS     mandatory
   DESCRIPTION
     "This variable represents the storage type value for the
      mscLpFiLtCntl tables."
::= { mscLpFiLtCntlRowStatusEntry 4 }

mscLpFiLtCntlIndex OBJECT-TYPE
   SYNTAX     NonReplicated 
   ACCESS     not-accessible
   STATUS     mandatory
   DESCRIPTION
     "This variable represents the index for the mscLpFiLtCntl tables."
::= { mscLpFiLtCntlRowStatusEntry 10 }

mscLpFiLtCntlTopTable OBJECT-TYPE
   SYNTAX     SEQUENCE OF MscLpFiLtCntlTopEntry
   ACCESS     not-accessible
   STATUS     mandatory
   DESCRIPTION
     "This group contains the operational data for the LanTest component 
      and its subcomponents."
::= { mscLpFiLtCntl 10 }

mscLpFiLtCntlTopEntry OBJECT-TYPE
   SYNTAX     MscLpFiLtCntlTopEntry
   ACCESS     not-accessible
   STATUS     mandatory
   DESCRIPTION
     "An entry in the mscLpFiLtCntlTopTable."
   INDEX {
      mscLpIndex,
      mscLpFiIndex,
      mscLpFiLtIndex,
      mscLpFiLtCntlIndex }
::= { mscLpFiLtCntlTopTable 1 }

MscLpFiLtCntlTopEntry ::= SEQUENCE {
   mscLpFiLtCntlTData
      AsciiString }

mscLpFiLtCntlTData OBJECT-TYPE
   SYNTAX     AsciiString (SIZE (0..255))
   ACCESS     read-write
   STATUS     mandatory
   DESCRIPTION
     "This attribute is used to display and set attributes."
::= { mscLpFiLtCntlTopEntry 1 }


-- Lp/n Fddi/n Phy/x
-- This component defines an instance of a FDDI port attached to a ring. 
-- Two instances of this component must be provisioned for each hardware 
-- port. Each port must be provisioned prior to inserting into the ring.

mscLpFiPhy OBJECT IDENTIFIER ::= { mscLpFi 3 }



mscLpFiPhyRowStatusTable OBJECT-TYPE
   SYNTAX     SEQUENCE OF MscLpFiPhyRowStatusEntry
   ACCESS     not-accessible
   STATUS     mandatory
   DESCRIPTION
     "This entry controls the addition and deletion of 
      mscLpFiPhy components."
::= { mscLpFiPhy 1 }

mscLpFiPhyRowStatusEntry OBJECT-TYPE
   SYNTAX     MscLpFiPhyRowStatusEntry
   ACCESS     not-accessible
   STATUS     mandatory
   DESCRIPTION
     "A single entry in the table represents a single 
      mscLpFiPhy component."
   INDEX {
      mscLpIndex,
      mscLpFiIndex,
      mscLpFiPhyFddiPhyTypeIndex }
::= { mscLpFiPhyRowStatusTable 1 }

MscLpFiPhyRowStatusEntry ::= SEQUENCE {
   mscLpFiPhyRowStatus
      RowStatus,
   mscLpFiPhyComponentName
      DisplayString,
   mscLpFiPhyStorageType
      StorageType,
   mscLpFiPhyFddiPhyTypeIndex
      INTEGER }

mscLpFiPhyRowStatus OBJECT-TYPE
   SYNTAX     RowStatus 
   ACCESS     read-write
   STATUS     mandatory
   DESCRIPTION
     "This variable is used as the basis for SNMP naming of
      mscLpFiPhy components.
      These components can be added."
::= { mscLpFiPhyRowStatusEntry 1 }

mscLpFiPhyComponentName OBJECT-TYPE
   SYNTAX     DisplayString 
   ACCESS     read-only
   STATUS     mandatory
   DESCRIPTION
     "This variable provides the component's string name for
      use with the ASCII Console Interface"
::= { mscLpFiPhyRowStatusEntry 2 }

mscLpFiPhyStorageType OBJECT-TYPE
   SYNTAX     StorageType 
   ACCESS     read-only
   STATUS     mandatory
   DESCRIPTION
     "This variable represents the storage type value for the
      mscLpFiPhy tables."
::= { mscLpFiPhyRowStatusEntry 4 }

mscLpFiPhyFddiPhyTypeIndex OBJECT-TYPE
   SYNTAX     INTEGER  {
                 a(0),
                 b(1) }
   ACCESS     not-accessible
   STATUS     mandatory
   DESCRIPTION
     "This variable represents the index for the mscLpFiPhy tables."
::= { mscLpFiPhyRowStatusEntry 10 }

mscLpFiPhyProvTable OBJECT-TYPE
   SYNTAX     SEQUENCE OF MscLpFiPhyProvEntry
   ACCESS     not-accessible
   STATUS     mandatory
   DESCRIPTION
     "This group contains the provisionable attributes of the Fddi Phy 
      component."
::= { mscLpFiPhy 10 }

mscLpFiPhyProvEntry OBJECT-TYPE
   SYNTAX     MscLpFiPhyProvEntry
   ACCESS     not-accessible
   STATUS     mandatory
   DESCRIPTION
     "An entry in the mscLpFiPhyProvTable."
   INDEX {
      mscLpIndex,
      mscLpFiIndex,
      mscLpFiPhyFddiPhyTypeIndex }
::= { mscLpFiPhyProvTable 1 }

MscLpFiPhyProvEntry ::= SEQUENCE {
   mscLpFiPhyLerCutoff
      Unsigned32,
   mscLpFiPhyLerAlarm
      Unsigned32,
   mscLpFiPhyLinkErrorMonitor
      INTEGER }

mscLpFiPhyLerCutoff OBJECT-TYPE
   SYNTAX     Unsigned32 (4..15)
   ACCESS     read-write
   STATUS     mandatory
   DESCRIPTION
     "The lerCutoff attribute contains the link error rate estimate at which a 
      link connection will be broken. The values will range from 10**-4 to 
      10**-15. Only the absolute value of the base 10 log is reported."
   DEFVAL     { 7 }
::= { mscLpFiPhyProvEntry 1 }

mscLpFiPhyLerAlarm OBJECT-TYPE
   SYNTAX     Unsigned32 (4..15)
   ACCESS     read-write
   STATUS     mandatory
   DESCRIPTION
     "The lerAlarm attribute contains the link error rate estimate at which a 
      link connection will generate an alarm. The values will range from 
      10**-4 to 10**-15. Only the absolute value of the base 10 log is 
      reported"
   DEFVAL     { 8 }
::= { mscLpFiPhyProvEntry 2 }

mscLpFiPhyLinkErrorMonitor OBJECT-TYPE
   SYNTAX     INTEGER  {
                 enabled(1),
                 disabled(2) }
   ACCESS     read-write
   STATUS     mandatory
   DESCRIPTION
     "The linkErrorMonitor attribute is used to select the state of the link error 
      monitor for the associated Phy component. If enabled, the link error 
      monitor will send the correct test status to the neighboring station. If 
      disabled, the link error monitor will always send a test passed status to 
      the neighboring station."
   DEFVAL     { enabled }
::= { mscLpFiPhyProvEntry 3 }

mscLpFiPhyOperTable OBJECT-TYPE
   SYNTAX     SEQUENCE OF MscLpFiPhyOperEntry
   ACCESS     not-accessible
   STATUS     mandatory
   DESCRIPTION
     "This group contains the operational attributes of the Fddi Phy 
      component."
::= { mscLpFiPhy 11 }

mscLpFiPhyOperEntry OBJECT-TYPE
   SYNTAX     MscLpFiPhyOperEntry
   ACCESS     not-accessible
   STATUS     mandatory
   DESCRIPTION
     "An entry in the mscLpFiPhyOperTable."
   INDEX {
      mscLpIndex,
      mscLpFiIndex,
      mscLpFiPhyFddiPhyTypeIndex }
::= { mscLpFiPhyOperTable 1 }

MscLpFiPhyOperEntry ::= SEQUENCE {
   mscLpFiPhyNeighborType
      INTEGER,
   mscLpFiPhyLctFailCounts
      Counter32,
   mscLpFiPhyLerEstimate
      Unsigned32,
   mscLpFiPhyLemRejectCounts
      Counter32,
   mscLpFiPhyLemCounts
      Counter32,
   mscLpFiPhyPcmState
      INTEGER,
   mscLpFiPhyLerFlag
      INTEGER,
   mscLpFiPhySignalState
      INTEGER,
   mscLpFiPhySignalBitsRcvd
      OCTET STRING,
   mscLpFiPhySignalBitsTxmt
      OCTET STRING }

mscLpFiPhyNeighborType OBJECT-TYPE
   SYNTAX     INTEGER  {
                 a(1),
                 b(2),
                 s(3),
                 m(4),
                 none(5) }
   ACCESS     read-only
   STATUS     mandatory
   DESCRIPTION
     "This attribute indicates the neighbor type of the neighbor physical layer."
::= { mscLpFiPhyOperEntry 4 }

mscLpFiPhyLctFailCounts OBJECT-TYPE
   SYNTAX     Counter32 
   ACCESS     read-only
   STATUS     mandatory
   DESCRIPTION
     "The lctFailCounts attribute contains the number of consecutive times the 
      Link Confidence Test (LCT) has failed. This counter will wrap around 
      after it reaches its maximum value."
::= { mscLpFiPhyOperEntry 13 }

mscLpFiPhyLerEstimate OBJECT-TYPE
   SYNTAX     Unsigned32 (4..15)
   ACCESS     read-only
   STATUS     mandatory
   DESCRIPTION
     "The lerEstimate attribute contains a long term average link error rate. 
      The values will range from 10**-4 to 10**-15. Only the absolute value 
      of the base 10 log is reported"
::= { mscLpFiPhyOperEntry 14 }

mscLpFiPhyLemRejectCounts OBJECT-TYPE
   SYNTAX     Counter32 
   ACCESS     read-only
   STATUS     mandatory
   DESCRIPTION
     "The lemRejectCounts attribute contains the number of times that a link 
      has been rejected. This counter will wrap around after it reaches its 
      maximum value."
::= { mscLpFiPhyOperEntry 15 }

mscLpFiPhyLemCounts OBJECT-TYPE
   SYNTAX     Counter32 
   ACCESS     read-only
   STATUS     mandatory
   DESCRIPTION
     "The lemCounts attribute contains the aggregate link error monitor error 
      count. This counter is set to zero only on station initialization. This 
      counter will wrap around after it reaches its maximum value."
::= { mscLpFiPhyOperEntry 16 }

mscLpFiPhyPcmState OBJECT-TYPE
   SYNTAX     INTEGER  {
                 off(1),
                 break(2),
                 trace(3),
                 connect(4),
                 next(5),
                 signal(6),
                 join(7),
                 verify(8),
                 active(9),
                 maint(10) }
   ACCESS     read-only
   STATUS     mandatory
   DESCRIPTION
     "The pcmState, physical connection manager (PCM), state indicates the 
      current state of the PCM state machine."
::= { mscLpFiPhyOperEntry 18 }

mscLpFiPhyLerFlag OBJECT-TYPE
   SYNTAX     INTEGER  {
                 true(1),
                 false(2) }
   ACCESS     read-only
   STATUS     mandatory
   DESCRIPTION
     "The lerFlag attribute indicates when the link error rate estimate is less 
      than or equal to the link error rate alarm. If true, the value of the link 
      error rate estimate is less than or equal to the link error rate alarm. If 
      false, the value of the link error rate estimate is greater than the link 
      error rate alarm."
::= { mscLpFiPhyOperEntry 20 }

mscLpFiPhySignalState OBJECT-TYPE
   SYNTAX     INTEGER  {
                 escape(0),
                 phyTypeL(1),
                 phyTypeH(2),
                 accept(3),
                 lctLengthL(4),
                 lctLengthH(5),
                 macAvail(6),
                 lctResult(7),
                 macLoop(8),
                 macOnPhy(9),
                 signalingDone(10) }
   ACCESS     read-only
   STATUS     mandatory
   DESCRIPTION
     "The signalState attribute contains the current physical connection 
      manager (PCM) signal bit being transmitted, or was transmitted, during 
      the PCM signal state."
::= { mscLpFiPhyOperEntry 23 }

mscLpFiPhySignalBitsRcvd OBJECT-TYPE
   SYNTAX     OCTET STRING (SIZE (2))
   ACCESS     read-only
   STATUS     mandatory
   DESCRIPTION
     "The signalBitsRcvd attribute contains the current physical connection 
      manager (PCM) signal bits received.

      Description of bits:
      escape(0)
      phyTypeL(1)
      phyTypeH(2)
      accept(3)
      lctLengthL(4)
      lctLengthH(5)
      macAvail(6)
      lctResult(7)
      macLoop(8)
      macOnPhy(9)"
::= { mscLpFiPhyOperEntry 24 }

mscLpFiPhySignalBitsTxmt OBJECT-TYPE
   SYNTAX     OCTET STRING (SIZE (2))
   ACCESS     read-only
   STATUS     mandatory
   DESCRIPTION
     "The signalBitsTxmt attribute contains the current physical connection 
      manager (PCM) signal bits transmitted.

      Description of bits:
      escape(0)
      phyTypeL(1)
      phyTypeH(2)
      accept(3)
      lctLengthL(4)
      lctLengthH(5)
      macAvail(6)
      lctResult(7)
      macLoop(8)
      macOnPhy(9)"
::= { mscLpFiPhyOperEntry 25 }


-- Lp/n Fddi/n Test, or
-- Lp/n Ethernet/n Test, or
-- Lp/n TokenRing/n Test, or
-- Lp/n IlsForwarder/n Test
-- The Test component is used to do StartUp port test for LAN cards.

mscLpFiTest OBJECT IDENTIFIER ::= { mscLpFi 5 }



mscLpFiTestRowStatusTable OBJECT-TYPE
   SYNTAX     SEQUENCE OF MscLpFiTestRowStatusEntry
   ACCESS     not-accessible
   STATUS     mandatory
   DESCRIPTION
     "This entry controls the addition and deletion of 
      mscLpFiTest components."
::= { mscLpFiTest 1 }

mscLpFiTestRowStatusEntry OBJECT-TYPE
   SYNTAX     MscLpFiTestRowStatusEntry
   ACCESS     not-accessible
   STATUS     mandatory
   DESCRIPTION
     "A single entry in the table represents a single 
      mscLpFiTest component."
   INDEX {
      mscLpIndex,
      mscLpFiIndex,
      mscLpFiTestIndex }
::= { mscLpFiTestRowStatusTable 1 }

MscLpFiTestRowStatusEntry ::= SEQUENCE {
   mscLpFiTestRowStatus
      RowStatus,
   mscLpFiTestComponentName
      DisplayString,
   mscLpFiTestStorageType
      StorageType,
   mscLpFiTestIndex
      NonReplicated }

mscLpFiTestRowStatus OBJECT-TYPE
   SYNTAX     RowStatus 
   ACCESS     read-only
   STATUS     mandatory
   DESCRIPTION
     "This variable is used as the basis for SNMP naming of
      mscLpFiTest components.
      These components cannot be added nor deleted."
::= { mscLpFiTestRowStatusEntry 1 }

mscLpFiTestComponentName OBJECT-TYPE
   SYNTAX     DisplayString 
   ACCESS     read-only
   STATUS     mandatory
   DESCRIPTION
     "This variable provides the component's string name for
      use with the ASCII Console Interface"
::= { mscLpFiTestRowStatusEntry 2 }

mscLpFiTestStorageType OBJECT-TYPE
   SYNTAX     StorageType 
   ACCESS     read-only
   STATUS     mandatory
   DESCRIPTION
     "This variable represents the storage type value for the
      mscLpFiTest tables."
::= { mscLpFiTestRowStatusEntry 4 }

mscLpFiTestIndex OBJECT-TYPE
   SYNTAX     NonReplicated 
   ACCESS     not-accessible
   STATUS     mandatory
   DESCRIPTION
     "This variable represents the index for the mscLpFiTest tables."
::= { mscLpFiTestRowStatusEntry 10 }

mscLpFiTestPTOTable OBJECT-TYPE
   SYNTAX     SEQUENCE OF MscLpFiTestPTOEntry
   ACCESS     not-accessible
   STATUS     mandatory
   DESCRIPTION
     "This group contains the operational data for the LanPortTest 
      component."
::= { mscLpFiTest 10 }

mscLpFiTestPTOEntry OBJECT-TYPE
   SYNTAX     MscLpFiTestPTOEntry
   ACCESS     not-accessible
   STATUS     mandatory
   DESCRIPTION
     "An entry in the mscLpFiTestPTOTable."
   INDEX {
      mscLpIndex,
      mscLpFiIndex,
      mscLpFiTestIndex }
::= { mscLpFiTestPTOTable 1 }

MscLpFiTestPTOEntry ::= SEQUENCE {
   mscLpFiTestType
      INTEGER,
   mscLpFiTestFrmSize
      Unsigned32,
   mscLpFiTestDuration
      Unsigned32 }

mscLpFiTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { mscLpFiTestPTOEntry 1 }

mscLpFiTestFrmSize OBJECT-TYPE
   SYNTAX     Unsigned32 (4..4096)
   ACCESS     read-write
   STATUS     mandatory
   DESCRIPTION
     "This attribute defines the size of the test data frames in number of 
      bytes."
   DEFVAL     { 1024 }
::= { mscLpFiTestPTOEntry 2 }

mscLpFiTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpFiTestPTOEntry 3 }

mscLpFiTestResultsTable OBJECT-TYPE
   SYNTAX     SEQUENCE OF MscLpFiTestResultsEntry
   ACCESS     not-accessible
   STATUS     mandatory
   DESCRIPTION
     "This group contains all the statistics related attributes of the Test 
      component."
::= { mscLpFiTest 11 }

mscLpFiTestResultsEntry OBJECT-TYPE
   SYNTAX     MscLpFiTestResultsEntry
   ACCESS     not-accessible
   STATUS     mandatory
   DESCRIPTION
     "An entry in the mscLpFiTestResultsTable."
   INDEX {
      mscLpIndex,
      mscLpFiIndex,
      mscLpFiTestIndex }
::= { mscLpFiTestResultsTable 1 }

MscLpFiTestResultsEntry ::= SEQUENCE {
   mscLpFiTestElapsedTime
      Counter32,
   mscLpFiTestTimeRemaining
      Unsigned32,
   mscLpFiTestCauseOfTermination
      INTEGER,
   mscLpFiTestFrmTx
      PassportCounter64,
   mscLpFiTestBitsTx
      PassportCounter64,
   mscLpFiTestFrmRx
      PassportCounter64,
   mscLpFiTestBitsRx
      PassportCounter64,
   mscLpFiTestErroredFrmRx
      PassportCounter64 }

mscLpFiTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpFiTestResultsEntry 4 }

mscLpFiTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpFiTestResultsEntry 5 }

mscLpFiTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { mscLpFiTestResultsEntry 6 }

mscLpFiTestFrmTx OBJECT-TYPE
   SYNTAX     PassportCounter64 
   ACCESS     read-only
   STATUS     mandatory
   DESCRIPTION
     "This attribute is the total number of frames sent during the test 
      period. This counter is not expected to reach its maximum value."
::= { mscLpFiTestResultsEntry 7 }

mscLpFiTestBitsTx OBJECT-TYPE
   SYNTAX     PassportCounter64 
   ACCESS     read-only
   STATUS     mandatory
   DESCRIPTION
     "This attribute is the total number of bits sent during the test period. 
      This counter is not expected to reach its maximum value."
::= { mscLpFiTestResultsEntry 8 }

mscLpFiTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpFiTestResultsEntry 9 }

mscLpFiTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { mscLpFiTestResultsEntry 10 }

mscLpFiTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { mscLpFiTestResultsEntry 11 }


-- Lp/n TokenRing/n
-- This component defines an instance of a Token Ring interface 
-- attached to a ring. One instance of this component must be created 
-- for each hardware interface. Each interface must be provisioned 
-- prior to inserting into the ring.

mscLpTr OBJECT IDENTIFIER ::= { mscLp 13 }



mscLpTrRowStatusTable OBJECT-TYPE
   SYNTAX     SEQUENCE OF MscLpTrRowStatusEntry
   ACCESS     not-accessible
   STATUS     mandatory
   DESCRIPTION
     "This entry controls the addition and deletion of 
      mscLpTr components."
::= { mscLpTr 1 }

mscLpTrRowStatusEntry OBJECT-TYPE
   SYNTAX     MscLpTrRowStatusEntry
   ACCESS     not-accessible
   STATUS     mandatory
   DESCRIPTION
     "A single entry in the table represents a single 
      mscLpTr component."
   INDEX {
      mscLpIndex,
      mscLpTrIndex }
::= { mscLpTrRowStatusTable 1 }

MscLpTrRowStatusEntry ::= SEQUENCE {
   mscLpTrRowStatus
      RowStatus,
   mscLpTrComponentName
      DisplayString,
   mscLpTrStorageType
      StorageType,
   mscLpTrIndex
      Integer32 }

mscLpTrRowStatus OBJECT-TYPE
   SYNTAX     RowStatus 
   ACCESS     read-write
   STATUS     mandatory
   DESCRIPTION
     "This variable is used as the basis for SNMP naming of
      mscLpTr components.
      These components can be added and deleted."
::= { mscLpTrRowStatusEntry 1 }

mscLpTrComponentName OBJECT-TYPE
   SYNTAX     DisplayString 
   ACCESS     read-only
   STATUS     mandatory
   DESCRIPTION
     "This variable provides the component's string name for
      use with the ASCII Console Interface"
::= { mscLpTrRowStatusEntry 2 }

mscLpTrStorageType OBJECT-TYPE
   SYNTAX     StorageType 
   ACCESS     read-only
   STATUS     mandatory
   DESCRIPTION
     "This variable represents the storage type value for the
      mscLpTr tables."
::= { mscLpTrRowStatusEntry 4 }

mscLpTrIndex OBJECT-TYPE
   SYNTAX     Integer32 (0..5)
   ACCESS     not-accessible
   STATUS     mandatory
   DESCRIPTION
     "This variable represents the index for the mscLpTr tables."
::= { mscLpTrRowStatusEntry 10 }

mscLpTrCidDataTable OBJECT-TYPE
   SYNTAX     SEQUENCE OF MscLpTrCidDataEntry
   ACCESS     not-accessible
   STATUS     mandatory
   DESCRIPTION
     "This group contains the attribute for a component's Customer 
      Identifier (CID). Refer to the attribute description for a detailed 
      explanation of CIDs."
::= { mscLpTr 10 }

mscLpTrCidDataEntry OBJECT-TYPE
   SYNTAX     MscLpTrCidDataEntry
   ACCESS     not-accessible
   STATUS     mandatory
   DESCRIPTION
     "An entry in the mscLpTrCidDataTable."
   INDEX {
      mscLpIndex,
      mscLpTrIndex }
::= { mscLpTrCidDataTable 1 }

MscLpTrCidDataEntry ::= SEQUENCE {
   mscLpTrCustomerIdentifier
      Unsigned32 }

mscLpTrCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpTrCidDataEntry 1 }

mscLpTrIfEntryTable OBJECT-TYPE
   SYNTAX     SEQUENCE OF MscLpTrIfEntryEntry
   ACCESS     not-accessible
   STATUS     mandatory
   DESCRIPTION
     "This group contains the provisionable attributes for the ifEntry."
::= { mscLpTr 11 }

mscLpTrIfEntryEntry OBJECT-TYPE
   SYNTAX     MscLpTrIfEntryEntry
   ACCESS     not-accessible
   STATUS     mandatory
   DESCRIPTION
     "An entry in the mscLpTrIfEntryTable."
   INDEX {
      mscLpIndex,
      mscLpTrIndex }
::= { mscLpTrIfEntryTable 1 }

MscLpTrIfEntryEntry ::= SEQUENCE {
   mscLpTrIfAdminStatus
      INTEGER,
   mscLpTrIfIndex
      InterfaceIndex }

mscLpTrIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpTrIfEntryEntry 1 }

mscLpTrIfIndex OBJECT-TYPE
   SYNTAX     InterfaceIndex (1..65535)
   ACCESS     read-only
   STATUS     mandatory
   DESCRIPTION
     "This is the index for the IfEntry. Its value is automatically initialized 
      during the provisioning process."
::= { mscLpTrIfEntryEntry 2 }

mscLpTrProvTable OBJECT-TYPE
   SYNTAX     SEQUENCE OF MscLpTrProvEntry
   ACCESS     not-accessible
   STATUS     mandatory
   DESCRIPTION
     "This group contains the provisionable attributes of the Token Ring 
      port."
::= { mscLpTr 12 }

mscLpTrProvEntry OBJECT-TYPE
   SYNTAX     MscLpTrProvEntry
   ACCESS     not-accessible
   STATUS     mandatory
   DESCRIPTION
     "An entry in the mscLpTrProvTable."
   INDEX {
      mscLpIndex,
      mscLpTrIndex }
::= { mscLpTrProvTable 1 }

MscLpTrProvEntry ::= SEQUENCE {
   mscLpTrRingSpeed
      INTEGER,
   mscLpTrMonitorParticipate
      INTEGER,
   mscLpTrFunctionalAddress
      MacAddress,
   mscLpTrNodeAddress
      MacAddress,
   mscLpTrGroupAddress
      MacAddress,
   mscLpTrProductId
      AsciiString,
   mscLpTrApplicationFramerName
      Link }

mscLpTrRingSpeed OBJECT-TYPE
   SYNTAX     INTEGER  {
                 fourMegabit(3),
                 sixteenMegabit(4) }
   ACCESS     read-write
   STATUS     mandatory
   DESCRIPTION
     "This attribute indicates the ring speed at the next insertion into the 
      ring. Note that all the interfaces on a ring must operate at the same 
      speed."
   DEFVAL     { sixteenMegabit }
::= { mscLpTrProvEntry 1 }

mscLpTrMonitorParticipate OBJECT-TYPE
   SYNTAX     INTEGER  {
                 true(1),
                 false(2) }
   ACCESS     read-write
   STATUS     mandatory
   DESCRIPTION
     "This attribute determines whether the interface will participate in 
      the active monitor selection process."
   DEFVAL     { false }
::= { mscLpTrProvEntry 2 }

mscLpTrFunctionalAddress OBJECT-TYPE
   SYNTAX     MacAddress (SIZE (6))
   ACCESS     read-write
   STATUS     mandatory
   DESCRIPTION
     "This attribute contains a bit mask of all token ring functional 
      addresses for which this interface will accept frames. The address is 
      displayed in canonical form."
   DEFVAL     { '0300feff8f01'H }
::= { mscLpTrProvEntry 3 }

mscLpTrNodeAddress OBJECT-TYPE
   SYNTAX     MacAddress (SIZE (6))
   ACCESS     read-write
   STATUS     mandatory
   DESCRIPTION
     "This attribute identifies the primary, node specific address 
      recognized by this interface. If an operator does not provision a 
      MAC address, the 			interface will use a predefined, permanently			
      assigned address.
      A valid node address must not be any of the following: a broadcast 
      address, a group address, a functional address or a null address. A 
      node address should be entered in the canonical form."
   DEFVAL     { '000000000000'H }
::= { mscLpTrProvEntry 4 }

mscLpTrGroupAddress OBJECT-TYPE
   SYNTAX     MacAddress (SIZE (6))
   ACCESS     read-write
   STATUS     mandatory
   DESCRIPTION
     "This attribute identifies the group address for 			which this interface 
      will accept frames. The address is displayed in canonical form. For 
      a valid group address, the least significant bit of the first octet 
      should be set to 1. Currently, only one group address can be 
      provisioned for one interface."
   DEFVAL     { '030001000000'H }
::= { mscLpTrProvEntry 5 }

mscLpTrProductId OBJECT-TYPE
   SYNTAX     AsciiString (SIZE (0..18))
   ACCESS     read-write
   STATUS     mandatory
   DESCRIPTION
     "This attribute is used to identify the host system attached to 			this 
      interface. This information is transmitted in response			 to Request 
      Station Attachment MAC frames."
   DEFVAL     { '4c414e20546f6b656e2052696e67'H }  -- "LAN Token Ring"
::= { mscLpTrProvEntry 6 }

mscLpTrApplicationFramerName OBJECT-TYPE
   SYNTAX     Link 
   ACCESS     read-write
   STATUS     mandatory
   DESCRIPTION
     "This attribute contains the component name of a Framer which is 
      associated with the Tr component."
::= { mscLpTrProvEntry 7 }

mscLpTrAdminInfoTable OBJECT-TYPE
   SYNTAX     SEQUENCE OF MscLpTrAdminInfoEntry
   ACCESS     not-accessible
   STATUS     mandatory
   DESCRIPTION
     "This group contains the attributes pertaining to the vendor of the 
      equipment."
::= { mscLpTr 13 }

mscLpTrAdminInfoEntry OBJECT-TYPE
   SYNTAX     MscLpTrAdminInfoEntry
   ACCESS     not-accessible
   STATUS     mandatory
   DESCRIPTION
     "An entry in the mscLpTrAdminInfoTable."
   INDEX {
      mscLpIndex,
      mscLpTrIndex }
::= { mscLpTrAdminInfoTable 1 }

MscLpTrAdminInfoEntry ::= SEQUENCE {
   mscLpTrVendor
      AsciiString,
   mscLpTrCommentText
      AsciiString }

mscLpTrVendor OBJECT-TYPE
   SYNTAX     AsciiString (SIZE (0..20))
   ACCESS     read-write
   STATUS     mandatory
   DESCRIPTION
     "This is the name of the vendor supplying the facility."
::= { mscLpTrAdminInfoEntry 1 }

mscLpTrCommentText OBJECT-TYPE
   SYNTAX     AsciiString (SIZE (0..60))
   ACCESS     read-write
   STATUS     mandatory
   DESCRIPTION
     "Any miscellaneous text about the facility."
::= { mscLpTrAdminInfoEntry 2 }

mscLpTrStateTable OBJECT-TYPE
   SYNTAX     SEQUENCE OF MscLpTrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpTr 15 }

mscLpTrStateEntry OBJECT-TYPE
   SYNTAX     MscLpTrStateEntry
   ACCESS     not-accessible
   STATUS     mandatory
   DESCRIPTION
     "An entry in the mscLpTrStateTable."
   INDEX {
      mscLpIndex,
      mscLpTrIndex }
::= { mscLpTrStateTable 1 }

MscLpTrStateEntry ::= SEQUENCE {
   mscLpTrAdminState
      INTEGER,
   mscLpTrOperationalState
      INTEGER,
   mscLpTrUsageState
      INTEGER }

mscLpTrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpTrStateEntry 1 }

mscLpTrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpTrStateEntry 2 }

mscLpTrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpTrStateEntry 3 }

mscLpTrOperStatusTable OBJECT-TYPE
   SYNTAX     SEQUENCE OF MscLpTrOperStatusEntry
   ACCESS     not-accessible
   STATUS     mandatory
   DESCRIPTION
     "This group includes the Operational Status attribute. This attribute 
      defines the current operational state of this component."
::= { mscLpTr 16 }

mscLpTrOperStatusEntry OBJECT-TYPE
   SYNTAX     MscLpTrOperStatusEntry
   ACCESS     not-accessible
   STATUS     mandatory
   DESCRIPTION
     "An entry in the mscLpTrOperStatusTable."
   INDEX {
      mscLpIndex,
      mscLpTrIndex }
::= { mscLpTrOperStatusTable 1 }

MscLpTrOperStatusEntry ::= SEQUENCE {
   mscLpTrSnmpOperStatus
      INTEGER }

mscLpTrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpTrOperStatusEntry 1 }

mscLpTrOperTable OBJECT-TYPE
   SYNTAX     SEQUENCE OF MscLpTrOperEntry
   ACCESS     not-accessible
   STATUS     mandatory
   DESCRIPTION
     "This group contains the operational attributes of the Token 		Ring 
      component."
::= { mscLpTr 17 }

mscLpTrOperEntry OBJECT-TYPE
   SYNTAX     MscLpTrOperEntry
   ACCESS     not-accessible
   STATUS     mandatory
   DESCRIPTION
     "An entry in the mscLpTrOperTable."
   INDEX {
      mscLpIndex,
      mscLpTrIndex }
::= { mscLpTrOperTable 1 }

MscLpTrOperEntry ::= SEQUENCE {
   mscLpTrMacAddress
      MacAddress,
   mscLpTrRingState
      INTEGER,
   mscLpTrRingStatus
      OCTET STRING,
   mscLpTrRingOpenStatus
      INTEGER,
   mscLpTrUpStream
      MacAddress,
   mscLpTrChipSet
      INTEGER,
   mscLpTrLastTimeBeaconSent
      EnterpriseDateAndTime }

mscLpTrMacAddress OBJECT-TYPE
   SYNTAX     MacAddress (SIZE (6))
   ACCESS     read-only
   STATUS     mandatory
   DESCRIPTION
     "This attribute contains the actual MAC address. The value is 
      assigned by the system if nodeAddress is not provisioned. This 
      address is displayed in canonical form. The non-canonical version 
      of this address is indicated in ncMacAddress."
   DEFVAL     { '000000000000'H }
::= { mscLpTrOperEntry 2 }

mscLpTrRingState OBJECT-TYPE
   SYNTAX     INTEGER  {
                 opened(1),
                 closed(2),
                 opening(3),
                 closing(4),
                 openFailure(5),
                 ringFailure(6) }
   ACCESS     read-only
   STATUS     mandatory
   DESCRIPTION
     "This attribute contains the value of the current interface state with 
      respect to entering or leaving the ring."
   DEFVAL     { ringFailure }
::= { mscLpTrOperEntry 4 }

mscLpTrRingStatus OBJECT-TYPE
   SYNTAX     OCTET STRING (SIZE (3))
   ACCESS     read-only
   STATUS     mandatory
   DESCRIPTION
     "This attribute contains the value of the current interface status after 
      the station has entered the ring. The value is a sum of values, one 
      for each currently applicable condition. Before the station attempts 
      an open this attribute has the value of noStatus.
      noProblems = 0,
      ringRecovery = 32,
      singleStation = 64,
      removeReceived = 256,
      reserved = 512,
      autoRemovalError = 1024,
      lobeWireFault = 2048,
      transmitBeacon = 4096,
      softError = 8192,
      hardError = 16384,
      signalLoss = 32768,
      noStatus = 131072

      Description of bits:
      noProblems(0)
      notused1(1)
      notused2(2)
      notused3(3)
      notused4(4)
      ringRecovery(5)
      singleStation(6)
      notused7(7)
      removeReceived(8)
      reserved(9)
      autoRemovalError(10)
      lobeWireFault(11)
      transmitBeacon(12)
      softError(13)
      hardError(14)
      signalLoss(15)
      notused16(16)
      noStatus(17)"
   DEFVAL     { '000040'H }
::= { mscLpTrOperEntry 5 }

mscLpTrRingOpenStatus OBJECT-TYPE
   SYNTAX     INTEGER  {
                 noOpen(1),
                 badParam(2),
                 lobeFailed(3),
                 signalLoss(4),
                 insertionTimeout(5),
                 ringFailed(6),
                 beaconing(7),
                 duplicateMac(8),
                 requestFailed(9),
                 removeReceived(10),
                 open(11) }
   ACCESS     read-only
   STATUS     mandatory
   DESCRIPTION
     "This attribute indicates what happened the last time the station 
      attempted to enter into the ring."
   DEFVAL     { noOpen }
::= { mscLpTrOperEntry 6 }

mscLpTrUpStream OBJECT-TYPE
   SYNTAX     MacAddress (SIZE (6))
   ACCESS     read-only
   STATUS     mandatory
   DESCRIPTION
     "This attribute is the MAC address of the station's up-stream 
      neighbor. This address is displayed in canonical form. The non-
      canonical version of this address is indicated in ncUpStream."
   DEFVAL     { '000000000000'H }
::= { mscLpTrOperEntry 7 }

mscLpTrChipSet OBJECT-TYPE
   SYNTAX     INTEGER  {
                 ibm16(1),
                 titms380(2),
                 titms380c16(3),
                 titms380c26(4) }
   ACCESS     read-only
   STATUS     mandatory
   DESCRIPTION
     "This attribute identifies the hardware chip set in use by an interface."
   DEFVAL     { titms380c16 }
::= { mscLpTrOperEntry 9 }

mscLpTrLastTimeBeaconSent OBJECT-TYPE
   SYNTAX     EnterpriseDateAndTime (SIZE (0 | 19))
   ACCESS     read-only
   STATUS     mandatory
   DESCRIPTION
     "This attribute indicates the time at which a Beacon frame was last 
      transmitted on this interface."
::= { mscLpTrOperEntry 10 }

mscLpTrStatsTable OBJECT-TYPE
   SYNTAX     SEQUENCE OF MscLpTrStatsEntry
   ACCESS     not-accessible
   STATUS     mandatory
   DESCRIPTION
     "This group contains statistical information for the Token 		Ring port."
::= { mscLpTr 18 }

mscLpTrStatsEntry OBJECT-TYPE
   SYNTAX     MscLpTrStatsEntry
   ACCESS     not-accessible
   STATUS     mandatory
   DESCRIPTION
     "An entry in the mscLpTrStatsTable."
   INDEX {
      mscLpIndex,
      mscLpTrIndex }
::= { mscLpTrStatsTable 1 }

MscLpTrStatsEntry ::= SEQUENCE {
   mscLpTrLineErrors
      Counter32,
   mscLpTrBurstErrors
      Counter32,
   mscLpTrAcErrors
      Counter32,
   mscLpTrAbortTransErrors
      Counter32,
   mscLpTrInternalErrors
      Counter32,
   mscLpTrLostFrameErrors
      Counter32,
   mscLpTrReceiveCongestions
      Counter32,
   mscLpTrFrameCopiedErrors
      Counter32,
   mscLpTrTokenErrors
      Counter32,
   mscLpTrSoftErrors
      Counter32,
   mscLpTrHardErrors
      Counter32,
   mscLpTrSignalLoss
      Counter32,
   mscLpTrTransmitBeacons
      Counter32,
   mscLpTrRingRecoverys
      Counter32,
   mscLpTrLobeWires
      Counter32,
   mscLpTrRemoveRings
      Counter32,
   mscLpTrSingleStation
      Counter32,
   mscLpTrFreqErrors
      Counter32 }

mscLpTrLineErrors OBJECT-TYPE
   SYNTAX     Counter32 
   ACCESS     read-only
   STATUS     mandatory
   DESCRIPTION
     "This attribute contains the number of frames or tokens copied or 
      repeated by a station where there is a non-data bit or a FCS error. 
      This counter wraps around when the maximum value is reached."
::= { mscLpTrStatsEntry 2 }

mscLpTrBurstErrors OBJECT-TYPE
   SYNTAX     Counter32 
   ACCESS     read-only
   STATUS     mandatory
   DESCRIPTION
     "This attribute contains the number of times the station detects the 
      absence of transitions for five consecutive half-bit times. This 
      counter wraps around when the maximum value is reached."
::= { mscLpTrStatsEntry 3 }

mscLpTrAcErrors OBJECT-TYPE
   SYNTAX     Counter32 
   ACCESS     read-only
   STATUS     mandatory
   DESCRIPTION
     "This attribute contains the number of times that a station can not set 
      the AC bits properly. This counter wraps around when the 
      maximum value is reached."
::= { mscLpTrStatsEntry 4 }

mscLpTrAbortTransErrors OBJECT-TYPE
   SYNTAX     Counter32 
   ACCESS     read-only
   STATUS     mandatory
   DESCRIPTION
     "This attribute contains the number of aborted frames. This counter 
      wraps around when the maximum value is reached."
::= { mscLpTrStatsEntry 5 }

mscLpTrInternalErrors OBJECT-TYPE
   SYNTAX     Counter32 
   ACCESS     read-only
   STATUS     mandatory
   DESCRIPTION
     "This attribute contains the number of internal errors. When the 
      value of the counter soars up quickly, it indicates a potential 
      hardware problem. This counter wraps around when the maximum 
      value is reached."
::= { mscLpTrStatsEntry 6 }

mscLpTrLostFrameErrors OBJECT-TYPE
   SYNTAX     Counter32 
   ACCESS     read-only
   STATUS     mandatory
   DESCRIPTION
     "This attribute contains the number of times a station is transmitting 
      and its TRR timer expires. This counter wraps around when the 
      maximum value is reached."
::= { mscLpTrStatsEntry 7 }

mscLpTrReceiveCongestions OBJECT-TYPE
   SYNTAX     Counter32 
   ACCESS     read-only
   STATUS     mandatory
   DESCRIPTION
     "This attribute contains the number of times a station is supposed to 
      receive a frame but cannot due to lack of buffer space. This counter 
      wraps around when the maximum value is reached."
::= { mscLpTrStatsEntry 8 }

mscLpTrFrameCopiedErrors OBJECT-TYPE
   SYNTAX     Counter32 
   ACCESS     read-only
   STATUS     mandatory
   DESCRIPTION
     "This attribute contains the number of times a station receives a 
      frame addressed to its specific address and detects that the A bit is 
      set. This counter wraps around when the maximum value is 
      reached."
::= { mscLpTrStatsEntry 9 }

mscLpTrTokenErrors OBJECT-TYPE
   SYNTAX     Counter32 
   ACCESS     read-only
   STATUS     mandatory
   DESCRIPTION
     "This attribute contains the number of times a station acting as the 
      active monitor recognizes an error condition that needs a token 
      transmission. This counter wraps around when the maximum value 
      is reached."
::= { mscLpTrStatsEntry 10 }

mscLpTrSoftErrors OBJECT-TYPE
   SYNTAX     Counter32 
   ACCESS     read-only
   STATUS     mandatory
   DESCRIPTION
     "This attribute contains the number of soft errors or the number of 
      Report Error Mac frames the station has transmitted. This counter 
      wraps around when the maximum value is reached."
::= { mscLpTrStatsEntry 11 }

mscLpTrHardErrors OBJECT-TYPE
   SYNTAX     Counter32 
   ACCESS     read-only
   STATUS     mandatory
   DESCRIPTION
     "This attribute contains the number of times this interface has 
      detected an immediately recoverable fatal error. This counter wraps 
      around when the maximum value is reached."
::= { mscLpTrStatsEntry 12 }

mscLpTrSignalLoss OBJECT-TYPE
   SYNTAX     Counter32 
   ACCESS     read-only
   STATUS     mandatory
   DESCRIPTION
     "This attribute contains the number of times signal condition has 
      been lost. This counter wraps around when the maximum value is 
      reached."
::= { mscLpTrStatsEntry 13 }

mscLpTrTransmitBeacons OBJECT-TYPE
   SYNTAX     Counter32 
   ACCESS     read-only
   STATUS     mandatory
   DESCRIPTION
     "This attribute contains the number of beacon frames transmitted. 
      This counter wraps around when the maximum value is reached."
::= { mscLpTrStatsEntry 14 }

mscLpTrRingRecoverys OBJECT-TYPE
   SYNTAX     Counter32 
   ACCESS     read-only
   STATUS     mandatory
   DESCRIPTION
     "This attribute contains the number of times the ring has been 
      purged. This counter wraps around when the maximum value is 
      reached."
::= { mscLpTrStatsEntry 15 }

mscLpTrLobeWires OBJECT-TYPE
   SYNTAX     Counter32 
   ACCESS     read-only
   STATUS     mandatory
   DESCRIPTION
     "This attribute contains the number of times the interface has 
      detected a short circuit in the lobe data path. This counter wraps 
      around when the maximum value is reached."
::= { mscLpTrStatsEntry 16 }

mscLpTrRemoveRings OBJECT-TYPE
   SYNTAX     Counter32 
   ACCESS     read-only
   STATUS     mandatory
   DESCRIPTION
     "This attribute contains the number of Remove Ring Station Mac 
      frames received. This counter wraps around when the maximum 
      value is reached."
::= { mscLpTrStatsEntry 17 }

mscLpTrSingleStation OBJECT-TYPE
   SYNTAX     Counter32 
   ACCESS     read-only
   STATUS     mandatory
   DESCRIPTION
     "This attribute contains the number of times the station has 
      determined it is the only one on the ring. This is not necessarily an 
      error. This counter wraps around when the maximum value is 
      reached."
::= { mscLpTrStatsEntry 18 }

mscLpTrFreqErrors OBJECT-TYPE
   SYNTAX     Counter32 
   ACCESS     read-only
   STATUS     mandatory
   DESCRIPTION
     "This attribute contains the number of signal frequency errors 
      detected. This counter wraps around when the maximum value is 
      reached."
::= { mscLpTrStatsEntry 19 }

mscLpTrNcMacOperTable OBJECT-TYPE
   SYNTAX     SEQUENCE OF MscLpTrNcMacOperEntry
   ACCESS     not-accessible
   STATUS     mandatory
   DESCRIPTION
     "This group contains the operational attributes of the TokenRing port 
      component related to non-canonical MAC addresses."
::= { mscLpTr 20 }

mscLpTrNcMacOperEntry OBJECT-TYPE
   SYNTAX     MscLpTrNcMacOperEntry
   ACCESS     not-accessible
   STATUS     mandatory
   DESCRIPTION
     "An entry in the mscLpTrNcMacOperTable."
   INDEX {
      mscLpIndex,
      mscLpTrIndex }
::= { mscLpTrNcMacOperTable 1 }

MscLpTrNcMacOperEntry ::= SEQUENCE {
   mscLpTrNcMacAddress
      MacAddress,
   mscLpTrNcUpStream
      MacAddress }

mscLpTrNcMacAddress OBJECT-TYPE
   SYNTAX     MacAddress (SIZE (6))
   ACCESS     read-only
   STATUS     mandatory
   DESCRIPTION
     "This attribute contains the actual MAC address. The value is 
      assigned by the system if nodeAddress is not provisioned. This 
      address is displayed in non-canonical form. The canonical version 
      of this address is indicated in macAddress."
::= { mscLpTrNcMacOperEntry 1 }

mscLpTrNcUpStream OBJECT-TYPE
   SYNTAX     MacAddress (SIZE (6))
   ACCESS     read-only
   STATUS     mandatory
   DESCRIPTION
     "This attribute is the MAC address of the station's up-stream 
      neighbor. This address is displayed in non-canonical form. The 
      canonical version of this address is indicated in upStream."
::= { mscLpTrNcMacOperEntry 2 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

mscLpTrLt OBJECT IDENTIFIER ::= { mscLpTr 2 }



mscLpTrLtRowStatusTable OBJECT-TYPE
   SYNTAX     SEQUENCE OF MscLpTrLtRowStatusEntry
   ACCESS     not-accessible
   STATUS     mandatory
   DESCRIPTION
     "This entry controls the addition and deletion of 
      mscLpTrLt components."
::= { mscLpTrLt 1 }

mscLpTrLtRowStatusEntry OBJECT-TYPE
   SYNTAX     MscLpTrLtRowStatusEntry
   ACCESS     not-accessible
   STATUS     mandatory
   DESCRIPTION
     "A single entry in the table represents a single 
      mscLpTrLt component."
   INDEX {
      mscLpIndex,
      mscLpTrIndex,
      mscLpTrLtIndex }
::= { mscLpTrLtRowStatusTable 1 }

MscLpTrLtRowStatusEntry ::= SEQUENCE {
   mscLpTrLtRowStatus
      RowStatus,
   mscLpTrLtComponentName
      DisplayString,
   mscLpTrLtStorageType
      StorageType,
   mscLpTrLtIndex
      NonReplicated }

mscLpTrLtRowStatus OBJECT-TYPE
   SYNTAX     RowStatus 
   ACCESS     read-only
   STATUS     mandatory
   DESCRIPTION
     "This variable is used as the basis for SNMP naming of
      mscLpTrLt components.
      These components cannot be added nor deleted."
::= { mscLpTrLtRowStatusEntry 1 }

mscLpTrLtComponentName OBJECT-TYPE
   SYNTAX     DisplayString 
   ACCESS     read-only
   STATUS     mandatory
   DESCRIPTION
     "This variable provides the component's string name for
      use with the ASCII Console Interface"
::= { mscLpTrLtRowStatusEntry 2 }

mscLpTrLtStorageType OBJECT-TYPE
   SYNTAX     StorageType 
   ACCESS     read-only
   STATUS     mandatory
   DESCRIPTION
     "This variable represents the storage type value for the
      mscLpTrLt tables."
::= { mscLpTrLtRowStatusEntry 4 }

mscLpTrLtIndex OBJECT-TYPE
   SYNTAX     NonReplicated 
   ACCESS     not-accessible
   STATUS     mandatory
   DESCRIPTION
     "This variable represents the index for the mscLpTrLt tables."
::= { mscLpTrLtRowStatusEntry 10 }

mscLpTrLtTopTable OBJECT-TYPE
   SYNTAX     SEQUENCE OF MscLpTrLtTopEntry
   ACCESS     not-accessible
   STATUS     mandatory
   DESCRIPTION
     "This group contains the operational data for the LanTest component 
      and its subcomponents."
::= { mscLpTrLt 20 }

mscLpTrLtTopEntry OBJECT-TYPE
   SYNTAX     MscLpTrLtTopEntry
   ACCESS     not-accessible
   STATUS     mandatory
   DESCRIPTION
     "An entry in the mscLpTrLtTopTable."
   INDEX {
      mscLpIndex,
      mscLpTrIndex,
      mscLpTrLtIndex }
::= { mscLpTrLtTopTable 1 }

MscLpTrLtTopEntry ::= SEQUENCE {
   mscLpTrLtTData
      AsciiString }

mscLpTrLtTData OBJECT-TYPE
   SYNTAX     AsciiString (SIZE (0..255))
   ACCESS     read-write
   STATUS     mandatory
   DESCRIPTION
     "This attribute is used to display and set attributes."
::= { mscLpTrLtTopEntry 1 }


-- This component compares frames received from the hardware and 
-- emulator during testing.

mscLpTrLtFrmCmp OBJECT IDENTIFIER ::= { mscLpTrLt 2 }



mscLpTrLtFrmCmpRowStatusTable OBJECT-TYPE
   SYNTAX     SEQUENCE OF MscLpTrLtFrmCmpRowStatusEntry
   ACCESS     not-accessible
   STATUS     mandatory
   DESCRIPTION
     "This entry controls the addition and deletion of 
      mscLpTrLtFrmCmp components."
::= { mscLpTrLtFrmCmp 1 }

mscLpTrLtFrmCmpRowStatusEntry OBJECT-TYPE
   SYNTAX     MscLpTrLtFrmCmpRowStatusEntry
   ACCESS     not-accessible
   STATUS     mandatory
   DESCRIPTION
     "A single entry in the table represents a single 
      mscLpTrLtFrmCmp component."
   INDEX {
      mscLpIndex,
      mscLpTrIndex,
      mscLpTrLtIndex,
      mscLpTrLtFrmCmpIndex }
::= { mscLpTrLtFrmCmpRowStatusTable 1 }

MscLpTrLtFrmCmpRowStatusEntry ::= SEQUENCE {
   mscLpTrLtFrmCmpRowStatus
      RowStatus,
   mscLpTrLtFrmCmpComponentName
      DisplayString,
   mscLpTrLtFrmCmpStorageType
      StorageType,
   mscLpTrLtFrmCmpIndex
      NonReplicated }

mscLpTrLtFrmCmpRowStatus OBJECT-TYPE
   SYNTAX     RowStatus 
   ACCESS     read-only
   STATUS     mandatory
   DESCRIPTION
     "This variable is used as the basis for SNMP naming of
      mscLpTrLtFrmCmp components.
      These components cannot be added nor deleted."
::= { mscLpTrLtFrmCmpRowStatusEntry 1 }

mscLpTrLtFrmCmpComponentName OBJECT-TYPE
   SYNTAX     DisplayString 
   ACCESS     read-only
   STATUS     mandatory
   DESCRIPTION
     "This variable provides the component's string name for
      use with the ASCII Console Interface"
::= { mscLpTrLtFrmCmpRowStatusEntry 2 }

mscLpTrLtFrmCmpStorageType OBJECT-TYPE
   SYNTAX     StorageType 
   ACCESS     read-only
   STATUS     mandatory
   DESCRIPTION
     "This variable represents the storage type value for the
      mscLpTrLtFrmCmp tables."
::= { mscLpTrLtFrmCmpRowStatusEntry 4 }

mscLpTrLtFrmCmpIndex OBJECT-TYPE
   SYNTAX     NonReplicated 
   ACCESS     not-accessible
   STATUS     mandatory
   DESCRIPTION
     "This variable represents the index for the mscLpTrLtFrmCmp tables."
::= { mscLpTrLtFrmCmpRowStatusEntry 10 }

mscLpTrLtFrmCmpTopTable OBJECT-TYPE
   SYNTAX     SEQUENCE OF MscLpTrLtFrmCmpTopEntry
   ACCESS     not-accessible
   STATUS     mandatory
   DESCRIPTION
     "This group contains the operational data for the LanTest component 
      and its subcomponents."
::= { mscLpTrLtFrmCmp 10 }

mscLpTrLtFrmCmpTopEntry OBJECT-TYPE
   SYNTAX     MscLpTrLtFrmCmpTopEntry
   ACCESS     not-accessible
   STATUS     mandatory
   DESCRIPTION
     "An entry in the mscLpTrLtFrmCmpTopTable."
   INDEX {
      mscLpIndex,
      mscLpTrIndex,
      mscLpTrLtIndex,
      mscLpTrLtFrmCmpIndex }
::= { mscLpTrLtFrmCmpTopTable 1 }

MscLpTrLtFrmCmpTopEntry ::= SEQUENCE {
   mscLpTrLtFrmCmpTData
      AsciiString }

mscLpTrLtFrmCmpTData OBJECT-TYPE
   SYNTAX     AsciiString (SIZE (0..255))
   ACCESS     read-write
   STATUS     mandatory
   DESCRIPTION
     "This attribute is used to display and set attributes."
::= { mscLpTrLtFrmCmpTopEntry 1 }


-- This component receives its input from FrameBuild and places it 
-- upon the hardware which sends it to the appropriate emulator.

mscLpTrLtFrmCpy OBJECT IDENTIFIER ::= { mscLpTrLt 3 }



mscLpTrLtFrmCpyRowStatusTable OBJECT-TYPE
   SYNTAX     SEQUENCE OF MscLpTrLtFrmCpyRowStatusEntry
   ACCESS     not-accessible
   STATUS     mandatory
   DESCRIPTION
     "This entry controls the addition and deletion of 
      mscLpTrLtFrmCpy components."
::= { mscLpTrLtFrmCpy 1 }

mscLpTrLtFrmCpyRowStatusEntry OBJECT-TYPE
   SYNTAX     MscLpTrLtFrmCpyRowStatusEntry
   ACCESS     not-accessible
   STATUS     mandatory
   DESCRIPTION
     "A single entry in the table represents a single 
      mscLpTrLtFrmCpy component."
   INDEX {
      mscLpIndex,
      mscLpTrIndex,
      mscLpTrLtIndex,
      mscLpTrLtFrmCpyIndex }
::= { mscLpTrLtFrmCpyRowStatusTable 1 }

MscLpTrLtFrmCpyRowStatusEntry ::= SEQUENCE {
   mscLpTrLtFrmCpyRowStatus
      RowStatus,
   mscLpTrLtFrmCpyComponentName
      DisplayString,
   mscLpTrLtFrmCpyStorageType
      StorageType,
   mscLpTrLtFrmCpyIndex
      NonReplicated }

mscLpTrLtFrmCpyRowStatus OBJECT-TYPE
   SYNTAX     RowStatus 
   ACCESS     read-only
   STATUS     mandatory
   DESCRIPTION
     "This variable is used as the basis for SNMP naming of
      mscLpTrLtFrmCpy components.
      These components cannot be added nor deleted."
::= { mscLpTrLtFrmCpyRowStatusEntry 1 }

mscLpTrLtFrmCpyComponentName OBJECT-TYPE
   SYNTAX     DisplayString 
   ACCESS     read-only
   STATUS     mandatory
   DESCRIPTION
     "This variable provides the component's string name for
      use with the ASCII Console Interface"
::= { mscLpTrLtFrmCpyRowStatusEntry 2 }

mscLpTrLtFrmCpyStorageType OBJECT-TYPE
   SYNTAX     StorageType 
   ACCESS     read-only
   STATUS     mandatory
   DESCRIPTION
     "This variable represents the storage type value for the
      mscLpTrLtFrmCpy tables."
::= { mscLpTrLtFrmCpyRowStatusEntry 4 }

mscLpTrLtFrmCpyIndex OBJECT-TYPE
   SYNTAX     NonReplicated 
   ACCESS     not-accessible
   STATUS     mandatory
   DESCRIPTION
     "This variable represents the index for the mscLpTrLtFrmCpy tables."
::= { mscLpTrLtFrmCpyRowStatusEntry 10 }

mscLpTrLtFrmCpyTopTable OBJECT-TYPE
   SYNTAX     SEQUENCE OF MscLpTrLtFrmCpyTopEntry
   ACCESS     not-accessible
   STATUS     mandatory
   DESCRIPTION
     "This group contains the operational data for the LanTest component 
      and its subcomponents."
::= { mscLpTrLtFrmCpy 10 }

mscLpTrLtFrmCpyTopEntry OBJECT-TYPE
   SYNTAX     MscLpTrLtFrmCpyTopEntry
   ACCESS     not-accessible
   STATUS     mandatory
   DESCRIPTION
     "An entry in the mscLpTrLtFrmCpyTopTable."
   INDEX {
      mscLpIndex,
      mscLpTrIndex,
      mscLpTrLtIndex,
      mscLpTrLtFrmCpyIndex }
::= { mscLpTrLtFrmCpyTopTable 1 }

MscLpTrLtFrmCpyTopEntry ::= SEQUENCE {
   mscLpTrLtFrmCpyTData
      AsciiString }

mscLpTrLtFrmCpyTData OBJECT-TYPE
   SYNTAX     AsciiString (SIZE (0..255))
   ACCESS     read-write
   STATUS     mandatory
   DESCRIPTION
     "This attribute is used to display and set attributes."
::= { mscLpTrLtFrmCpyTopEntry 1 }


-- This component controls the emulator and hardware to ensure 
-- frames output from each will match in FrameCompare.

mscLpTrLtPrtCfg OBJECT IDENTIFIER ::= { mscLpTrLt 4 }



mscLpTrLtPrtCfgRowStatusTable OBJECT-TYPE
   SYNTAX     SEQUENCE OF MscLpTrLtPrtCfgRowStatusEntry
   ACCESS     not-accessible
   STATUS     mandatory
   DESCRIPTION
     "This entry controls the addition and deletion of 
      mscLpTrLtPrtCfg components."
::= { mscLpTrLtPrtCfg 1 }

mscLpTrLtPrtCfgRowStatusEntry OBJECT-TYPE
   SYNTAX     MscLpTrLtPrtCfgRowStatusEntry
   ACCESS     not-accessible
   STATUS     mandatory
   DESCRIPTION
     "A single entry in the table represents a single 
      mscLpTrLtPrtCfg component."
   INDEX {
      mscLpIndex,
      mscLpTrIndex,
      mscLpTrLtIndex,
      mscLpTrLtPrtCfgIndex }
::= { mscLpTrLtPrtCfgRowStatusTable 1 }

MscLpTrLtPrtCfgRowStatusEntry ::= SEQUENCE {
   mscLpTrLtPrtCfgRowStatus
      RowStatus,
   mscLpTrLtPrtCfgComponentName
      DisplayString,
   mscLpTrLtPrtCfgStorageType
      StorageType,
   mscLpTrLtPrtCfgIndex
      NonReplicated }

mscLpTrLtPrtCfgRowStatus OBJECT-TYPE
   SYNTAX     RowStatus 
   ACCESS     read-only
   STATUS     mandatory
   DESCRIPTION
     "This variable is used as the basis for SNMP naming of
      mscLpTrLtPrtCfg components.
      These components cannot be added nor deleted."
::= { mscLpTrLtPrtCfgRowStatusEntry 1 }

mscLpTrLtPrtCfgComponentName OBJECT-TYPE
   SYNTAX     DisplayString 
   ACCESS     read-only
   STATUS     mandatory
   DESCRIPTION
     "This variable provides the component's string name for
      use with the ASCII Console Interface"
::= { mscLpTrLtPrtCfgRowStatusEntry 2 }

mscLpTrLtPrtCfgStorageType OBJECT-TYPE
   SYNTAX     StorageType 
   ACCESS     read-only
   STATUS     mandatory
   DESCRIPTION
     "This variable represents the storage type value for the
      mscLpTrLtPrtCfg tables."
::= { mscLpTrLtPrtCfgRowStatusEntry 4 }

mscLpTrLtPrtCfgIndex OBJECT-TYPE
   SYNTAX     NonReplicated 
   ACCESS     not-accessible
   STATUS     mandatory
   DESCRIPTION
     "This variable represents the index for the mscLpTrLtPrtCfg tables."
::= { mscLpTrLtPrtCfgRowStatusEntry 10 }

mscLpTrLtPrtCfgTopTable OBJECT-TYPE
   SYNTAX     SEQUENCE OF MscLpTrLtPrtCfgTopEntry
   ACCESS     not-accessible
   STATUS     mandatory
   DESCRIPTION
     "This group contains the operational data for the LanTest component 
      and its subcomponents."
::= { mscLpTrLtPrtCfg 10 }

mscLpTrLtPrtCfgTopEntry OBJECT-TYPE
   SYNTAX     MscLpTrLtPrtCfgTopEntry
   ACCESS     not-accessible
   STATUS     mandatory
   DESCRIPTION
     "An entry in the mscLpTrLtPrtCfgTopTable."
   INDEX {
      mscLpIndex,
      mscLpTrIndex,
      mscLpTrLtIndex,
      mscLpTrLtPrtCfgIndex }
::= { mscLpTrLtPrtCfgTopTable 1 }

MscLpTrLtPrtCfgTopEntry ::= SEQUENCE {
   mscLpTrLtPrtCfgTData
      AsciiString }

mscLpTrLtPrtCfgTData OBJECT-TYPE
   SYNTAX     AsciiString (SIZE (0..255))
   ACCESS     read-write
   STATUS     mandatory
   DESCRIPTION
     "This attribute is used to display and set attributes."
::= { mscLpTrLtPrtCfgTopEntry 1 }


-- LanTest Framebuild
-- This component controls the building of all frames built and sent by 
-- the LanTest component. Each component under FrameBuild builds 
-- a portion of a packet or frame.

mscLpTrLtFb OBJECT IDENTIFIER ::= { mscLpTrLt 5 }



mscLpTrLtFbRowStatusTable OBJECT-TYPE
   SYNTAX     SEQUENCE OF MscLpTrLtFbRowStatusEntry
   ACCESS     not-accessible
   STATUS     mandatory
   DESCRIPTION
     "This entry controls the addition and deletion of 
      mscLpTrLtFb components."
::= { mscLpTrLtFb 1 }

mscLpTrLtFbRowStatusEntry OBJECT-TYPE
   SYNTAX     MscLpTrLtFbRowStatusEntry
   ACCESS     not-accessible
   STATUS     mandatory
   DESCRIPTION
     "A single entry in the table represents a single 
      mscLpTrLtFb component."
   INDEX {
      mscLpIndex,
      mscLpTrIndex,
      mscLpTrLtIndex,
      mscLpTrLtFbIndex }
::= { mscLpTrLtFbRowStatusTable 1 }

MscLpTrLtFbRowStatusEntry ::= SEQUENCE {
   mscLpTrLtFbRowStatus
      RowStatus,
   mscLpTrLtFbComponentName
      DisplayString,
   mscLpTrLtFbStorageType
      StorageType,
   mscLpTrLtFbIndex
      NonReplicated }

mscLpTrLtFbRowStatus OBJECT-TYPE
   SYNTAX     RowStatus 
   ACCESS     read-only
   STATUS     mandatory
   DESCRIPTION
     "This variable is used as the basis for SNMP naming of
      mscLpTrLtFb components.
      These components cannot be added nor deleted."
::= { mscLpTrLtFbRowStatusEntry 1 }

mscLpTrLtFbComponentName OBJECT-TYPE
   SYNTAX     DisplayString 
   ACCESS     read-only
   STATUS     mandatory
   DESCRIPTION
     "This variable provides the component's string name for
      use with the ASCII Console Interface"
::= { mscLpTrLtFbRowStatusEntry 2 }

mscLpTrLtFbStorageType OBJECT-TYPE
   SYNTAX     StorageType 
   ACCESS     read-only
   STATUS     mandatory
   DESCRIPTION
     "This variable represents the storage type value for the
      mscLpTrLtFb tables."
::= { mscLpTrLtFbRowStatusEntry 4 }

mscLpTrLtFbIndex OBJECT-TYPE
   SYNTAX     NonReplicated 
   ACCESS     not-accessible
   STATUS     mandatory
   DESCRIPTION
     "This variable represents the index for the mscLpTrLtFb tables."
::= { mscLpTrLtFbRowStatusEntry 10 }

mscLpTrLtFbTopTable OBJECT-TYPE
   SYNTAX     SEQUENCE OF MscLpTrLtFbTopEntry
   ACCESS     not-accessible
   STATUS     mandatory
   DESCRIPTION
     "This group contains the operational data for the LanTest component 
      and its subcomponents."
::= { mscLpTrLtFb 20 }

mscLpTrLtFbTopEntry OBJECT-TYPE
   SYNTAX     MscLpTrLtFbTopEntry
   ACCESS     not-accessible
   STATUS     mandatory
   DESCRIPTION
     "An entry in the mscLpTrLtFbTopTable."
   INDEX {
      mscLpIndex,
      mscLpTrIndex,
      mscLpTrLtIndex,
      mscLpTrLtFbIndex }
::= { mscLpTrLtFbTopTable 1 }

MscLpTrLtFbTopEntry ::= SEQUENCE {
   mscLpTrLtFbTData
      AsciiString }

mscLpTrLtFbTData OBJECT-TYPE
   SYNTAX     AsciiString (SIZE (0..255))
   ACCESS     read-write
   STATUS     mandatory
   DESCRIPTION
     "This attribute is used to display and set attributes."
::= { mscLpTrLtFbTopEntry 1 }


-- LanTest TransmitInfo
-- This component builds a transmit header which is attached to all 
-- frames transmitted on LAN interfaces.

mscLpTrLtFbTxInfo OBJECT IDENTIFIER ::= { mscLpTrLtFb 2 }



mscLpTrLtFbTxInfoRowStatusTable OBJECT-TYPE
   SYNTAX     SEQUENCE OF MscLpTrLtFbTxInfoRowStatusEntry
   ACCESS     not-accessible
   STATUS     mandatory
   DESCRIPTION
     "This entry controls the addition and deletion of 
      mscLpTrLtFbTxInfo components."
::= { mscLpTrLtFbTxInfo 1 }

mscLpTrLtFbTxInfoRowStatusEntry OBJECT-TYPE
   SYNTAX     MscLpTrLtFbTxInfoRowStatusEntry
   ACCESS     not-accessible
   STATUS     mandatory
   DESCRIPTION
     "A single entry in the table represents a single 
      mscLpTrLtFbTxInfo component."
   INDEX {
      mscLpIndex,
      mscLpTrIndex,
      mscLpTrLtIndex,
      mscLpTrLtFbIndex,
      mscLpTrLtFbTxInfoIndex }
::= { mscLpTrLtFbTxInfoRowStatusTable 1 }

MscLpTrLtFbTxInfoRowStatusEntry ::= SEQUENCE {
   mscLpTrLtFbTxInfoRowStatus
      RowStatus,
   mscLpTrLtFbTxInfoComponentName
      DisplayString,
   mscLpTrLtFbTxInfoStorageType
      StorageType,
   mscLpTrLtFbTxInfoIndex
      NonReplicated }

mscLpTrLtFbTxInfoRowStatus OBJECT-TYPE
   SYNTAX     RowStatus 
   ACCESS     read-only
   STATUS     mandatory
   DESCRIPTION
     "This variable is used as the basis for SNMP naming of
      mscLpTrLtFbTxInfo components.
      These components cannot be added nor deleted."
::= { mscLpTrLtFbTxInfoRowStatusEntry 1 }

mscLpTrLtFbTxInfoComponentName OBJECT-TYPE
   SYNTAX     DisplayString 
   ACCESS     read-only
   STATUS     mandatory
   DESCRIPTION
     "This variable provides the component's string name for
      use with the ASCII Console Interface"
::= { mscLpTrLtFbTxInfoRowStatusEntry 2 }

mscLpTrLtFbTxInfoStorageType OBJECT-TYPE
   SYNTAX     StorageType 
   ACCESS     read-only
   STATUS     mandatory
   DESCRIPTION
     "This variable represents the storage type value for the
      mscLpTrLtFbTxInfo tables."
::= { mscLpTrLtFbTxInfoRowStatusEntry 4 }

mscLpTrLtFbTxInfoIndex OBJECT-TYPE
   SYNTAX     NonReplicated 
   ACCESS     not-accessible
   STATUS     mandatory
   DESCRIPTION
     "This variable represents the index for the mscLpTrLtFbTxInfo tables."
::= { mscLpTrLtFbTxInfoRowStatusEntry 10 }

mscLpTrLtFbTxInfoTopTable OBJECT-TYPE
   SYNTAX     SEQUENCE OF MscLpTrLtFbTxInfoTopEntry
   ACCESS     not-accessible
   STATUS     mandatory
   DESCRIPTION
     "This group contains the operational data for the LanTest component 
      and its subcomponents."
::= { mscLpTrLtFbTxInfo 10 }

mscLpTrLtFbTxInfoTopEntry OBJECT-TYPE
   SYNTAX     MscLpTrLtFbTxInfoTopEntry
   ACCESS     not-accessible
   STATUS     mandatory
   DESCRIPTION
     "An entry in the mscLpTrLtFbTxInfoTopTable."
   INDEX {
      mscLpIndex,
      mscLpTrIndex,
      mscLpTrLtIndex,
      mscLpTrLtFbIndex,
      mscLpTrLtFbTxInfoIndex }
::= { mscLpTrLtFbTxInfoTopTable 1 }

MscLpTrLtFbTxInfoTopEntry ::= SEQUENCE {
   mscLpTrLtFbTxInfoTData
      AsciiString }

mscLpTrLtFbTxInfoTData OBJECT-TYPE
   SYNTAX     AsciiString (SIZE (0..255))
   ACCESS     read-write
   STATUS     mandatory
   DESCRIPTION
     "This attribute is used to display and set attributes."
::= { mscLpTrLtFbTxInfoTopEntry 1 }


-- LanTest FddiMac
-- This component builds an FDDI MAC header which is attached to 
-- all FDDI frames.

mscLpTrLtFbFddiMac OBJECT IDENTIFIER ::= { mscLpTrLtFb 3 }



mscLpTrLtFbFddiMacRowStatusTable OBJECT-TYPE
   SYNTAX     SEQUENCE OF MscLpTrLtFbFddiMacRowStatusEntry
   ACCESS     not-accessible
   STATUS     mandatory
   DESCRIPTION
     "This entry controls the addition and deletion of 
      mscLpTrLtFbFddiMac components."
::= { mscLpTrLtFbFddiMac 1 }

mscLpTrLtFbFddiMacRowStatusEntry OBJECT-TYPE
   SYNTAX     MscLpTrLtFbFddiMacRowStatusEntry
   ACCESS     not-accessible
   STATUS     mandatory
   DESCRIPTION
     "A single entry in the table represents a single 
      mscLpTrLtFbFddiMac component."
   INDEX {
      mscLpIndex,
      mscLpTrIndex,
      mscLpTrLtIndex,
      mscLpTrLtFbIndex,
      mscLpTrLtFbFddiMacIndex }
::= { mscLpTrLtFbFddiMacRowStatusTable 1 }

MscLpTrLtFbFddiMacRowStatusEntry ::= SEQUENCE {
   mscLpTrLtFbFddiMacRowStatus
      RowStatus,
   mscLpTrLtFbFddiMacComponentName
      DisplayString,
   mscLpTrLtFbFddiMacStorageType
      StorageType,
   mscLpTrLtFbFddiMacIndex
      NonReplicated }

mscLpTrLtFbFddiMacRowStatus OBJECT-TYPE
   SYNTAX     RowStatus 
   ACCESS     read-only
   STATUS     mandatory
   DESCRIPTION
     "This variable is used as the basis for SNMP naming of
      mscLpTrLtFbFddiMac components.
      These components cannot be added nor deleted."
::= { mscLpTrLtFbFddiMacRowStatusEntry 1 }

mscLpTrLtFbFddiMacComponentName OBJECT-TYPE
   SYNTAX     DisplayString 
   ACCESS     read-only
   STATUS     mandatory
   DESCRIPTION
     "This variable provides the component's string name for
      use with the ASCII Console Interface"
::= { mscLpTrLtFbFddiMacRowStatusEntry 2 }

mscLpTrLtFbFddiMacStorageType OBJECT-TYPE
   SYNTAX     StorageType 
   ACCESS     read-only
   STATUS     mandatory
   DESCRIPTION
     "This variable represents the storage type value for the
      mscLpTrLtFbFddiMac tables."
::= { mscLpTrLtFbFddiMacRowStatusEntry 4 }

mscLpTrLtFbFddiMacIndex OBJECT-TYPE
   SYNTAX     NonReplicated 
   ACCESS     not-accessible
   STATUS     mandatory
   DESCRIPTION
     "This variable represents the index for the mscLpTrLtFbFddiMac tables."
::= { mscLpTrLtFbFddiMacRowStatusEntry 10 }

mscLpTrLtFbFddiMacTopTable OBJECT-TYPE
   SYNTAX     SEQUENCE OF MscLpTrLtFbFddiMacTopEntry
   ACCESS     not-accessible
   STATUS     mandatory
   DESCRIPTION
     "This group contains the operational data for the LanTest component 
      and its subcomponents."
::= { mscLpTrLtFbFddiMac 10 }

mscLpTrLtFbFddiMacTopEntry OBJECT-TYPE
   SYNTAX     MscLpTrLtFbFddiMacTopEntry
   ACCESS     not-accessible
   STATUS     mandatory
   DESCRIPTION
     "An entry in the mscLpTrLtFbFddiMacTopTable."
   INDEX {
      mscLpIndex,
      mscLpTrIndex,
      mscLpTrLtIndex,
      mscLpTrLtFbIndex,
      mscLpTrLtFbFddiMacIndex }
::= { mscLpTrLtFbFddiMacTopTable 1 }

MscLpTrLtFbFddiMacTopEntry ::= SEQUENCE {
   mscLpTrLtFbFddiMacTData
      AsciiString }

mscLpTrLtFbFddiMacTData OBJECT-TYPE
   SYNTAX     AsciiString (SIZE (0..255))
   ACCESS     read-write
   STATUS     mandatory
   DESCRIPTION
     "This attribute is used to display and set attributes."
::= { mscLpTrLtFbFddiMacTopEntry 1 }


-- LanTest EthernetMac
-- This component builds an Ethernet MAC header which is attached 
-- to all Ethernet frames.

mscLpTrLtFbMacEnet OBJECT IDENTIFIER ::= { mscLpTrLtFb 4 }



mscLpTrLtFbMacEnetRowStatusTable OBJECT-TYPE
   SYNTAX     SEQUENCE OF MscLpTrLtFbMacEnetRowStatusEntry
   ACCESS     not-accessible
   STATUS     mandatory
   DESCRIPTION
     "This entry controls the addition and deletion of 
      mscLpTrLtFbMacEnet components."
::= { mscLpTrLtFbMacEnet 1 }

mscLpTrLtFbMacEnetRowStatusEntry OBJECT-TYPE
   SYNTAX     MscLpTrLtFbMacEnetRowStatusEntry
   ACCESS     not-accessible
   STATUS     mandatory
   DESCRIPTION
     "A single entry in the table represents a single 
      mscLpTrLtFbMacEnet component."
   INDEX {
      mscLpIndex,
      mscLpTrIndex,
      mscLpTrLtIndex,
      mscLpTrLtFbIndex,
      mscLpTrLtFbMacEnetIndex }
::= { mscLpTrLtFbMacEnetRowStatusTable 1 }

MscLpTrLtFbMacEnetRowStatusEntry ::= SEQUENCE {
   mscLpTrLtFbMacEnetRowStatus
      RowStatus,
   mscLpTrLtFbMacEnetComponentName
      DisplayString,
   mscLpTrLtFbMacEnetStorageType
      StorageType,
   mscLpTrLtFbMacEnetIndex
      NonReplicated }

mscLpTrLtFbMacEnetRowStatus OBJECT-TYPE
   SYNTAX     RowStatus 
   ACCESS     read-only
   STATUS     mandatory
   DESCRIPTION
     "This variable is used as the basis for SNMP naming of
      mscLpTrLtFbMacEnet components.
      These components cannot be added nor deleted."
::= { mscLpTrLtFbMacEnetRowStatusEntry 1 }

mscLpTrLtFbMacEnetComponentName OBJECT-TYPE
   SYNTAX     DisplayString 
   ACCESS     read-only
   STATUS     mandatory
   DESCRIPTION
     "This variable provides the component's string name for
      use with the ASCII Console Interface"
::= { mscLpTrLtFbMacEnetRowStatusEntry 2 }

mscLpTrLtFbMacEnetStorageType OBJECT-TYPE
   SYNTAX     StorageType 
   ACCESS     read-only
   STATUS     mandatory
   DESCRIPTION
     "This variable represents the storage type value for the
      mscLpTrLtFbMacEnet tables."
::= { mscLpTrLtFbMacEnetRowStatusEntry 4 }

mscLpTrLtFbMacEnetIndex OBJECT-TYPE
   SYNTAX     NonReplicated 
   ACCESS     not-accessible
   STATUS     mandatory
   DESCRIPTION
     "This variable represents the index for the mscLpTrLtFbMacEnet tables."
::= { mscLpTrLtFbMacEnetRowStatusEntry 10 }

mscLpTrLtFbMacEnetTopTable OBJECT-TYPE
   SYNTAX     SEQUENCE OF MscLpTrLtFbMacEnetTopEntry
   ACCESS     not-accessible
   STATUS     mandatory
   DESCRIPTION
     "This group contains the operational data for the LanTest component 
      and its subcomponents."
::= { mscLpTrLtFbMacEnet 10 }

mscLpTrLtFbMacEnetTopEntry OBJECT-TYPE
   SYNTAX     MscLpTrLtFbMacEnetTopEntry
   ACCESS     not-accessible
   STATUS     mandatory
   DESCRIPTION
     "An entry in the mscLpTrLtFbMacEnetTopTable."
   INDEX {
      mscLpIndex,
      mscLpTrIndex,
      mscLpTrLtIndex,
      mscLpTrLtFbIndex,
      mscLpTrLtFbMacEnetIndex }
::= { mscLpTrLtFbMacEnetTopTable 1 }

MscLpTrLtFbMacEnetTopEntry ::= SEQUENCE {
   mscLpTrLtFbMacEnetTData
      AsciiString }

mscLpTrLtFbMacEnetTData OBJECT-TYPE
   SYNTAX     AsciiString (SIZE (0..255))
   ACCESS     read-write
   STATUS     mandatory
   DESCRIPTION
     "This attribute is used to display and set attributes."
::= { mscLpTrLtFbMacEnetTopEntry 1 }


-- LanTest TokenRingMac
-- This component builds a Token Ring MAC header which is attached 
-- to all Token Ring frames.

mscLpTrLtFbMacTr OBJECT IDENTIFIER ::= { mscLpTrLtFb 5 }



mscLpTrLtFbMacTrRowStatusTable OBJECT-TYPE
   SYNTAX     SEQUENCE OF MscLpTrLtFbMacTrRowStatusEntry
   ACCESS     not-accessible
   STATUS     mandatory
   DESCRIPTION
     "This entry controls the addition and deletion of 
      mscLpTrLtFbMacTr components."
::= { mscLpTrLtFbMacTr 1 }

mscLpTrLtFbMacTrRowStatusEntry OBJECT-TYPE
   SYNTAX     MscLpTrLtFbMacTrRowStatusEntry
   ACCESS     not-accessible
   STATUS     mandatory
   DESCRIPTION
     "A single entry in the table represents a single 
      mscLpTrLtFbMacTr component."
   INDEX {
      mscLpIndex,
      mscLpTrIndex,
      mscLpTrLtIndex,
      mscLpTrLtFbIndex,
      mscLpTrLtFbMacTrIndex }
::= { mscLpTrLtFbMacTrRowStatusTable 1 }

MscLpTrLtFbMacTrRowStatusEntry ::= SEQUENCE {
   mscLpTrLtFbMacTrRowStatus
      RowStatus,
   mscLpTrLtFbMacTrComponentName
      DisplayString,
   mscLpTrLtFbMacTrStorageType
      StorageType,
   mscLpTrLtFbMacTrIndex
      NonReplicated }

mscLpTrLtFbMacTrRowStatus OBJECT-TYPE
   SYNTAX     RowStatus 
   ACCESS     read-only
   STATUS     mandatory
   DESCRIPTION
     "This variable is used as the basis for SNMP naming of
      mscLpTrLtFbMacTr components.
      These components cannot be added nor deleted."
::= { mscLpTrLtFbMacTrRowStatusEntry 1 }

mscLpTrLtFbMacTrComponentName OBJECT-TYPE
   SYNTAX     DisplayString 
   ACCESS     read-only
   STATUS     mandatory
   DESCRIPTION
     "This variable provides the component's string name for
      use with the ASCII Console Interface"
::= { mscLpTrLtFbMacTrRowStatusEntry 2 }

mscLpTrLtFbMacTrStorageType OBJECT-TYPE
   SYNTAX     StorageType 
   ACCESS     read-only
   STATUS     mandatory
   DESCRIPTION
     "This variable represents the storage type value for the
      mscLpTrLtFbMacTr tables."
::= { mscLpTrLtFbMacTrRowStatusEntry 4 }

mscLpTrLtFbMacTrIndex OBJECT-TYPE
   SYNTAX     NonReplicated 
   ACCESS     not-accessible
   STATUS     mandatory
   DESCRIPTION
     "This variable represents the index for the mscLpTrLtFbMacTr tables."
::= { mscLpTrLtFbMacTrRowStatusEntry 10 }

mscLpTrLtFbMacTrTopTable OBJECT-TYPE
   SYNTAX     SEQUENCE OF MscLpTrLtFbMacTrTopEntry
   ACCESS     not-accessible
   STATUS     mandatory
   DESCRIPTION
     "This group contains the operational data for the LanTest component 
      and its subcomponents."
::= { mscLpTrLtFbMacTr 10 }

mscLpTrLtFbMacTrTopEntry OBJECT-TYPE
   SYNTAX     MscLpTrLtFbMacTrTopEntry
   ACCESS     not-accessible
   STATUS     mandatory
   DESCRIPTION
     "An entry in the mscLpTrLtFbMacTrTopTable."
   INDEX {
      mscLpIndex,
      mscLpTrIndex,
      mscLpTrLtIndex,
      mscLpTrLtFbIndex,
      mscLpTrLtFbMacTrIndex }
::= { mscLpTrLtFbMacTrTopTable 1 }

MscLpTrLtFbMacTrTopEntry ::= SEQUENCE {
   mscLpTrLtFbMacTrTData
      AsciiString }

mscLpTrLtFbMacTrTData OBJECT-TYPE
   SYNTAX     AsciiString (SIZE (0..255))
   ACCESS     read-write
   STATUS     mandatory
   DESCRIPTION
     "This attribute is used to display and set attributes."
::= { mscLpTrLtFbMacTrTopEntry 1 }


-- This component adds a data field to frame.

mscLpTrLtFbData OBJECT IDENTIFIER ::= { mscLpTrLtFb 6 }



mscLpTrLtFbDataRowStatusTable OBJECT-TYPE
   SYNTAX     SEQUENCE OF MscLpTrLtFbDataRowStatusEntry
   ACCESS     not-accessible
   STATUS     mandatory
   DESCRIPTION
     "This entry controls the addition and deletion of 
      mscLpTrLtFbData components."
::= { mscLpTrLtFbData 1 }

mscLpTrLtFbDataRowStatusEntry OBJECT-TYPE
   SYNTAX     MscLpTrLtFbDataRowStatusEntry
   ACCESS     not-accessible
   STATUS     mandatory
   DESCRIPTION
     "A single entry in the table represents a single 
      mscLpTrLtFbData component."
   INDEX {
      mscLpIndex,
      mscLpTrIndex,
      mscLpTrLtIndex,
      mscLpTrLtFbIndex,
      mscLpTrLtFbDataIndex }
::= { mscLpTrLtFbDataRowStatusTable 1 }

MscLpTrLtFbDataRowStatusEntry ::= SEQUENCE {
   mscLpTrLtFbDataRowStatus
      RowStatus,
   mscLpTrLtFbDataComponentName
      DisplayString,
   mscLpTrLtFbDataStorageType
      StorageType,
   mscLpTrLtFbDataIndex
      NonReplicated }

mscLpTrLtFbDataRowStatus OBJECT-TYPE
   SYNTAX     RowStatus 
   ACCESS     read-only
   STATUS     mandatory
   DESCRIPTION
     "This variable is used as the basis for SNMP naming of
      mscLpTrLtFbData components.
      These components cannot be added nor deleted."
::= { mscLpTrLtFbDataRowStatusEntry 1 }

mscLpTrLtFbDataComponentName OBJECT-TYPE
   SYNTAX     DisplayString 
   ACCESS     read-only
   STATUS     mandatory
   DESCRIPTION
     "This variable provides the component's string name for
      use with the ASCII Console Interface"
::= { mscLpTrLtFbDataRowStatusEntry 2 }

mscLpTrLtFbDataStorageType OBJECT-TYPE
   SYNTAX     StorageType 
   ACCESS     read-only
   STATUS     mandatory
   DESCRIPTION
     "This variable represents the storage type value for the
      mscLpTrLtFbData tables."
::= { mscLpTrLtFbDataRowStatusEntry 4 }

mscLpTrLtFbDataIndex OBJECT-TYPE
   SYNTAX     NonReplicated 
   ACCESS     not-accessible
   STATUS     mandatory
   DESCRIPTION
     "This variable represents the index for the mscLpTrLtFbData tables."
::= { mscLpTrLtFbDataRowStatusEntry 10 }

mscLpTrLtFbDataTopTable OBJECT-TYPE
   SYNTAX     SEQUENCE OF MscLpTrLtFbDataTopEntry
   ACCESS     not-accessible
   STATUS     mandatory
   DESCRIPTION
     "This group contains the operational data for the LanTest component 
      and its subcomponents."
::= { mscLpTrLtFbData 10 }

mscLpTrLtFbDataTopEntry OBJECT-TYPE
   SYNTAX     MscLpTrLtFbDataTopEntry
   ACCESS     not-accessible
   STATUS     mandatory
   DESCRIPTION
     "An entry in the mscLpTrLtFbDataTopTable."
   INDEX {
      mscLpIndex,
      mscLpTrIndex,
      mscLpTrLtIndex,
      mscLpTrLtFbIndex,
      mscLpTrLtFbDataIndex }
::= { mscLpTrLtFbDataTopTable 1 }

MscLpTrLtFbDataTopEntry ::= SEQUENCE {
   mscLpTrLtFbDataTData
      AsciiString }

mscLpTrLtFbDataTData OBJECT-TYPE
   SYNTAX     AsciiString (SIZE (0..255))
   ACCESS     read-write
   STATUS     mandatory
   DESCRIPTION
     "This attribute is used to display and set attributes."
::= { mscLpTrLtFbDataTopEntry 1 }


-- LanTest IpHeader
-- This component adds an IP header to a frame or packet.

mscLpTrLtFbIpH OBJECT IDENTIFIER ::= { mscLpTrLtFb 7 }



mscLpTrLtFbIpHRowStatusTable OBJECT-TYPE
   SYNTAX     SEQUENCE OF MscLpTrLtFbIpHRowStatusEntry
   ACCESS     not-accessible
   STATUS     mandatory
   DESCRIPTION
     "This entry controls the addition and deletion of 
      mscLpTrLtFbIpH components."
::= { mscLpTrLtFbIpH 1 }

mscLpTrLtFbIpHRowStatusEntry OBJECT-TYPE
   SYNTAX     MscLpTrLtFbIpHRowStatusEntry
   ACCESS     not-accessible
   STATUS     mandatory
   DESCRIPTION
     "A single entry in the table represents a single 
      mscLpTrLtFbIpH component."
   INDEX {
      mscLpIndex,
      mscLpTrIndex,
      mscLpTrLtIndex,
      mscLpTrLtFbIndex,
      mscLpTrLtFbIpHIndex }
::= { mscLpTrLtFbIpHRowStatusTable 1 }

MscLpTrLtFbIpHRowStatusEntry ::= SEQUENCE {
   mscLpTrLtFbIpHRowStatus
      RowStatus,
   mscLpTrLtFbIpHComponentName
      DisplayString,
   mscLpTrLtFbIpHStorageType
      StorageType,
   mscLpTrLtFbIpHIndex
      NonReplicated }

mscLpTrLtFbIpHRowStatus OBJECT-TYPE
   SYNTAX     RowStatus 
   ACCESS     read-only
   STATUS     mandatory
   DESCRIPTION
     "This variable is used as the basis for SNMP naming of
      mscLpTrLtFbIpH components.
      These components cannot be added nor deleted."
::= { mscLpTrLtFbIpHRowStatusEntry 1 }

mscLpTrLtFbIpHComponentName OBJECT-TYPE
   SYNTAX     DisplayString 
   ACCESS     read-only
   STATUS     mandatory
   DESCRIPTION
     "This variable provides the component's string name for
      use with the ASCII Console Interface"
::= { mscLpTrLtFbIpHRowStatusEntry 2 }

mscLpTrLtFbIpHStorageType OBJECT-TYPE
   SYNTAX     StorageType 
   ACCESS     read-only
   STATUS     mandatory
   DESCRIPTION
     "This variable represents the storage type value for the
      mscLpTrLtFbIpH tables."
::= { mscLpTrLtFbIpHRowStatusEntry 4 }

mscLpTrLtFbIpHIndex OBJECT-TYPE
   SYNTAX     NonReplicated 
   ACCESS     not-accessible
   STATUS     mandatory
   DESCRIPTION
     "This variable represents the index for the mscLpTrLtFbIpH tables."
::= { mscLpTrLtFbIpHRowStatusEntry 10 }

mscLpTrLtFbIpHTopTable OBJECT-TYPE
   SYNTAX     SEQUENCE OF MscLpTrLtFbIpHTopEntry
   ACCESS     not-accessible
   STATUS     mandatory
   DESCRIPTION
     "This group contains the operational data for the LanTest component 
      and its subcomponents."
::= { mscLpTrLtFbIpH 10 }

mscLpTrLtFbIpHTopEntry OBJECT-TYPE
   SYNTAX     MscLpTrLtFbIpHTopEntry
   ACCESS     not-accessible
   STATUS     mandatory
   DESCRIPTION
     "An entry in the mscLpTrLtFbIpHTopTable."
   INDEX {
      mscLpIndex,
      mscLpTrIndex,
      mscLpTrLtIndex,
      mscLpTrLtFbIndex,
      mscLpTrLtFbIpHIndex }
::= { mscLpTrLtFbIpHTopTable 1 }

MscLpTrLtFbIpHTopEntry ::= SEQUENCE {
   mscLpTrLtFbIpHTData
      AsciiString }

mscLpTrLtFbIpHTData OBJECT-TYPE
   SYNTAX     AsciiString (SIZE (0..255))
   ACCESS     read-write
   STATUS     mandatory
   DESCRIPTION
     "This attribute is used to display and set attributes."
::= { mscLpTrLtFbIpHTopEntry 1 }


-- LanTest LlcHeader
-- This component adds an LLC 802.2 or Ethernet header to a frame 
-- or packet.

mscLpTrLtFbLlch OBJECT IDENTIFIER ::= { mscLpTrLtFb 8 }



mscLpTrLtFbLlchRowStatusTable OBJECT-TYPE
   SYNTAX     SEQUENCE OF MscLpTrLtFbLlchRowStatusEntry
   ACCESS     not-accessible
   STATUS     mandatory
   DESCRIPTION
     "This entry controls the addition and deletion of 
      mscLpTrLtFbLlch components."
::= { mscLpTrLtFbLlch 1 }

mscLpTrLtFbLlchRowStatusEntry OBJECT-TYPE
   SYNTAX     MscLpTrLtFbLlchRowStatusEntry
   ACCESS     not-accessible
   STATUS     mandatory
   DESCRIPTION
     "A single entry in the table represents a single 
      mscLpTrLtFbLlch component."
   INDEX {
      mscLpIndex,
      mscLpTrIndex,
      mscLpTrLtIndex,
      mscLpTrLtFbIndex,
      mscLpTrLtFbLlchIndex }
::= { mscLpTrLtFbLlchRowStatusTable 1 }

MscLpTrLtFbLlchRowStatusEntry ::= SEQUENCE {
   mscLpTrLtFbLlchRowStatus
      RowStatus,
   mscLpTrLtFbLlchComponentName
      DisplayString,
   mscLpTrLtFbLlchStorageType
      StorageType,
   mscLpTrLtFbLlchIndex
      NonReplicated }

mscLpTrLtFbLlchRowStatus OBJECT-TYPE
   SYNTAX     RowStatus 
   ACCESS     read-only
   STATUS     mandatory
   DESCRIPTION
     "This variable is used as the basis for SNMP naming of
      mscLpTrLtFbLlch components.
      These components cannot be added nor deleted."
::= { mscLpTrLtFbLlchRowStatusEntry 1 }

mscLpTrLtFbLlchComponentName OBJECT-TYPE
   SYNTAX     DisplayString 
   ACCESS     read-only
   STATUS     mandatory
   DESCRIPTION
     "This variable provides the component's string name for
      use with the ASCII Console Interface"
::= { mscLpTrLtFbLlchRowStatusEntry 2 }

mscLpTrLtFbLlchStorageType OBJECT-TYPE
   SYNTAX     StorageType 
   ACCESS     read-only
   STATUS     mandatory
   DESCRIPTION
     "This variable represents the storage type value for the
      mscLpTrLtFbLlch tables."
::= { mscLpTrLtFbLlchRowStatusEntry 4 }

mscLpTrLtFbLlchIndex OBJECT-TYPE
   SYNTAX     NonReplicated 
   ACCESS     not-accessible
   STATUS     mandatory
   DESCRIPTION
     "This variable represents the index for the mscLpTrLtFbLlch tables."
::= { mscLpTrLtFbLlchRowStatusEntry 10 }

mscLpTrLtFbLlchTopTable OBJECT-TYPE
   SYNTAX     SEQUENCE OF MscLpTrLtFbLlchTopEntry
   ACCESS     not-accessible
   STATUS     mandatory
   DESCRIPTION
     "This group contains the operational data for the LanTest component 
      and its subcomponents."
::= { mscLpTrLtFbLlch 10 }

mscLpTrLtFbLlchTopEntry OBJECT-TYPE
   SYNTAX     MscLpTrLtFbLlchTopEntry
   ACCESS     not-accessible
   STATUS     mandatory
   DESCRIPTION
     "An entry in the mscLpTrLtFbLlchTopTable."
   INDEX {
      mscLpIndex,
      mscLpTrIndex,
      mscLpTrLtIndex,
      mscLpTrLtFbIndex,
      mscLpTrLtFbLlchIndex }
::= { mscLpTrLtFbLlchTopTable 1 }

MscLpTrLtFbLlchTopEntry ::= SEQUENCE {
   mscLpTrLtFbLlchTData
      AsciiString }

mscLpTrLtFbLlchTData OBJECT-TYPE
   SYNTAX     AsciiString (SIZE (0..255))
   ACCESS     read-write
   STATUS     mandatory
   DESCRIPTION
     "This attribute is used to display and set attributes."
::= { mscLpTrLtFbLlchTopEntry 1 }


-- This component adds an AppleTalk header to a frame or packet.

mscLpTrLtFbAppleH OBJECT IDENTIFIER ::= { mscLpTrLtFb 9 }



mscLpTrLtFbAppleHRowStatusTable OBJECT-TYPE
   SYNTAX     SEQUENCE OF MscLpTrLtFbAppleHRowStatusEntry
   ACCESS     not-accessible
   STATUS     mandatory
   DESCRIPTION
     "This entry controls the addition and deletion of 
      mscLpTrLtFbAppleH components."
::= { mscLpTrLtFbAppleH 1 }

mscLpTrLtFbAppleHRowStatusEntry OBJECT-TYPE
   SYNTAX     MscLpTrLtFbAppleHRowStatusEntry
   ACCESS     not-accessible
   STATUS     mandatory
   DESCRIPTION
     "A single entry in the table represents a single 
      mscLpTrLtFbAppleH component."
   INDEX {
      mscLpIndex,
      mscLpTrIndex,
      mscLpTrLtIndex,
      mscLpTrLtFbIndex,
      mscLpTrLtFbAppleHIndex }
::= { mscLpTrLtFbAppleHRowStatusTable 1 }

MscLpTrLtFbAppleHRowStatusEntry ::= SEQUENCE {
   mscLpTrLtFbAppleHRowStatus
      RowStatus,
   mscLpTrLtFbAppleHComponentName
      DisplayString,
   mscLpTrLtFbAppleHStorageType
      StorageType,
   mscLpTrLtFbAppleHIndex
      NonReplicated }

mscLpTrLtFbAppleHRowStatus OBJECT-TYPE
   SYNTAX     RowStatus 
   ACCESS     read-only
   STATUS     mandatory
   DESCRIPTION
     "This variable is used as the basis for SNMP naming of
      mscLpTrLtFbAppleH components.
      These components cannot be added nor deleted."
::= { mscLpTrLtFbAppleHRowStatusEntry 1 }

mscLpTrLtFbAppleHComponentName OBJECT-TYPE
   SYNTAX     DisplayString 
   ACCESS     read-only
   STATUS     mandatory
   DESCRIPTION
     "This variable provides the component's string name for
      use with the ASCII Console Interface"
::= { mscLpTrLtFbAppleHRowStatusEntry 2 }

mscLpTrLtFbAppleHStorageType OBJECT-TYPE
   SYNTAX     StorageType 
   ACCESS     read-only
   STATUS     mandatory
   DESCRIPTION
     "This variable represents the storage type value for the
      mscLpTrLtFbAppleH tables."
::= { mscLpTrLtFbAppleHRowStatusEntry 4 }

mscLpTrLtFbAppleHIndex OBJECT-TYPE
   SYNTAX     NonReplicated 
   ACCESS     not-accessible
   STATUS     mandatory
   DESCRIPTION
     "This variable represents the index for the mscLpTrLtFbAppleH tables."
::= { mscLpTrLtFbAppleHRowStatusEntry 10 }

mscLpTrLtFbAppleHTopTable OBJECT-TYPE
   SYNTAX     SEQUENCE OF MscLpTrLtFbAppleHTopEntry
   ACCESS     not-accessible
   STATUS     mandatory
   DESCRIPTION
     "This group contains the operational data for the LanTest component 
      and its subcomponents."
::= { mscLpTrLtFbAppleH 10 }

mscLpTrLtFbAppleHTopEntry OBJECT-TYPE
   SYNTAX     MscLpTrLtFbAppleHTopEntry
   ACCESS     not-accessible
   STATUS     mandatory
   DESCRIPTION
     "An entry in the mscLpTrLtFbAppleHTopTable."
   INDEX {
      mscLpIndex,
      mscLpTrIndex,
      mscLpTrLtIndex,
      mscLpTrLtFbIndex,
      mscLpTrLtFbAppleHIndex }
::= { mscLpTrLtFbAppleHTopTable 1 }

MscLpTrLtFbAppleHTopEntry ::= SEQUENCE {
   mscLpTrLtFbAppleHTData
      AsciiString }

mscLpTrLtFbAppleHTData OBJECT-TYPE
   SYNTAX     AsciiString (SIZE (0..255))
   ACCESS     read-write
   STATUS     mandatory
   DESCRIPTION
     "This attribute is used to display and set attributes."
::= { mscLpTrLtFbAppleHTopEntry 1 }


-- This component adds an IPX header to a frame or packet.

mscLpTrLtFbIpxH OBJECT IDENTIFIER ::= { mscLpTrLtFb 10 }



mscLpTrLtFbIpxHRowStatusTable OBJECT-TYPE
   SYNTAX     SEQUENCE OF MscLpTrLtFbIpxHRowStatusEntry
   ACCESS     not-accessible
   STATUS     mandatory
   DESCRIPTION
     "This entry controls the addition and deletion of 
      mscLpTrLtFbIpxH components."
::= { mscLpTrLtFbIpxH 1 }

mscLpTrLtFbIpxHRowStatusEntry OBJECT-TYPE
   SYNTAX     MscLpTrLtFbIpxHRowStatusEntry
   ACCESS     not-accessible
   STATUS     mandatory
   DESCRIPTION
     "A single entry in the table represents a single 
      mscLpTrLtFbIpxH component."
   INDEX {
      mscLpIndex,
      mscLpTrIndex,
      mscLpTrLtIndex,
      mscLpTrLtFbIndex,
      mscLpTrLtFbIpxHIndex }
::= { mscLpTrLtFbIpxHRowStatusTable 1 }

MscLpTrLtFbIpxHRowStatusEntry ::= SEQUENCE {
   mscLpTrLtFbIpxHRowStatus
      RowStatus,
   mscLpTrLtFbIpxHComponentName
      DisplayString,
   mscLpTrLtFbIpxHStorageType
      StorageType,
   mscLpTrLtFbIpxHIndex
      NonReplicated }

mscLpTrLtFbIpxHRowStatus OBJECT-TYPE
   SYNTAX     RowStatus 
   ACCESS     read-only
   STATUS     mandatory
   DESCRIPTION
     "This variable is used as the basis for SNMP naming of
      mscLpTrLtFbIpxH components.
      These components cannot be added nor deleted."
::= { mscLpTrLtFbIpxHRowStatusEntry 1 }

mscLpTrLtFbIpxHComponentName OBJECT-TYPE
   SYNTAX     DisplayString 
   ACCESS     read-only
   STATUS     mandatory
   DESCRIPTION
     "This variable provides the component's string name for
      use with the ASCII Console Interface"
::= { mscLpTrLtFbIpxHRowStatusEntry 2 }

mscLpTrLtFbIpxHStorageType OBJECT-TYPE
   SYNTAX     StorageType 
   ACCESS     read-only
   STATUS     mandatory
   DESCRIPTION
     "This variable represents the storage type value for the
      mscLpTrLtFbIpxH tables."
::= { mscLpTrLtFbIpxHRowStatusEntry 4 }

mscLpTrLtFbIpxHIndex OBJECT-TYPE
   SYNTAX     NonReplicated 
   ACCESS     not-accessible
   STATUS     mandatory
   DESCRIPTION
     "This variable represents the index for the mscLpTrLtFbIpxH tables."
::= { mscLpTrLtFbIpxHRowStatusEntry 10 }

mscLpTrLtFbIpxHTopTable OBJECT-TYPE
   SYNTAX     SEQUENCE OF MscLpTrLtFbIpxHTopEntry
   ACCESS     not-accessible
   STATUS     mandatory
   DESCRIPTION
     "This group contains the operational data for the LanTest component 
      and its subcomponents."
::= { mscLpTrLtFbIpxH 10 }

mscLpTrLtFbIpxHTopEntry OBJECT-TYPE
   SYNTAX     MscLpTrLtFbIpxHTopEntry
   ACCESS     not-accessible
   STATUS     mandatory
   DESCRIPTION
     "An entry in the mscLpTrLtFbIpxHTopTable."
   INDEX {
      mscLpIndex,
      mscLpTrIndex,
      mscLpTrLtIndex,
      mscLpTrLtFbIndex,
      mscLpTrLtFbIpxHIndex }
::= { mscLpTrLtFbIpxHTopTable 1 }

MscLpTrLtFbIpxHTopEntry ::= SEQUENCE {
   mscLpTrLtFbIpxHTData
      AsciiString }

mscLpTrLtFbIpxHTData OBJECT-TYPE
   SYNTAX     AsciiString (SIZE (0..255))
   ACCESS     read-write
   STATUS     mandatory
   DESCRIPTION
     "This attribute is used to display and set attributes."
::= { mscLpTrLtFbIpxHTopEntry 1 }


-- LanTest Control
-- This component controls the overall testing by telling the 
-- FrameBuild component to start and check the FrameCompare 
-- component to see if the test is complete.

mscLpTrLtCntl OBJECT IDENTIFIER ::= { mscLpTrLt 6 }



mscLpTrLtCntlRowStatusTable OBJECT-TYPE
   SYNTAX     SEQUENCE OF MscLpTrLtCntlRowStatusEntry
   ACCESS     not-accessible
   STATUS     mandatory
   DESCRIPTION
     "This entry controls the addition and deletion of 
      mscLpTrLtCntl components."
::= { mscLpTrLtCntl 1 }

mscLpTrLtCntlRowStatusEntry OBJECT-TYPE
   SYNTAX     MscLpTrLtCntlRowStatusEntry
   ACCESS     not-accessible
   STATUS     mandatory
   DESCRIPTION
     "A single entry in the table represents a single 
      mscLpTrLtCntl component."
   INDEX {
      mscLpIndex,
      mscLpTrIndex,
      mscLpTrLtIndex,
      mscLpTrLtCntlIndex }
::= { mscLpTrLtCntlRowStatusTable 1 }

MscLpTrLtCntlRowStatusEntry ::= SEQUENCE {
   mscLpTrLtCntlRowStatus
      RowStatus,
   mscLpTrLtCntlComponentName
      DisplayString,
   mscLpTrLtCntlStorageType
      StorageType,
   mscLpTrLtCntlIndex
      NonReplicated }

mscLpTrLtCntlRowStatus OBJECT-TYPE
   SYNTAX     RowStatus 
   ACCESS     read-only
   STATUS     mandatory
   DESCRIPTION
     "This variable is used as the basis for SNMP naming of
      mscLpTrLtCntl components.
      These components cannot be added nor deleted."
::= { mscLpTrLtCntlRowStatusEntry 1 }

mscLpTrLtCntlComponentName OBJECT-TYPE
   SYNTAX     DisplayString 
   ACCESS     read-only
   STATUS     mandatory
   DESCRIPTION
     "This variable provides the component's string name for
      use with the ASCII Console Interface"
::= { mscLpTrLtCntlRowStatusEntry 2 }

mscLpTrLtCntlStorageType OBJECT-TYPE
   SYNTAX     StorageType 
   ACCESS     read-only
   STATUS     mandatory
   DESCRIPTION
     "This variable represents the storage type value for the
      mscLpTrLtCntl tables."
::= { mscLpTrLtCntlRowStatusEntry 4 }

mscLpTrLtCntlIndex OBJECT-TYPE
   SYNTAX     NonReplicated 
   ACCESS     not-accessible
   STATUS     mandatory
   DESCRIPTION
     "This variable represents the index for the mscLpTrLtCntl tables."
::= { mscLpTrLtCntlRowStatusEntry 10 }

mscLpTrLtCntlTopTable OBJECT-TYPE
   SYNTAX     SEQUENCE OF MscLpTrLtCntlTopEntry
   ACCESS     not-accessible
   STATUS     mandatory
   DESCRIPTION
     "This group contains the operational data for the LanTest component 
      and its subcomponents."
::= { mscLpTrLtCntl 10 }

mscLpTrLtCntlTopEntry OBJECT-TYPE
   SYNTAX     MscLpTrLtCntlTopEntry
   ACCESS     not-accessible
   STATUS     mandatory
   DESCRIPTION
     "An entry in the mscLpTrLtCntlTopTable."
   INDEX {
      mscLpIndex,
      mscLpTrIndex,
      mscLpTrLtIndex,
      mscLpTrLtCntlIndex }
::= { mscLpTrLtCntlTopTable 1 }

MscLpTrLtCntlTopEntry ::= SEQUENCE {
   mscLpTrLtCntlTData
      AsciiString }

mscLpTrLtCntlTData OBJECT-TYPE
   SYNTAX     AsciiString (SIZE (0..255))
   ACCESS     read-write
   STATUS     mandatory
   DESCRIPTION
     "This attribute is used to display and set attributes."
::= { mscLpTrLtCntlTopEntry 1 }


-- Lp/n Fddi/n Test, or
-- Lp/n Ethernet/n Test, or
-- Lp/n TokenRing/n Test, or
-- Lp/n IlsForwarder/n Test
-- The Test component is used to do StartUp port test for LAN cards.

mscLpTrTest OBJECT IDENTIFIER ::= { mscLpTr 5 }



mscLpTrTestRowStatusTable OBJECT-TYPE
   SYNTAX     SEQUENCE OF MscLpTrTestRowStatusEntry
   ACCESS     not-accessible
   STATUS     mandatory
   DESCRIPTION
     "This entry controls the addition and deletion of 
      mscLpTrTest components."
::= { mscLpTrTest 1 }

mscLpTrTestRowStatusEntry OBJECT-TYPE
   SYNTAX     MscLpTrTestRowStatusEntry
   ACCESS     not-accessible
   STATUS     mandatory
   DESCRIPTION
     "A single entry in the table represents a single 
      mscLpTrTest component."
   INDEX {
      mscLpIndex,
      mscLpTrIndex,
      mscLpTrTestIndex }
::= { mscLpTrTestRowStatusTable 1 }

MscLpTrTestRowStatusEntry ::= SEQUENCE {
   mscLpTrTestRowStatus
      RowStatus,
   mscLpTrTestComponentName
      DisplayString,
   mscLpTrTestStorageType
      StorageType,
   mscLpTrTestIndex
      NonReplicated }

mscLpTrTestRowStatus OBJECT-TYPE
   SYNTAX     RowStatus 
   ACCESS     read-only
   STATUS     mandatory
   DESCRIPTION
     "This variable is used as the basis for SNMP naming of
      mscLpTrTest components.
      These components cannot be added nor deleted."
::= { mscLpTrTestRowStatusEntry 1 }

mscLpTrTestComponentName OBJECT-TYPE
   SYNTAX     DisplayString 
   ACCESS     read-only
   STATUS     mandatory
   DESCRIPTION
     "This variable provides the component's string name for
      use with the ASCII Console Interface"
::= { mscLpTrTestRowStatusEntry 2 }

mscLpTrTestStorageType OBJECT-TYPE
   SYNTAX     StorageType 
   ACCESS     read-only
   STATUS     mandatory
   DESCRIPTION
     "This variable represents the storage type value for the
      mscLpTrTest tables."
::= { mscLpTrTestRowStatusEntry 4 }

mscLpTrTestIndex OBJECT-TYPE
   SYNTAX     NonReplicated 
   ACCESS     not-accessible
   STATUS     mandatory
   DESCRIPTION
     "This variable represents the index for the mscLpTrTest tables."
::= { mscLpTrTestRowStatusEntry 10 }

mscLpTrTestPTOTable OBJECT-TYPE
   SYNTAX     SEQUENCE OF MscLpTrTestPTOEntry
   ACCESS     not-accessible
   STATUS     mandatory
   DESCRIPTION
     "This group contains the operational data for the LanPortTest 
      component."
::= { mscLpTrTest 10 }

mscLpTrTestPTOEntry OBJECT-TYPE
   SYNTAX     MscLpTrTestPTOEntry
   ACCESS     not-accessible
   STATUS     mandatory
   DESCRIPTION
     "An entry in the mscLpTrTestPTOTable."
   INDEX {
      mscLpIndex,
      mscLpTrIndex,
      mscLpTrTestIndex }
::= { mscLpTrTestPTOTable 1 }

MscLpTrTestPTOEntry ::= SEQUENCE {
   mscLpTrTestType
      INTEGER,
   mscLpTrTestFrmSize
      Unsigned32,
   mscLpTrTestDuration
      Unsigned32 }

mscLpTrTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { mscLpTrTestPTOEntry 1 }

mscLpTrTestFrmSize OBJECT-TYPE
   SYNTAX     Unsigned32 (4..4096)
   ACCESS     read-write
   STATUS     mandatory
   DESCRIPTION
     "This attribute defines the size of the test data frames in number of 
      bytes."
   DEFVAL     { 1024 }
::= { mscLpTrTestPTOEntry 2 }

mscLpTrTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpTrTestPTOEntry 3 }

mscLpTrTestResultsTable OBJECT-TYPE
   SYNTAX     SEQUENCE OF MscLpTrTestResultsEntry
   ACCESS     not-accessible
   STATUS     mandatory
   DESCRIPTION
     "This group contains all the statistics related attributes of the Test 
      component."
::= { mscLpTrTest 11 }

mscLpTrTestResultsEntry OBJECT-TYPE
   SYNTAX     MscLpTrTestResultsEntry
   ACCESS     not-accessible
   STATUS     mandatory
   DESCRIPTION
     "An entry in the mscLpTrTestResultsTable."
   INDEX {
      mscLpIndex,
      mscLpTrIndex,
      mscLpTrTestIndex }
::= { mscLpTrTestResultsTable 1 }

MscLpTrTestResultsEntry ::= SEQUENCE {
   mscLpTrTestElapsedTime
      Counter32,
   mscLpTrTestTimeRemaining
      Unsigned32,
   mscLpTrTestCauseOfTermination
      INTEGER,
   mscLpTrTestFrmTx
      PassportCounter64,
   mscLpTrTestBitsTx
      PassportCounter64,
   mscLpTrTestFrmRx
      PassportCounter64,
   mscLpTrTestBitsRx
      PassportCounter64,
   mscLpTrTestErroredFrmRx
      PassportCounter64 }

mscLpTrTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpTrTestResultsEntry 4 }

mscLpTrTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpTrTestResultsEntry 5 }

mscLpTrTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { mscLpTrTestResultsEntry 6 }

mscLpTrTestFrmTx OBJECT-TYPE
   SYNTAX     PassportCounter64 
   ACCESS     read-only
   STATUS     mandatory
   DESCRIPTION
     "This attribute is the total number of frames sent during the test 
      period. This counter is not expected to reach its maximum value."
::= { mscLpTrTestResultsEntry 7 }

mscLpTrTestBitsTx OBJECT-TYPE
   SYNTAX     PassportCounter64 
   ACCESS     read-only
   STATUS     mandatory
   DESCRIPTION
     "This attribute is the total number of bits sent during the test period. 
      This counter is not expected to reach its maximum value."
::= { mscLpTrTestResultsEntry 8 }

mscLpTrTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpTrTestResultsEntry 9 }

mscLpTrTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { mscLpTrTestResultsEntry 10 }

mscLpTrTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { mscLpTrTestResultsEntry 11 }


-- Lp/n IlsForwarder/0
-- This component defines an instance of a IlsForwarder. At least one 
-- instance of this component must be provisioned if there is any AtmMpe 
-- component provisioned.

mscLpIlsFwdr OBJECT IDENTIFIER ::= { mscLp 21 }



mscLpIlsFwdrRowStatusTable OBJECT-TYPE
   SYNTAX     SEQUENCE OF MscLpIlsFwdrRowStatusEntry
   ACCESS     not-accessible
   STATUS     mandatory
   DESCRIPTION
     "This entry controls the addition and deletion of 
      mscLpIlsFwdr components."
::= { mscLpIlsFwdr 1 }

mscLpIlsFwdrRowStatusEntry OBJECT-TYPE
   SYNTAX     MscLpIlsFwdrRowStatusEntry
   ACCESS     not-accessible
   STATUS     mandatory
   DESCRIPTION
     "A single entry in the table represents a single 
      mscLpIlsFwdr component."
   INDEX {
      mscLpIndex,
      mscLpIlsFwdrIndex }
::= { mscLpIlsFwdrRowStatusTable 1 }

MscLpIlsFwdrRowStatusEntry ::= SEQUENCE {
   mscLpIlsFwdrRowStatus
      RowStatus,
   mscLpIlsFwdrComponentName
      DisplayString,
   mscLpIlsFwdrStorageType
      StorageType,
   mscLpIlsFwdrIndex
      Integer32 }

mscLpIlsFwdrRowStatus OBJECT-TYPE
   SYNTAX     RowStatus 
   ACCESS     read-write
   STATUS     mandatory
   DESCRIPTION
     "This variable is used as the basis for SNMP naming of
      mscLpIlsFwdr components.
      These components can be added and deleted."
::= { mscLpIlsFwdrRowStatusEntry 1 }

mscLpIlsFwdrComponentName OBJECT-TYPE
   SYNTAX     DisplayString 
   ACCESS     read-only
   STATUS     mandatory
   DESCRIPTION
     "This variable provides the component's string name for
      use with the ASCII Console Interface"
::= { mscLpIlsFwdrRowStatusEntry 2 }

mscLpIlsFwdrStorageType OBJECT-TYPE
   SYNTAX     StorageType 
   ACCESS     read-only
   STATUS     mandatory
   DESCRIPTION
     "This variable represents the storage type value for the
      mscLpIlsFwdr tables."
::= { mscLpIlsFwdrRowStatusEntry 4 }

mscLpIlsFwdrIndex OBJECT-TYPE
   SYNTAX     Integer32 (0)
   ACCESS     not-accessible
   STATUS     mandatory
   DESCRIPTION
     "This variable represents the index for the mscLpIlsFwdr tables."
::= { mscLpIlsFwdrRowStatusEntry 10 }

mscLpIlsFwdrIfEntryTable OBJECT-TYPE
   SYNTAX     SEQUENCE OF MscLpIlsFwdrIfEntryEntry
   ACCESS     not-accessible
   STATUS     mandatory
   DESCRIPTION
     "This group contains the provisionable attributes for the ifEntry."
::= { mscLpIlsFwdr 11 }

mscLpIlsFwdrIfEntryEntry OBJECT-TYPE
   SYNTAX     MscLpIlsFwdrIfEntryEntry
   ACCESS     not-accessible
   STATUS     mandatory
   DESCRIPTION
     "An entry in the mscLpIlsFwdrIfEntryTable."
   INDEX {
      mscLpIndex,
      mscLpIlsFwdrIndex }
::= { mscLpIlsFwdrIfEntryTable 1 }

MscLpIlsFwdrIfEntryEntry ::= SEQUENCE {
   mscLpIlsFwdrIfAdminStatus
      INTEGER,
   mscLpIlsFwdrIfIndex
      InterfaceIndex }

mscLpIlsFwdrIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpIlsFwdrIfEntryEntry 1 }

mscLpIlsFwdrIfIndex OBJECT-TYPE
   SYNTAX     InterfaceIndex (1..65535)
   ACCESS     read-only
   STATUS     mandatory
   DESCRIPTION
     "This is the index for the IfEntry. Its value is automatically initialized 
      during the provisioning process."
::= { mscLpIlsFwdrIfEntryEntry 2 }

mscLpIlsFwdrStateTable OBJECT-TYPE
   SYNTAX     SEQUENCE OF MscLpIlsFwdrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpIlsFwdr 12 }

mscLpIlsFwdrStateEntry OBJECT-TYPE
   SYNTAX     MscLpIlsFwdrStateEntry
   ACCESS     not-accessible
   STATUS     mandatory
   DESCRIPTION
     "An entry in the mscLpIlsFwdrStateTable."
   INDEX {
      mscLpIndex,
      mscLpIlsFwdrIndex }
::= { mscLpIlsFwdrStateTable 1 }

MscLpIlsFwdrStateEntry ::= SEQUENCE {
   mscLpIlsFwdrAdminState
      INTEGER,
   mscLpIlsFwdrOperationalState
      INTEGER,
   mscLpIlsFwdrUsageState
      INTEGER }

mscLpIlsFwdrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpIlsFwdrStateEntry 1 }

mscLpIlsFwdrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpIlsFwdrStateEntry 2 }

mscLpIlsFwdrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpIlsFwdrStateEntry 3 }

mscLpIlsFwdrOperStatusTable OBJECT-TYPE
   SYNTAX     SEQUENCE OF MscLpIlsFwdrOperStatusEntry
   ACCESS     not-accessible
   STATUS     mandatory
   DESCRIPTION
     "This group includes the Operational Status attribute. This attribute 
      defines the current operational state of this component."
::= { mscLpIlsFwdr 13 }

mscLpIlsFwdrOperStatusEntry OBJECT-TYPE
   SYNTAX     MscLpIlsFwdrOperStatusEntry
   ACCESS     not-accessible
   STATUS     mandatory
   DESCRIPTION
     "An entry in the mscLpIlsFwdrOperStatusTable."
   INDEX {
      mscLpIndex,
      mscLpIlsFwdrIndex }
::= { mscLpIlsFwdrOperStatusTable 1 }

MscLpIlsFwdrOperStatusEntry ::= SEQUENCE {
   mscLpIlsFwdrSnmpOperStatus
      INTEGER }

mscLpIlsFwdrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpIlsFwdrOperStatusEntry 1 }

mscLpIlsFwdrStatsTable OBJECT-TYPE
   SYNTAX     SEQUENCE OF MscLpIlsFwdrStatsEntry
   ACCESS     not-accessible
   STATUS     mandatory
   DESCRIPTION
     "This group contains the operational frame statistics related attributes of 
      the IlsForwarder component."
::= { mscLpIlsFwdr 14 }

mscLpIlsFwdrStatsEntry OBJECT-TYPE
   SYNTAX     MscLpIlsFwdrStatsEntry
   ACCESS     not-accessible
   STATUS     mandatory
   DESCRIPTION
     "An entry in the mscLpIlsFwdrStatsTable."
   INDEX {
      mscLpIndex,
      mscLpIlsFwdrIndex }
::= { mscLpIlsFwdrStatsTable 1 }

MscLpIlsFwdrStatsEntry ::= SEQUENCE {
   mscLpIlsFwdrFramesReceived
      PassportCounter64,
   mscLpIlsFwdrProcessedCount
      PassportCounter64,
   mscLpIlsFwdrErrorCount
      PassportCounter64,
   mscLpIlsFwdrFramesDiscarded
      PassportCounter64 }

mscLpIlsFwdrFramesReceived OBJECT-TYPE
   SYNTAX     PassportCounter64 
   ACCESS     read-only
   STATUS     mandatory
   DESCRIPTION
     "This attribute counts the total number of frames that have been received 
      by this card. This counter will wrap around after it reaches its maximum 
      value."
::= { mscLpIlsFwdrStatsEntry 1 }

mscLpIlsFwdrProcessedCount OBJECT-TYPE
   SYNTAX     PassportCounter64 
   ACCESS     read-only
   STATUS     mandatory
   DESCRIPTION
     "This attribute counts the number of frames successfully processed by 
      this card. This counter will wrap around after it reaches its maximum 
      value."
::= { mscLpIlsFwdrStatsEntry 2 }

mscLpIlsFwdrErrorCount OBJECT-TYPE
   SYNTAX     PassportCounter64 
   ACCESS     read-only
   STATUS     mandatory
   DESCRIPTION
     "This attribute counts the number of internal errors detected in 
      transferring frames from an ATM card to this card. A continuous 
      increment of this count indicates that the hardware may probably be 
      defective. This counter will wrap around after it reaches its maximum 
      value."
::= { mscLpIlsFwdrStatsEntry 3 }

mscLpIlsFwdrFramesDiscarded OBJECT-TYPE
   SYNTAX     PassportCounter64 
   ACCESS     read-only
   STATUS     mandatory
   DESCRIPTION
     "This attribute counts the number of frames which are discarded due to 
      local buffer congestion. This counter will wrap around after it reaches its 
      maximum value."
::= { mscLpIlsFwdrStatsEntry 4 }

mscLpIlsFwdrLinkToTrafficSourceTable OBJECT-TYPE
   SYNTAX     SEQUENCE OF MscLpIlsFwdrLinkToTrafficSourceEntry
   ACCESS     not-accessible
   STATUS     mandatory
   DESCRIPTION
     "This attribute contains a list of components that are using this 
      IlsForwarder."
::= { mscLpIlsFwdr 312 }

mscLpIlsFwdrLinkToTrafficSourceEntry OBJECT-TYPE
   SYNTAX     MscLpIlsFwdrLinkToTrafficSourceEntry
   ACCESS     not-accessible
   STATUS     mandatory
   DESCRIPTION
     "An entry in the mscLpIlsFwdrLinkToTrafficSourceTable."
   INDEX {
      mscLpIndex,
      mscLpIlsFwdrIndex,
      mscLpIlsFwdrLinkToTrafficSourceValue }
::= { mscLpIlsFwdrLinkToTrafficSourceTable 1 }

MscLpIlsFwdrLinkToTrafficSourceEntry ::= SEQUENCE {
   mscLpIlsFwdrLinkToTrafficSourceValue
      Link }

mscLpIlsFwdrLinkToTrafficSourceValue OBJECT-TYPE
   SYNTAX     Link 
   ACCESS     read-only
   STATUS     mandatory
   DESCRIPTION
     "This variable represents both the value and the index for the
      mscLpIlsFwdrLinkToTrafficSourceTable."
::= { mscLpIlsFwdrLinkToTrafficSourceEntry 1 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

mscLpIlsFwdrLt OBJECT IDENTIFIER ::= { mscLpIlsFwdr 2 }



mscLpIlsFwdrLtRowStatusTable OBJECT-TYPE
   SYNTAX     SEQUENCE OF MscLpIlsFwdrLtRowStatusEntry
   ACCESS     not-accessible
   STATUS     mandatory
   DESCRIPTION
     "This entry controls the addition and deletion of 
      mscLpIlsFwdrLt components."
::= { mscLpIlsFwdrLt 1 }

mscLpIlsFwdrLtRowStatusEntry OBJECT-TYPE
   SYNTAX     MscLpIlsFwdrLtRowStatusEntry
   ACCESS     not-accessible
   STATUS     mandatory
   DESCRIPTION
     "A single entry in the table represents a single 
      mscLpIlsFwdrLt component."
   INDEX {
      mscLpIndex,
      mscLpIlsFwdrIndex,
      mscLpIlsFwdrLtIndex }
::= { mscLpIlsFwdrLtRowStatusTable 1 }

MscLpIlsFwdrLtRowStatusEntry ::= SEQUENCE {
   mscLpIlsFwdrLtRowStatus
      RowStatus,
   mscLpIlsFwdrLtComponentName
      DisplayString,
   mscLpIlsFwdrLtStorageType
      StorageType,
   mscLpIlsFwdrLtIndex
      NonReplicated }

mscLpIlsFwdrLtRowStatus OBJECT-TYPE
   SYNTAX     RowStatus 
   ACCESS     read-only
   STATUS     mandatory
   DESCRIPTION
     "This variable is used as the basis for SNMP naming of
      mscLpIlsFwdrLt components.
      These components cannot be added nor deleted."
::= { mscLpIlsFwdrLtRowStatusEntry 1 }

mscLpIlsFwdrLtComponentName OBJECT-TYPE
   SYNTAX     DisplayString 
   ACCESS     read-only
   STATUS     mandatory
   DESCRIPTION
     "This variable provides the component's string name for
      use with the ASCII Console Interface"
::= { mscLpIlsFwdrLtRowStatusEntry 2 }

mscLpIlsFwdrLtStorageType OBJECT-TYPE
   SYNTAX     StorageType 
   ACCESS     read-only
   STATUS     mandatory
   DESCRIPTION
     "This variable represents the storage type value for the
      mscLpIlsFwdrLt tables."
::= { mscLpIlsFwdrLtRowStatusEntry 4 }

mscLpIlsFwdrLtIndex OBJECT-TYPE
   SYNTAX     NonReplicated 
   ACCESS     not-accessible
   STATUS     mandatory
   DESCRIPTION
     "This variable represents the index for the mscLpIlsFwdrLt tables."
::= { mscLpIlsFwdrLtRowStatusEntry 10 }

mscLpIlsFwdrLtTopTable OBJECT-TYPE
   SYNTAX     SEQUENCE OF MscLpIlsFwdrLtTopEntry
   ACCESS     not-accessible
   STATUS     mandatory
   DESCRIPTION
     "This group contains the operational data for the LanTest component 
      and its subcomponents."
::= { mscLpIlsFwdrLt 20 }

mscLpIlsFwdrLtTopEntry OBJECT-TYPE
   SYNTAX     MscLpIlsFwdrLtTopEntry
   ACCESS     not-accessible
   STATUS     mandatory
   DESCRIPTION
     "An entry in the mscLpIlsFwdrLtTopTable."
   INDEX {
      mscLpIndex,
      mscLpIlsFwdrIndex,
      mscLpIlsFwdrLtIndex }
::= { mscLpIlsFwdrLtTopTable 1 }

MscLpIlsFwdrLtTopEntry ::= SEQUENCE {
   mscLpIlsFwdrLtTData
      AsciiString }

mscLpIlsFwdrLtTData OBJECT-TYPE
   SYNTAX     AsciiString (SIZE (0..255))
   ACCESS     read-write
   STATUS     mandatory
   DESCRIPTION
     "This attribute is used to display and set attributes."
::= { mscLpIlsFwdrLtTopEntry 1 }


-- This component compares frames received from the hardware and 
-- emulator during testing.

mscLpIlsFwdrLtFrmCmp OBJECT IDENTIFIER ::= { mscLpIlsFwdrLt 2 }



mscLpIlsFwdrLtFrmCmpRowStatusTable OBJECT-TYPE
   SYNTAX     SEQUENCE OF MscLpIlsFwdrLtFrmCmpRowStatusEntry
   ACCESS     not-accessible
   STATUS     mandatory
   DESCRIPTION
     "This entry controls the addition and deletion of 
      mscLpIlsFwdrLtFrmCmp components."
::= { mscLpIlsFwdrLtFrmCmp 1 }

mscLpIlsFwdrLtFrmCmpRowStatusEntry OBJECT-TYPE
   SYNTAX     MscLpIlsFwdrLtFrmCmpRowStatusEntry
   ACCESS     not-accessible
   STATUS     mandatory
   DESCRIPTION
     "A single entry in the table represents a single 
      mscLpIlsFwdrLtFrmCmp component."
   INDEX {
      mscLpIndex,
      mscLpIlsFwdrIndex,
      mscLpIlsFwdrLtIndex,
      mscLpIlsFwdrLtFrmCmpIndex }
::= { mscLpIlsFwdrLtFrmCmpRowStatusTable 1 }

MscLpIlsFwdrLtFrmCmpRowStatusEntry ::= SEQUENCE {
   mscLpIlsFwdrLtFrmCmpRowStatus
      RowStatus,
   mscLpIlsFwdrLtFrmCmpComponentName
      DisplayString,
   mscLpIlsFwdrLtFrmCmpStorageType
      StorageType,
   mscLpIlsFwdrLtFrmCmpIndex
      NonReplicated }

mscLpIlsFwdrLtFrmCmpRowStatus OBJECT-TYPE
   SYNTAX     RowStatus 
   ACCESS     read-only
   STATUS     mandatory
   DESCRIPTION
     "This variable is used as the basis for SNMP naming of
      mscLpIlsFwdrLtFrmCmp components.
      These components cannot be added nor deleted."
::= { mscLpIlsFwdrLtFrmCmpRowStatusEntry 1 }

mscLpIlsFwdrLtFrmCmpComponentName OBJECT-TYPE
   SYNTAX     DisplayString 
   ACCESS     read-only
   STATUS     mandatory
   DESCRIPTION
     "This variable provides the component's string name for
      use with the ASCII Console Interface"
::= { mscLpIlsFwdrLtFrmCmpRowStatusEntry 2 }

mscLpIlsFwdrLtFrmCmpStorageType OBJECT-TYPE
   SYNTAX     StorageType 
   ACCESS     read-only
   STATUS     mandatory
   DESCRIPTION
     "This variable represents the storage type value for the
      mscLpIlsFwdrLtFrmCmp tables."
::= { mscLpIlsFwdrLtFrmCmpRowStatusEntry 4 }

mscLpIlsFwdrLtFrmCmpIndex OBJECT-TYPE
   SYNTAX     NonReplicated 
   ACCESS     not-accessible
   STATUS     mandatory
   DESCRIPTION
     "This variable represents the index for the mscLpIlsFwdrLtFrmCmp tables."
::= { mscLpIlsFwdrLtFrmCmpRowStatusEntry 10 }

mscLpIlsFwdrLtFrmCmpTopTable OBJECT-TYPE
   SYNTAX     SEQUENCE OF MscLpIlsFwdrLtFrmCmpTopEntry
   ACCESS     not-accessible
   STATUS     mandatory
   DESCRIPTION
     "This group contains the operational data for the LanTest component 
      and its subcomponents."
::= { mscLpIlsFwdrLtFrmCmp 10 }

mscLpIlsFwdrLtFrmCmpTopEntry OBJECT-TYPE
   SYNTAX     MscLpIlsFwdrLtFrmCmpTopEntry
   ACCESS     not-accessible
   STATUS     mandatory
   DESCRIPTION
     "An entry in the mscLpIlsFwdrLtFrmCmpTopTable."
   INDEX {
      mscLpIndex,
      mscLpIlsFwdrIndex,
      mscLpIlsFwdrLtIndex,
      mscLpIlsFwdrLtFrmCmpIndex }
::= { mscLpIlsFwdrLtFrmCmpTopTable 1 }

MscLpIlsFwdrLtFrmCmpTopEntry ::= SEQUENCE {
   mscLpIlsFwdrLtFrmCmpTData
      AsciiString }

mscLpIlsFwdrLtFrmCmpTData OBJECT-TYPE
   SYNTAX     AsciiString (SIZE (0..255))
   ACCESS     read-write
   STATUS     mandatory
   DESCRIPTION
     "This attribute is used to display and set attributes."
::= { mscLpIlsFwdrLtFrmCmpTopEntry 1 }


-- This component receives its input from FrameBuild and places it 
-- upon the hardware which sends it to the appropriate emulator.

mscLpIlsFwdrLtFrmCpy OBJECT IDENTIFIER ::= { mscLpIlsFwdrLt 3 }



mscLpIlsFwdrLtFrmCpyRowStatusTable OBJECT-TYPE
   SYNTAX     SEQUENCE OF MscLpIlsFwdrLtFrmCpyRowStatusEntry
   ACCESS     not-accessible
   STATUS     mandatory
   DESCRIPTION
     "This entry controls the addition and deletion of 
      mscLpIlsFwdrLtFrmCpy components."
::= { mscLpIlsFwdrLtFrmCpy 1 }

mscLpIlsFwdrLtFrmCpyRowStatusEntry OBJECT-TYPE
   SYNTAX     MscLpIlsFwdrLtFrmCpyRowStatusEntry
   ACCESS     not-accessible
   STATUS     mandatory
   DESCRIPTION
     "A single entry in the table represents a single 
      mscLpIlsFwdrLtFrmCpy component."
   INDEX {
      mscLpIndex,
      mscLpIlsFwdrIndex,
      mscLpIlsFwdrLtIndex,
      mscLpIlsFwdrLtFrmCpyIndex }
::= { mscLpIlsFwdrLtFrmCpyRowStatusTable 1 }

MscLpIlsFwdrLtFrmCpyRowStatusEntry ::= SEQUENCE {
   mscLpIlsFwdrLtFrmCpyRowStatus
      RowStatus,
   mscLpIlsFwdrLtFrmCpyComponentName
      DisplayString,
   mscLpIlsFwdrLtFrmCpyStorageType
      StorageType,
   mscLpIlsFwdrLtFrmCpyIndex
      NonReplicated }

mscLpIlsFwdrLtFrmCpyRowStatus OBJECT-TYPE
   SYNTAX     RowStatus 
   ACCESS     read-only
   STATUS     mandatory
   DESCRIPTION
     "This variable is used as the basis for SNMP naming of
      mscLpIlsFwdrLtFrmCpy components.
      These components cannot be added nor deleted."
::= { mscLpIlsFwdrLtFrmCpyRowStatusEntry 1 }

mscLpIlsFwdrLtFrmCpyComponentName OBJECT-TYPE
   SYNTAX     DisplayString 
   ACCESS     read-only
   STATUS     mandatory
   DESCRIPTION
     "This variable provides the component's string name for
      use with the ASCII Console Interface"
::= { mscLpIlsFwdrLtFrmCpyRowStatusEntry 2 }

mscLpIlsFwdrLtFrmCpyStorageType OBJECT-TYPE
   SYNTAX     StorageType 
   ACCESS     read-only
   STATUS     mandatory
   DESCRIPTION
     "This variable represents the storage type value for the
      mscLpIlsFwdrLtFrmCpy tables."
::= { mscLpIlsFwdrLtFrmCpyRowStatusEntry 4 }

mscLpIlsFwdrLtFrmCpyIndex OBJECT-TYPE
   SYNTAX     NonReplicated 
   ACCESS     not-accessible
   STATUS     mandatory
   DESCRIPTION
     "This variable represents the index for the mscLpIlsFwdrLtFrmCpy tables."
::= { mscLpIlsFwdrLtFrmCpyRowStatusEntry 10 }

mscLpIlsFwdrLtFrmCpyTopTable OBJECT-TYPE
   SYNTAX     SEQUENCE OF MscLpIlsFwdrLtFrmCpyTopEntry
   ACCESS     not-accessible
   STATUS     mandatory
   DESCRIPTION
     "This group contains the operational data for the LanTest component 
      and its subcomponents."
::= { mscLpIlsFwdrLtFrmCpy 10 }

mscLpIlsFwdrLtFrmCpyTopEntry OBJECT-TYPE
   SYNTAX     MscLpIlsFwdrLtFrmCpyTopEntry
   ACCESS     not-accessible
   STATUS     mandatory
   DESCRIPTION
     "An entry in the mscLpIlsFwdrLtFrmCpyTopTable."
   INDEX {
      mscLpIndex,
      mscLpIlsFwdrIndex,
      mscLpIlsFwdrLtIndex,
      mscLpIlsFwdrLtFrmCpyIndex }
::= { mscLpIlsFwdrLtFrmCpyTopTable 1 }

MscLpIlsFwdrLtFrmCpyTopEntry ::= SEQUENCE {
   mscLpIlsFwdrLtFrmCpyTData
      AsciiString }

mscLpIlsFwdrLtFrmCpyTData OBJECT-TYPE
   SYNTAX     AsciiString (SIZE (0..255))
   ACCESS     read-write
   STATUS     mandatory
   DESCRIPTION
     "This attribute is used to display and set attributes."
::= { mscLpIlsFwdrLtFrmCpyTopEntry 1 }


-- This component controls the emulator and hardware to ensure 
-- frames output from each will match in FrameCompare.

mscLpIlsFwdrLtPrtCfg OBJECT IDENTIFIER ::= { mscLpIlsFwdrLt 4 }



mscLpIlsFwdrLtPrtCfgRowStatusTable OBJECT-TYPE
   SYNTAX     SEQUENCE OF MscLpIlsFwdrLtPrtCfgRowStatusEntry
   ACCESS     not-accessible
   STATUS     mandatory
   DESCRIPTION
     "This entry controls the addition and deletion of 
      mscLpIlsFwdrLtPrtCfg components."
::= { mscLpIlsFwdrLtPrtCfg 1 }

mscLpIlsFwdrLtPrtCfgRowStatusEntry OBJECT-TYPE
   SYNTAX     MscLpIlsFwdrLtPrtCfgRowStatusEntry
   ACCESS     not-accessible
   STATUS     mandatory
   DESCRIPTION
     "A single entry in the table represents a single 
      mscLpIlsFwdrLtPrtCfg component."
   INDEX {
      mscLpIndex,
      mscLpIlsFwdrIndex,
      mscLpIlsFwdrLtIndex,
      mscLpIlsFwdrLtPrtCfgIndex }
::= { mscLpIlsFwdrLtPrtCfgRowStatusTable 1 }

MscLpIlsFwdrLtPrtCfgRowStatusEntry ::= SEQUENCE {
   mscLpIlsFwdrLtPrtCfgRowStatus
      RowStatus,
   mscLpIlsFwdrLtPrtCfgComponentName
      DisplayString,
   mscLpIlsFwdrLtPrtCfgStorageType
      StorageType,
   mscLpIlsFwdrLtPrtCfgIndex
      NonReplicated }

mscLpIlsFwdrLtPrtCfgRowStatus OBJECT-TYPE
   SYNTAX     RowStatus 
   ACCESS     read-only
   STATUS     mandatory
   DESCRIPTION
     "This variable is used as the basis for SNMP naming of
      mscLpIlsFwdrLtPrtCfg components.
      These components cannot be added nor deleted."
::= { mscLpIlsFwdrLtPrtCfgRowStatusEntry 1 }

mscLpIlsFwdrLtPrtCfgComponentName OBJECT-TYPE
   SYNTAX     DisplayString 
   ACCESS     read-only
   STATUS     mandatory
   DESCRIPTION
     "This variable provides the component's string name for
      use with the ASCII Console Interface"
::= { mscLpIlsFwdrLtPrtCfgRowStatusEntry 2 }

mscLpIlsFwdrLtPrtCfgStorageType OBJECT-TYPE
   SYNTAX     StorageType 
   ACCESS     read-only
   STATUS     mandatory
   DESCRIPTION
     "This variable represents the storage type value for the
      mscLpIlsFwdrLtPrtCfg tables."
::= { mscLpIlsFwdrLtPrtCfgRowStatusEntry 4 }

mscLpIlsFwdrLtPrtCfgIndex OBJECT-TYPE
   SYNTAX     NonReplicated 
   ACCESS     not-accessible
   STATUS     mandatory
   DESCRIPTION
     "This variable represents the index for the mscLpIlsFwdrLtPrtCfg tables."
::= { mscLpIlsFwdrLtPrtCfgRowStatusEntry 10 }

mscLpIlsFwdrLtPrtCfgTopTable OBJECT-TYPE
   SYNTAX     SEQUENCE OF MscLpIlsFwdrLtPrtCfgTopEntry
   ACCESS     not-accessible
   STATUS     mandatory
   DESCRIPTION
     "This group contains the operational data for the LanTest component 
      and its subcomponents."
::= { mscLpIlsFwdrLtPrtCfg 10 }

mscLpIlsFwdrLtPrtCfgTopEntry OBJECT-TYPE
   SYNTAX     MscLpIlsFwdrLtPrtCfgTopEntry
   ACCESS     not-accessible
   STATUS     mandatory
   DESCRIPTION
     "An entry in the mscLpIlsFwdrLtPrtCfgTopTable."
   INDEX {
      mscLpIndex,
      mscLpIlsFwdrIndex,
      mscLpIlsFwdrLtIndex,
      mscLpIlsFwdrLtPrtCfgIndex }
::= { mscLpIlsFwdrLtPrtCfgTopTable 1 }

MscLpIlsFwdrLtPrtCfgTopEntry ::= SEQUENCE {
   mscLpIlsFwdrLtPrtCfgTData
      AsciiString }

mscLpIlsFwdrLtPrtCfgTData OBJECT-TYPE
   SYNTAX     AsciiString (SIZE (0..255))
   ACCESS     read-write
   STATUS     mandatory
   DESCRIPTION
     "This attribute is used to display and set attributes."
::= { mscLpIlsFwdrLtPrtCfgTopEntry 1 }


-- LanTest Framebuild
-- This component controls the building of all frames built and sent by 
-- the LanTest component. Each component under FrameBuild builds 
-- a portion of a packet or frame.

mscLpIlsFwdrLtFb OBJECT IDENTIFIER ::= { mscLpIlsFwdrLt 5 }



mscLpIlsFwdrLtFbRowStatusTable OBJECT-TYPE
   SYNTAX     SEQUENCE OF MscLpIlsFwdrLtFbRowStatusEntry
   ACCESS     not-accessible
   STATUS     mandatory
   DESCRIPTION
     "This entry controls the addition and deletion of 
      mscLpIlsFwdrLtFb components."
::= { mscLpIlsFwdrLtFb 1 }

mscLpIlsFwdrLtFbRowStatusEntry OBJECT-TYPE
   SYNTAX     MscLpIlsFwdrLtFbRowStatusEntry
   ACCESS     not-accessible
   STATUS     mandatory
   DESCRIPTION
     "A single entry in the table represents a single 
      mscLpIlsFwdrLtFb component."
   INDEX {
      mscLpIndex,
      mscLpIlsFwdrIndex,
      mscLpIlsFwdrLtIndex,
      mscLpIlsFwdrLtFbIndex }
::= { mscLpIlsFwdrLtFbRowStatusTable 1 }

MscLpIlsFwdrLtFbRowStatusEntry ::= SEQUENCE {
   mscLpIlsFwdrLtFbRowStatus
      RowStatus,
   mscLpIlsFwdrLtFbComponentName
      DisplayString,
   mscLpIlsFwdrLtFbStorageType
      StorageType,
   mscLpIlsFwdrLtFbIndex
      NonReplicated }

mscLpIlsFwdrLtFbRowStatus OBJECT-TYPE
   SYNTAX     RowStatus 
   ACCESS     read-only
   STATUS     mandatory
   DESCRIPTION
     "This variable is used as the basis for SNMP naming of
      mscLpIlsFwdrLtFb components.
      These components cannot be added nor deleted."
::= { mscLpIlsFwdrLtFbRowStatusEntry 1 }

mscLpIlsFwdrLtFbComponentName OBJECT-TYPE
   SYNTAX     DisplayString 
   ACCESS     read-only
   STATUS     mandatory
   DESCRIPTION
     "This variable provides the component's string name for
      use with the ASCII Console Interface"
::= { mscLpIlsFwdrLtFbRowStatusEntry 2 }

mscLpIlsFwdrLtFbStorageType OBJECT-TYPE
   SYNTAX     StorageType 
   ACCESS     read-only
   STATUS     mandatory
   DESCRIPTION
     "This variable represents the storage type value for the
      mscLpIlsFwdrLtFb tables."
::= { mscLpIlsFwdrLtFbRowStatusEntry 4 }

mscLpIlsFwdrLtFbIndex OBJECT-TYPE
   SYNTAX     NonReplicated 
   ACCESS     not-accessible
   STATUS     mandatory
   DESCRIPTION
     "This variable represents the index for the mscLpIlsFwdrLtFb tables."
::= { mscLpIlsFwdrLtFbRowStatusEntry 10 }

mscLpIlsFwdrLtFbTopTable OBJECT-TYPE
   SYNTAX     SEQUENCE OF MscLpIlsFwdrLtFbTopEntry
   ACCESS     not-accessible
   STATUS     mandatory
   DESCRIPTION
     "This group contains the operational data for the LanTest component 
      and its subcomponents."
::= { mscLpIlsFwdrLtFb 20 }

mscLpIlsFwdrLtFbTopEntry OBJECT-TYPE
   SYNTAX     MscLpIlsFwdrLtFbTopEntry
   ACCESS     not-accessible
   STATUS     mandatory
   DESCRIPTION
     "An entry in the mscLpIlsFwdrLtFbTopTable."
   INDEX {
      mscLpIndex,
      mscLpIlsFwdrIndex,
      mscLpIlsFwdrLtIndex,
      mscLpIlsFwdrLtFbIndex }
::= { mscLpIlsFwdrLtFbTopTable 1 }

MscLpIlsFwdrLtFbTopEntry ::= SEQUENCE {
   mscLpIlsFwdrLtFbTData
      AsciiString }

mscLpIlsFwdrLtFbTData OBJECT-TYPE
   SYNTAX     AsciiString (SIZE (0..255))
   ACCESS     read-write
   STATUS     mandatory
   DESCRIPTION
     "This attribute is used to display and set attributes."
::= { mscLpIlsFwdrLtFbTopEntry 1 }


-- LanTest TransmitInfo
-- This component builds a transmit header which is attached to all 
-- frames transmitted on LAN interfaces.

mscLpIlsFwdrLtFbTxInfo OBJECT IDENTIFIER ::= { mscLpIlsFwdrLtFb 2 }



mscLpIlsFwdrLtFbTxInfoRowStatusTable OBJECT-TYPE
   SYNTAX     SEQUENCE OF MscLpIlsFwdrLtFbTxInfoRowStatusEntry
   ACCESS     not-accessible
   STATUS     mandatory
   DESCRIPTION
     "This entry controls the addition and deletion of 
      mscLpIlsFwdrLtFbTxInfo components."
::= { mscLpIlsFwdrLtFbTxInfo 1 }

mscLpIlsFwdrLtFbTxInfoRowStatusEntry OBJECT-TYPE
   SYNTAX     MscLpIlsFwdrLtFbTxInfoRowStatusEntry
   ACCESS     not-accessible
   STATUS     mandatory
   DESCRIPTION
     "A single entry in the table represents a single 
      mscLpIlsFwdrLtFbTxInfo component."
   INDEX {
      mscLpIndex,
      mscLpIlsFwdrIndex,
      mscLpIlsFwdrLtIndex,
      mscLpIlsFwdrLtFbIndex,
      mscLpIlsFwdrLtFbTxInfoIndex }
::= { mscLpIlsFwdrLtFbTxInfoRowStatusTable 1 }

MscLpIlsFwdrLtFbTxInfoRowStatusEntry ::= SEQUENCE {
   mscLpIlsFwdrLtFbTxInfoRowStatus
      RowStatus,
   mscLpIlsFwdrLtFbTxInfoComponentName
      DisplayString,
   mscLpIlsFwdrLtFbTxInfoStorageType
      StorageType,
   mscLpIlsFwdrLtFbTxInfoIndex
      NonReplicated }

mscLpIlsFwdrLtFbTxInfoRowStatus OBJECT-TYPE
   SYNTAX     RowStatus 
   ACCESS     read-only
   STATUS     mandatory
   DESCRIPTION
     "This variable is used as the basis for SNMP naming of
      mscLpIlsFwdrLtFbTxInfo components.
      These components cannot be added nor deleted."
::= { mscLpIlsFwdrLtFbTxInfoRowStatusEntry 1 }

mscLpIlsFwdrLtFbTxInfoComponentName OBJECT-TYPE
   SYNTAX     DisplayString 
   ACCESS     read-only
   STATUS     mandatory
   DESCRIPTION
     "This variable provides the component's string name for
      use with the ASCII Console Interface"
::= { mscLpIlsFwdrLtFbTxInfoRowStatusEntry 2 }

mscLpIlsFwdrLtFbTxInfoStorageType OBJECT-TYPE
   SYNTAX     StorageType 
   ACCESS     read-only
   STATUS     mandatory
   DESCRIPTION
     "This variable represents the storage type value for the
      mscLpIlsFwdrLtFbTxInfo tables."
::= { mscLpIlsFwdrLtFbTxInfoRowStatusEntry 4 }

mscLpIlsFwdrLtFbTxInfoIndex OBJECT-TYPE
   SYNTAX     NonReplicated 
   ACCESS     not-accessible
   STATUS     mandatory
   DESCRIPTION
     "This variable represents the index for the mscLpIlsFwdrLtFbTxInfo tables."
::= { mscLpIlsFwdrLtFbTxInfoRowStatusEntry 10 }

mscLpIlsFwdrLtFbTxInfoTopTable OBJECT-TYPE
   SYNTAX     SEQUENCE OF MscLpIlsFwdrLtFbTxInfoTopEntry
   ACCESS     not-accessible
   STATUS     mandatory
   DESCRIPTION
     "This group contains the operational data for the LanTest component 
      and its subcomponents."
::= { mscLpIlsFwdrLtFbTxInfo 10 }

mscLpIlsFwdrLtFbTxInfoTopEntry OBJECT-TYPE
   SYNTAX     MscLpIlsFwdrLtFbTxInfoTopEntry
   ACCESS     not-accessible
   STATUS     mandatory
   DESCRIPTION
     "An entry in the mscLpIlsFwdrLtFbTxInfoTopTable."
   INDEX {
      mscLpIndex,
      mscLpIlsFwdrIndex,
      mscLpIlsFwdrLtIndex,
      mscLpIlsFwdrLtFbIndex,
      mscLpIlsFwdrLtFbTxInfoIndex }
::= { mscLpIlsFwdrLtFbTxInfoTopTable 1 }

MscLpIlsFwdrLtFbTxInfoTopEntry ::= SEQUENCE {
   mscLpIlsFwdrLtFbTxInfoTData
      AsciiString }

mscLpIlsFwdrLtFbTxInfoTData OBJECT-TYPE
   SYNTAX     AsciiString (SIZE (0..255))
   ACCESS     read-write
   STATUS     mandatory
   DESCRIPTION
     "This attribute is used to display and set attributes."
::= { mscLpIlsFwdrLtFbTxInfoTopEntry 1 }


-- LanTest FddiMac
-- This component builds an FDDI MAC header which is attached to 
-- all FDDI frames.

mscLpIlsFwdrLtFbFddiMac OBJECT IDENTIFIER ::= { mscLpIlsFwdrLtFb 3 }



mscLpIlsFwdrLtFbFddiMacRowStatusTable OBJECT-TYPE
   SYNTAX     SEQUENCE OF MscLpIlsFwdrLtFbFddiMacRowStatusEntry
   ACCESS     not-accessible
   STATUS     mandatory
   DESCRIPTION
     "This entry controls the addition and deletion of 
      mscLpIlsFwdrLtFbFddiMac components."
::= { mscLpIlsFwdrLtFbFddiMac 1 }

mscLpIlsFwdrLtFbFddiMacRowStatusEntry OBJECT-TYPE
   SYNTAX     MscLpIlsFwdrLtFbFddiMacRowStatusEntry
   ACCESS     not-accessible
   STATUS     mandatory
   DESCRIPTION
     "A single entry in the table represents a single 
      mscLpIlsFwdrLtFbFddiMac component."
   INDEX {
      mscLpIndex,
      mscLpIlsFwdrIndex,
      mscLpIlsFwdrLtIndex,
      mscLpIlsFwdrLtFbIndex,
      mscLpIlsFwdrLtFbFddiMacIndex }
::= { mscLpIlsFwdrLtFbFddiMacRowStatusTable 1 }

MscLpIlsFwdrLtFbFddiMacRowStatusEntry ::= SEQUENCE {
   mscLpIlsFwdrLtFbFddiMacRowStatus
      RowStatus,
   mscLpIlsFwdrLtFbFddiMacComponentName
      DisplayString,
   mscLpIlsFwdrLtFbFddiMacStorageType
      StorageType,
   mscLpIlsFwdrLtFbFddiMacIndex
      NonReplicated }

mscLpIlsFwdrLtFbFddiMacRowStatus OBJECT-TYPE
   SYNTAX     RowStatus 
   ACCESS     read-only
   STATUS     mandatory
   DESCRIPTION
     "This variable is used as the basis for SNMP naming of
      mscLpIlsFwdrLtFbFddiMac components.
      These components cannot be added nor deleted."
::= { mscLpIlsFwdrLtFbFddiMacRowStatusEntry 1 }

mscLpIlsFwdrLtFbFddiMacComponentName OBJECT-TYPE
   SYNTAX     DisplayString 
   ACCESS     read-only
   STATUS     mandatory
   DESCRIPTION
     "This variable provides the component's string name for
      use with the ASCII Console Interface"
::= { mscLpIlsFwdrLtFbFddiMacRowStatusEntry 2 }

mscLpIlsFwdrLtFbFddiMacStorageType OBJECT-TYPE
   SYNTAX     StorageType 
   ACCESS     read-only
   STATUS     mandatory
   DESCRIPTION
     "This variable represents the storage type value for the
      mscLpIlsFwdrLtFbFddiMac tables."
::= { mscLpIlsFwdrLtFbFddiMacRowStatusEntry 4 }

mscLpIlsFwdrLtFbFddiMacIndex OBJECT-TYPE
   SYNTAX     NonReplicated 
   ACCESS     not-accessible
   STATUS     mandatory
   DESCRIPTION
     "This variable represents the index for the mscLpIlsFwdrLtFbFddiMac tables."
::= { mscLpIlsFwdrLtFbFddiMacRowStatusEntry 10 }

mscLpIlsFwdrLtFbFddiMacTopTable OBJECT-TYPE
   SYNTAX     SEQUENCE OF MscLpIlsFwdrLtFbFddiMacTopEntry
   ACCESS     not-accessible
   STATUS     mandatory
   DESCRIPTION
     "This group contains the operational data for the LanTest component 
      and its subcomponents."
::= { mscLpIlsFwdrLtFbFddiMac 10 }

mscLpIlsFwdrLtFbFddiMacTopEntry OBJECT-TYPE
   SYNTAX     MscLpIlsFwdrLtFbFddiMacTopEntry
   ACCESS     not-accessible
   STATUS     mandatory
   DESCRIPTION
     "An entry in the mscLpIlsFwdrLtFbFddiMacTopTable."
   INDEX {
      mscLpIndex,
      mscLpIlsFwdrIndex,
      mscLpIlsFwdrLtIndex,
      mscLpIlsFwdrLtFbIndex,
      mscLpIlsFwdrLtFbFddiMacIndex }
::= { mscLpIlsFwdrLtFbFddiMacTopTable 1 }

MscLpIlsFwdrLtFbFddiMacTopEntry ::= SEQUENCE {
   mscLpIlsFwdrLtFbFddiMacTData
      AsciiString }

mscLpIlsFwdrLtFbFddiMacTData OBJECT-TYPE
   SYNTAX     AsciiString (SIZE (0..255))
   ACCESS     read-write
   STATUS     mandatory
   DESCRIPTION
     "This attribute is used to display and set attributes."
::= { mscLpIlsFwdrLtFbFddiMacTopEntry 1 }


-- LanTest EthernetMac
-- This component builds an Ethernet MAC header which is attached 
-- to all Ethernet frames.

mscLpIlsFwdrLtFbMacEnet OBJECT IDENTIFIER ::= { mscLpIlsFwdrLtFb 4 }



mscLpIlsFwdrLtFbMacEnetRowStatusTable OBJECT-TYPE
   SYNTAX     SEQUENCE OF MscLpIlsFwdrLtFbMacEnetRowStatusEntry
   ACCESS     not-accessible
   STATUS     mandatory
   DESCRIPTION
     "This entry controls the addition and deletion of 
      mscLpIlsFwdrLtFbMacEnet components."
::= { mscLpIlsFwdrLtFbMacEnet 1 }

mscLpIlsFwdrLtFbMacEnetRowStatusEntry OBJECT-TYPE
   SYNTAX     MscLpIlsFwdrLtFbMacEnetRowStatusEntry
   ACCESS     not-accessible
   STATUS     mandatory
   DESCRIPTION
     "A single entry in the table represents a single 
      mscLpIlsFwdrLtFbMacEnet component."
   INDEX {
      mscLpIndex,
      mscLpIlsFwdrIndex,
      mscLpIlsFwdrLtIndex,
      mscLpIlsFwdrLtFbIndex,
      mscLpIlsFwdrLtFbMacEnetIndex }
::= { mscLpIlsFwdrLtFbMacEnetRowStatusTable 1 }

MscLpIlsFwdrLtFbMacEnetRowStatusEntry ::= SEQUENCE {
   mscLpIlsFwdrLtFbMacEnetRowStatus
      RowStatus,
   mscLpIlsFwdrLtFbMacEnetComponentName
      DisplayString,
   mscLpIlsFwdrLtFbMacEnetStorageType
      StorageType,
   mscLpIlsFwdrLtFbMacEnetIndex
      NonReplicated }

mscLpIlsFwdrLtFbMacEnetRowStatus OBJECT-TYPE
   SYNTAX     RowStatus 
   ACCESS     read-only
   STATUS     mandatory
   DESCRIPTION
     "This variable is used as the basis for SNMP naming of
      mscLpIlsFwdrLtFbMacEnet components.
      These components cannot be added nor deleted."
::= { mscLpIlsFwdrLtFbMacEnetRowStatusEntry 1 }

mscLpIlsFwdrLtFbMacEnetComponentName OBJECT-TYPE
   SYNTAX     DisplayString 
   ACCESS     read-only
   STATUS     mandatory
   DESCRIPTION
     "This variable provides the component's string name for
      use with the ASCII Console Interface"
::= { mscLpIlsFwdrLtFbMacEnetRowStatusEntry 2 }

mscLpIlsFwdrLtFbMacEnetStorageType OBJECT-TYPE
   SYNTAX     StorageType 
   ACCESS     read-only
   STATUS     mandatory
   DESCRIPTION
     "This variable represents the storage type value for the
      mscLpIlsFwdrLtFbMacEnet tables."
::= { mscLpIlsFwdrLtFbMacEnetRowStatusEntry 4 }

mscLpIlsFwdrLtFbMacEnetIndex OBJECT-TYPE
   SYNTAX     NonReplicated 
   ACCESS     not-accessible
   STATUS     mandatory
   DESCRIPTION
     "This variable represents the index for the mscLpIlsFwdrLtFbMacEnet tables."
::= { mscLpIlsFwdrLtFbMacEnetRowStatusEntry 10 }

mscLpIlsFwdrLtFbMacEnetTopTable OBJECT-TYPE
   SYNTAX     SEQUENCE OF MscLpIlsFwdrLtFbMacEnetTopEntry
   ACCESS     not-accessible
   STATUS     mandatory
   DESCRIPTION
     "This group contains the operational data for the LanTest component 
      and its subcomponents."
::= { mscLpIlsFwdrLtFbMacEnet 10 }

mscLpIlsFwdrLtFbMacEnetTopEntry OBJECT-TYPE
   SYNTAX     MscLpIlsFwdrLtFbMacEnetTopEntry
   ACCESS     not-accessible
   STATUS     mandatory
   DESCRIPTION
     "An entry in the mscLpIlsFwdrLtFbMacEnetTopTable."
   INDEX {
      mscLpIndex,
      mscLpIlsFwdrIndex,
      mscLpIlsFwdrLtIndex,
      mscLpIlsFwdrLtFbIndex,
      mscLpIlsFwdrLtFbMacEnetIndex }
::= { mscLpIlsFwdrLtFbMacEnetTopTable 1 }

MscLpIlsFwdrLtFbMacEnetTopEntry ::= SEQUENCE {
   mscLpIlsFwdrLtFbMacEnetTData
      AsciiString }

mscLpIlsFwdrLtFbMacEnetTData OBJECT-TYPE
   SYNTAX     AsciiString (SIZE (0..255))
   ACCESS     read-write
   STATUS     mandatory
   DESCRIPTION
     "This attribute is used to display and set attributes."
::= { mscLpIlsFwdrLtFbMacEnetTopEntry 1 }


-- LanTest TokenRingMac
-- This component builds a Token Ring MAC header which is attached 
-- to all Token Ring frames.

mscLpIlsFwdrLtFbMacTr OBJECT IDENTIFIER ::= { mscLpIlsFwdrLtFb 5 }



mscLpIlsFwdrLtFbMacTrRowStatusTable OBJECT-TYPE
   SYNTAX     SEQUENCE OF MscLpIlsFwdrLtFbMacTrRowStatusEntry
   ACCESS     not-accessible
   STATUS     mandatory
   DESCRIPTION
     "This entry controls the addition and deletion of 
      mscLpIlsFwdrLtFbMacTr components."
::= { mscLpIlsFwdrLtFbMacTr 1 }

mscLpIlsFwdrLtFbMacTrRowStatusEntry OBJECT-TYPE
   SYNTAX     MscLpIlsFwdrLtFbMacTrRowStatusEntry
   ACCESS     not-accessible
   STATUS     mandatory
   DESCRIPTION
     "A single entry in the table represents a single 
      mscLpIlsFwdrLtFbMacTr component."
   INDEX {
      mscLpIndex,
      mscLpIlsFwdrIndex,
      mscLpIlsFwdrLtIndex,
      mscLpIlsFwdrLtFbIndex,
      mscLpIlsFwdrLtFbMacTrIndex }
::= { mscLpIlsFwdrLtFbMacTrRowStatusTable 1 }

MscLpIlsFwdrLtFbMacTrRowStatusEntry ::= SEQUENCE {
   mscLpIlsFwdrLtFbMacTrRowStatus
      RowStatus,
   mscLpIlsFwdrLtFbMacTrComponentName
      DisplayString,
   mscLpIlsFwdrLtFbMacTrStorageType
      StorageType,
   mscLpIlsFwdrLtFbMacTrIndex
      NonReplicated }

mscLpIlsFwdrLtFbMacTrRowStatus OBJECT-TYPE
   SYNTAX     RowStatus 
   ACCESS     read-only
   STATUS     mandatory
   DESCRIPTION
     "This variable is used as the basis for SNMP naming of
      mscLpIlsFwdrLtFbMacTr components.
      These components cannot be added nor deleted."
::= { mscLpIlsFwdrLtFbMacTrRowStatusEntry 1 }

mscLpIlsFwdrLtFbMacTrComponentName OBJECT-TYPE
   SYNTAX     DisplayString 
   ACCESS     read-only
   STATUS     mandatory
   DESCRIPTION
     "This variable provides the component's string name for
      use with the ASCII Console Interface"
::= { mscLpIlsFwdrLtFbMacTrRowStatusEntry 2 }

mscLpIlsFwdrLtFbMacTrStorageType OBJECT-TYPE
   SYNTAX     StorageType 
   ACCESS     read-only
   STATUS     mandatory
   DESCRIPTION
     "This variable represents the storage type value for the
      mscLpIlsFwdrLtFbMacTr tables."
::= { mscLpIlsFwdrLtFbMacTrRowStatusEntry 4 }

mscLpIlsFwdrLtFbMacTrIndex OBJECT-TYPE
   SYNTAX     NonReplicated 
   ACCESS     not-accessible
   STATUS     mandatory
   DESCRIPTION
     "This variable represents the index for the mscLpIlsFwdrLtFbMacTr tables."
::= { mscLpIlsFwdrLtFbMacTrRowStatusEntry 10 }

mscLpIlsFwdrLtFbMacTrTopTable OBJECT-TYPE
   SYNTAX     SEQUENCE OF MscLpIlsFwdrLtFbMacTrTopEntry
   ACCESS     not-accessible
   STATUS     mandatory
   DESCRIPTION
     "This group contains the operational data for the LanTest component 
      and its subcomponents."
::= { mscLpIlsFwdrLtFbMacTr 10 }

mscLpIlsFwdrLtFbMacTrTopEntry OBJECT-TYPE
   SYNTAX     MscLpIlsFwdrLtFbMacTrTopEntry
   ACCESS     not-accessible
   STATUS     mandatory
   DESCRIPTION
     "An entry in the mscLpIlsFwdrLtFbMacTrTopTable."
   INDEX {
      mscLpIndex,
      mscLpIlsFwdrIndex,
      mscLpIlsFwdrLtIndex,
      mscLpIlsFwdrLtFbIndex,
      mscLpIlsFwdrLtFbMacTrIndex }
::= { mscLpIlsFwdrLtFbMacTrTopTable 1 }

MscLpIlsFwdrLtFbMacTrTopEntry ::= SEQUENCE {
   mscLpIlsFwdrLtFbMacTrTData
      AsciiString }

mscLpIlsFwdrLtFbMacTrTData OBJECT-TYPE
   SYNTAX     AsciiString (SIZE (0..255))
   ACCESS     read-write
   STATUS     mandatory
   DESCRIPTION
     "This attribute is used to display and set attributes."
::= { mscLpIlsFwdrLtFbMacTrTopEntry 1 }


-- This component adds a data field to frame.

mscLpIlsFwdrLtFbData OBJECT IDENTIFIER ::= { mscLpIlsFwdrLtFb 6 }



mscLpIlsFwdrLtFbDataRowStatusTable OBJECT-TYPE
   SYNTAX     SEQUENCE OF MscLpIlsFwdrLtFbDataRowStatusEntry
   ACCESS     not-accessible
   STATUS     mandatory
   DESCRIPTION
     "This entry controls the addition and deletion of 
      mscLpIlsFwdrLtFbData components."
::= { mscLpIlsFwdrLtFbData 1 }

mscLpIlsFwdrLtFbDataRowStatusEntry OBJECT-TYPE
   SYNTAX     MscLpIlsFwdrLtFbDataRowStatusEntry
   ACCESS     not-accessible
   STATUS     mandatory
   DESCRIPTION
     "A single entry in the table represents a single 
      mscLpIlsFwdrLtFbData component."
   INDEX {
      mscLpIndex,
      mscLpIlsFwdrIndex,
      mscLpIlsFwdrLtIndex,
      mscLpIlsFwdrLtFbIndex,
      mscLpIlsFwdrLtFbDataIndex }
::= { mscLpIlsFwdrLtFbDataRowStatusTable 1 }

MscLpIlsFwdrLtFbDataRowStatusEntry ::= SEQUENCE {
   mscLpIlsFwdrLtFbDataRowStatus
      RowStatus,
   mscLpIlsFwdrLtFbDataComponentName
      DisplayString,
   mscLpIlsFwdrLtFbDataStorageType
      StorageType,
   mscLpIlsFwdrLtFbDataIndex
      NonReplicated }

mscLpIlsFwdrLtFbDataRowStatus OBJECT-TYPE
   SYNTAX     RowStatus 
   ACCESS     read-only
   STATUS     mandatory
   DESCRIPTION
     "This variable is used as the basis for SNMP naming of
      mscLpIlsFwdrLtFbData components.
      These components cannot be added nor deleted."
::= { mscLpIlsFwdrLtFbDataRowStatusEntry 1 }

mscLpIlsFwdrLtFbDataComponentName OBJECT-TYPE
   SYNTAX     DisplayString 
   ACCESS     read-only
   STATUS     mandatory
   DESCRIPTION
     "This variable provides the component's string name for
      use with the ASCII Console Interface"
::= { mscLpIlsFwdrLtFbDataRowStatusEntry 2 }

mscLpIlsFwdrLtFbDataStorageType OBJECT-TYPE
   SYNTAX     StorageType 
   ACCESS     read-only
   STATUS     mandatory
   DESCRIPTION
     "This variable represents the storage type value for the
      mscLpIlsFwdrLtFbData tables."
::= { mscLpIlsFwdrLtFbDataRowStatusEntry 4 }

mscLpIlsFwdrLtFbDataIndex OBJECT-TYPE
   SYNTAX     NonReplicated 
   ACCESS     not-accessible
   STATUS     mandatory
   DESCRIPTION
     "This variable represents the index for the mscLpIlsFwdrLtFbData tables."
::= { mscLpIlsFwdrLtFbDataRowStatusEntry 10 }

mscLpIlsFwdrLtFbDataTopTable OBJECT-TYPE
   SYNTAX     SEQUENCE OF MscLpIlsFwdrLtFbDataTopEntry
   ACCESS     not-accessible
   STATUS     mandatory
   DESCRIPTION
     "This group contains the operational data for the LanTest component 
      and its subcomponents."
::= { mscLpIlsFwdrLtFbData 10 }

mscLpIlsFwdrLtFbDataTopEntry OBJECT-TYPE
   SYNTAX     MscLpIlsFwdrLtFbDataTopEntry
   ACCESS     not-accessible
   STATUS     mandatory
   DESCRIPTION
     "An entry in the mscLpIlsFwdrLtFbDataTopTable."
   INDEX {
      mscLpIndex,
      mscLpIlsFwdrIndex,
      mscLpIlsFwdrLtIndex,
      mscLpIlsFwdrLtFbIndex,
      mscLpIlsFwdrLtFbDataIndex }
::= { mscLpIlsFwdrLtFbDataTopTable 1 }

MscLpIlsFwdrLtFbDataTopEntry ::= SEQUENCE {
   mscLpIlsFwdrLtFbDataTData
      AsciiString }

mscLpIlsFwdrLtFbDataTData OBJECT-TYPE
   SYNTAX     AsciiString (SIZE (0..255))
   ACCESS     read-write
   STATUS     mandatory
   DESCRIPTION
     "This attribute is used to display and set attributes."
::= { mscLpIlsFwdrLtFbDataTopEntry 1 }


-- LanTest IpHeader
-- This component adds an IP header to a frame or packet.

mscLpIlsFwdrLtFbIpH OBJECT IDENTIFIER ::= { mscLpIlsFwdrLtFb 7 }



mscLpIlsFwdrLtFbIpHRowStatusTable OBJECT-TYPE
   SYNTAX     SEQUENCE OF MscLpIlsFwdrLtFbIpHRowStatusEntry
   ACCESS     not-accessible
   STATUS     mandatory
   DESCRIPTION
     "This entry controls the addition and deletion of 
      mscLpIlsFwdrLtFbIpH components."
::= { mscLpIlsFwdrLtFbIpH 1 }

mscLpIlsFwdrLtFbIpHRowStatusEntry OBJECT-TYPE
   SYNTAX     MscLpIlsFwdrLtFbIpHRowStatusEntry
   ACCESS     not-accessible
   STATUS     mandatory
   DESCRIPTION
     "A single entry in the table represents a single 
      mscLpIlsFwdrLtFbIpH component."
   INDEX {
      mscLpIndex,
      mscLpIlsFwdrIndex,
      mscLpIlsFwdrLtIndex,
      mscLpIlsFwdrLtFbIndex,
      mscLpIlsFwdrLtFbIpHIndex }
::= { mscLpIlsFwdrLtFbIpHRowStatusTable 1 }

MscLpIlsFwdrLtFbIpHRowStatusEntry ::= SEQUENCE {
   mscLpIlsFwdrLtFbIpHRowStatus
      RowStatus,
   mscLpIlsFwdrLtFbIpHComponentName
      DisplayString,
   mscLpIlsFwdrLtFbIpHStorageType
      StorageType,
   mscLpIlsFwdrLtFbIpHIndex
      NonReplicated }

mscLpIlsFwdrLtFbIpHRowStatus OBJECT-TYPE
   SYNTAX     RowStatus 
   ACCESS     read-only
   STATUS     mandatory
   DESCRIPTION
     "This variable is used as the basis for SNMP naming of
      mscLpIlsFwdrLtFbIpH components.
      These components cannot be added nor deleted."
::= { mscLpIlsFwdrLtFbIpHRowStatusEntry 1 }

mscLpIlsFwdrLtFbIpHComponentName OBJECT-TYPE
   SYNTAX     DisplayString 
   ACCESS     read-only
   STATUS     mandatory
   DESCRIPTION
     "This variable provides the component's string name for
      use with the ASCII Console Interface"
::= { mscLpIlsFwdrLtFbIpHRowStatusEntry 2 }

mscLpIlsFwdrLtFbIpHStorageType OBJECT-TYPE
   SYNTAX     StorageType 
   ACCESS     read-only
   STATUS     mandatory
   DESCRIPTION
     "This variable represents the storage type value for the
      mscLpIlsFwdrLtFbIpH tables."
::= { mscLpIlsFwdrLtFbIpHRowStatusEntry 4 }

mscLpIlsFwdrLtFbIpHIndex OBJECT-TYPE
   SYNTAX     NonReplicated 
   ACCESS     not-accessible
   STATUS     mandatory
   DESCRIPTION
     "This variable represents the index for the mscLpIlsFwdrLtFbIpH tables."
::= { mscLpIlsFwdrLtFbIpHRowStatusEntry 10 }

mscLpIlsFwdrLtFbIpHTopTable OBJECT-TYPE
   SYNTAX     SEQUENCE OF MscLpIlsFwdrLtFbIpHTopEntry
   ACCESS     not-accessible
   STATUS     mandatory
   DESCRIPTION
     "This group contains the operational data for the LanTest component 
      and its subcomponents."
::= { mscLpIlsFwdrLtFbIpH 10 }

mscLpIlsFwdrLtFbIpHTopEntry OBJECT-TYPE
   SYNTAX     MscLpIlsFwdrLtFbIpHTopEntry
   ACCESS     not-accessible
   STATUS     mandatory
   DESCRIPTION
     "An entry in the mscLpIlsFwdrLtFbIpHTopTable."
   INDEX {
      mscLpIndex,
      mscLpIlsFwdrIndex,
      mscLpIlsFwdrLtIndex,
      mscLpIlsFwdrLtFbIndex,
      mscLpIlsFwdrLtFbIpHIndex }
::= { mscLpIlsFwdrLtFbIpHTopTable 1 }

MscLpIlsFwdrLtFbIpHTopEntry ::= SEQUENCE {
   mscLpIlsFwdrLtFbIpHTData
      AsciiString }

mscLpIlsFwdrLtFbIpHTData OBJECT-TYPE
   SYNTAX     AsciiString (SIZE (0..255))
   ACCESS     read-write
   STATUS     mandatory
   DESCRIPTION
     "This attribute is used to display and set attributes."
::= { mscLpIlsFwdrLtFbIpHTopEntry 1 }


-- LanTest LlcHeader
-- This component adds an LLC 802.2 or Ethernet header to a frame 
-- or packet.

mscLpIlsFwdrLtFbLlch OBJECT IDENTIFIER ::= { mscLpIlsFwdrLtFb 8 }



mscLpIlsFwdrLtFbLlchRowStatusTable OBJECT-TYPE
   SYNTAX     SEQUENCE OF MscLpIlsFwdrLtFbLlchRowStatusEntry
   ACCESS     not-accessible
   STATUS     mandatory
   DESCRIPTION
     "This entry controls the addition and deletion of 
      mscLpIlsFwdrLtFbLlch components."
::= { mscLpIlsFwdrLtFbLlch 1 }

mscLpIlsFwdrLtFbLlchRowStatusEntry OBJECT-TYPE
   SYNTAX     MscLpIlsFwdrLtFbLlchRowStatusEntry
   ACCESS     not-accessible
   STATUS     mandatory
   DESCRIPTION
     "A single entry in the table represents a single 
      mscLpIlsFwdrLtFbLlch component."
   INDEX {
      mscLpIndex,
      mscLpIlsFwdrIndex,
      mscLpIlsFwdrLtIndex,
      mscLpIlsFwdrLtFbIndex,
      mscLpIlsFwdrLtFbLlchIndex }
::= { mscLpIlsFwdrLtFbLlchRowStatusTable 1 }

MscLpIlsFwdrLtFbLlchRowStatusEntry ::= SEQUENCE {
   mscLpIlsFwdrLtFbLlchRowStatus
      RowStatus,
   mscLpIlsFwdrLtFbLlchComponentName
      DisplayString,
   mscLpIlsFwdrLtFbLlchStorageType
      StorageType,
   mscLpIlsFwdrLtFbLlchIndex
      NonReplicated }

mscLpIlsFwdrLtFbLlchRowStatus OBJECT-TYPE
   SYNTAX     RowStatus 
   ACCESS     read-only
   STATUS     mandatory
   DESCRIPTION
     "This variable is used as the basis for SNMP naming of
      mscLpIlsFwdrLtFbLlch components.
      These components cannot be added nor deleted."
::= { mscLpIlsFwdrLtFbLlchRowStatusEntry 1 }

mscLpIlsFwdrLtFbLlchComponentName OBJECT-TYPE
   SYNTAX     DisplayString 
   ACCESS     read-only
   STATUS     mandatory
   DESCRIPTION
     "This variable provides the component's string name for
      use with the ASCII Console Interface"
::= { mscLpIlsFwdrLtFbLlchRowStatusEntry 2 }

mscLpIlsFwdrLtFbLlchStorageType OBJECT-TYPE
   SYNTAX     StorageType 
   ACCESS     read-only
   STATUS     mandatory
   DESCRIPTION
     "This variable represents the storage type value for the
      mscLpIlsFwdrLtFbLlch tables."
::= { mscLpIlsFwdrLtFbLlchRowStatusEntry 4 }

mscLpIlsFwdrLtFbLlchIndex OBJECT-TYPE
   SYNTAX     NonReplicated 
   ACCESS     not-accessible
   STATUS     mandatory
   DESCRIPTION
     "This variable represents the index for the mscLpIlsFwdrLtFbLlch tables."
::= { mscLpIlsFwdrLtFbLlchRowStatusEntry 10 }

mscLpIlsFwdrLtFbLlchTopTable OBJECT-TYPE
   SYNTAX     SEQUENCE OF MscLpIlsFwdrLtFbLlchTopEntry
   ACCESS     not-accessible
   STATUS     mandatory
   DESCRIPTION
     "This group contains the operational data for the LanTest component 
      and its subcomponents."
::= { mscLpIlsFwdrLtFbLlch 10 }

mscLpIlsFwdrLtFbLlchTopEntry OBJECT-TYPE
   SYNTAX     MscLpIlsFwdrLtFbLlchTopEntry
   ACCESS     not-accessible
   STATUS     mandatory
   DESCRIPTION
     "An entry in the mscLpIlsFwdrLtFbLlchTopTable."
   INDEX {
      mscLpIndex,
      mscLpIlsFwdrIndex,
      mscLpIlsFwdrLtIndex,
      mscLpIlsFwdrLtFbIndex,
      mscLpIlsFwdrLtFbLlchIndex }
::= { mscLpIlsFwdrLtFbLlchTopTable 1 }

MscLpIlsFwdrLtFbLlchTopEntry ::= SEQUENCE {
   mscLpIlsFwdrLtFbLlchTData
      AsciiString }

mscLpIlsFwdrLtFbLlchTData OBJECT-TYPE
   SYNTAX     AsciiString (SIZE (0..255))
   ACCESS     read-write
   STATUS     mandatory
   DESCRIPTION
     "This attribute is used to display and set attributes."
::= { mscLpIlsFwdrLtFbLlchTopEntry 1 }


-- This component adds an AppleTalk header to a frame or packet.

mscLpIlsFwdrLtFbAppleH OBJECT IDENTIFIER ::= { mscLpIlsFwdrLtFb 9 }



mscLpIlsFwdrLtFbAppleHRowStatusTable OBJECT-TYPE
   SYNTAX     SEQUENCE OF MscLpIlsFwdrLtFbAppleHRowStatusEntry
   ACCESS     not-accessible
   STATUS     mandatory
   DESCRIPTION
     "This entry controls the addition and deletion of 
      mscLpIlsFwdrLtFbAppleH components."
::= { mscLpIlsFwdrLtFbAppleH 1 }

mscLpIlsFwdrLtFbAppleHRowStatusEntry OBJECT-TYPE
   SYNTAX     MscLpIlsFwdrLtFbAppleHRowStatusEntry
   ACCESS     not-accessible
   STATUS     mandatory
   DESCRIPTION
     "A single entry in the table represents a single 
      mscLpIlsFwdrLtFbAppleH component."
   INDEX {
      mscLpIndex,
      mscLpIlsFwdrIndex,
      mscLpIlsFwdrLtIndex,
      mscLpIlsFwdrLtFbIndex,
      mscLpIlsFwdrLtFbAppleHIndex }
::= { mscLpIlsFwdrLtFbAppleHRowStatusTable 1 }

MscLpIlsFwdrLtFbAppleHRowStatusEntry ::= SEQUENCE {
   mscLpIlsFwdrLtFbAppleHRowStatus
      RowStatus,
   mscLpIlsFwdrLtFbAppleHComponentName
      DisplayString,
   mscLpIlsFwdrLtFbAppleHStorageType
      StorageType,
   mscLpIlsFwdrLtFbAppleHIndex
      NonReplicated }

mscLpIlsFwdrLtFbAppleHRowStatus OBJECT-TYPE
   SYNTAX     RowStatus 
   ACCESS     read-only
   STATUS     mandatory
   DESCRIPTION
     "This variable is used as the basis for SNMP naming of
      mscLpIlsFwdrLtFbAppleH components.
      These components cannot be added nor deleted."
::= { mscLpIlsFwdrLtFbAppleHRowStatusEntry 1 }

mscLpIlsFwdrLtFbAppleHComponentName OBJECT-TYPE
   SYNTAX     DisplayString 
   ACCESS     read-only
   STATUS     mandatory
   DESCRIPTION
     "This variable provides the component's string name for
      use with the ASCII Console Interface"
::= { mscLpIlsFwdrLtFbAppleHRowStatusEntry 2 }

mscLpIlsFwdrLtFbAppleHStorageType OBJECT-TYPE
   SYNTAX     StorageType 
   ACCESS     read-only
   STATUS     mandatory
   DESCRIPTION
     "This variable represents the storage type value for the
      mscLpIlsFwdrLtFbAppleH tables."
::= { mscLpIlsFwdrLtFbAppleHRowStatusEntry 4 }

mscLpIlsFwdrLtFbAppleHIndex OBJECT-TYPE
   SYNTAX     NonReplicated 
   ACCESS     not-accessible
   STATUS     mandatory
   DESCRIPTION
     "This variable represents the index for the mscLpIlsFwdrLtFbAppleH tables."
::= { mscLpIlsFwdrLtFbAppleHRowStatusEntry 10 }

mscLpIlsFwdrLtFbAppleHTopTable OBJECT-TYPE
   SYNTAX     SEQUENCE OF MscLpIlsFwdrLtFbAppleHTopEntry
   ACCESS     not-accessible
   STATUS     mandatory
   DESCRIPTION
     "This group contains the operational data for the LanTest component 
      and its subcomponents."
::= { mscLpIlsFwdrLtFbAppleH 10 }

mscLpIlsFwdrLtFbAppleHTopEntry OBJECT-TYPE
   SYNTAX     MscLpIlsFwdrLtFbAppleHTopEntry
   ACCESS     not-accessible
   STATUS     mandatory
   DESCRIPTION
     "An entry in the mscLpIlsFwdrLtFbAppleHTopTable."
   INDEX {
      mscLpIndex,
      mscLpIlsFwdrIndex,
      mscLpIlsFwdrLtIndex,
      mscLpIlsFwdrLtFbIndex,
      mscLpIlsFwdrLtFbAppleHIndex }
::= { mscLpIlsFwdrLtFbAppleHTopTable 1 }

MscLpIlsFwdrLtFbAppleHTopEntry ::= SEQUENCE {
   mscLpIlsFwdrLtFbAppleHTData
      AsciiString }

mscLpIlsFwdrLtFbAppleHTData OBJECT-TYPE
   SYNTAX     AsciiString (SIZE (0..255))
   ACCESS     read-write
   STATUS     mandatory
   DESCRIPTION
     "This attribute is used to display and set attributes."
::= { mscLpIlsFwdrLtFbAppleHTopEntry 1 }


-- This component adds an IPX header to a frame or packet.

mscLpIlsFwdrLtFbIpxH OBJECT IDENTIFIER ::= { mscLpIlsFwdrLtFb 10 }



mscLpIlsFwdrLtFbIpxHRowStatusTable OBJECT-TYPE
   SYNTAX     SEQUENCE OF MscLpIlsFwdrLtFbIpxHRowStatusEntry
   ACCESS     not-accessible
   STATUS     mandatory
   DESCRIPTION
     "This entry controls the addition and deletion of 
      mscLpIlsFwdrLtFbIpxH components."
::= { mscLpIlsFwdrLtFbIpxH 1 }

mscLpIlsFwdrLtFbIpxHRowStatusEntry OBJECT-TYPE
   SYNTAX     MscLpIlsFwdrLtFbIpxHRowStatusEntry
   ACCESS     not-accessible
   STATUS     mandatory
   DESCRIPTION
     "A single entry in the table represents a single 
      mscLpIlsFwdrLtFbIpxH component."
   INDEX {
      mscLpIndex,
      mscLpIlsFwdrIndex,
      mscLpIlsFwdrLtIndex,
      mscLpIlsFwdrLtFbIndex,
      mscLpIlsFwdrLtFbIpxHIndex }
::= { mscLpIlsFwdrLtFbIpxHRowStatusTable 1 }

MscLpIlsFwdrLtFbIpxHRowStatusEntry ::= SEQUENCE {
   mscLpIlsFwdrLtFbIpxHRowStatus
      RowStatus,
   mscLpIlsFwdrLtFbIpxHComponentName
      DisplayString,
   mscLpIlsFwdrLtFbIpxHStorageType
      StorageType,
   mscLpIlsFwdrLtFbIpxHIndex
      NonReplicated }

mscLpIlsFwdrLtFbIpxHRowStatus OBJECT-TYPE
   SYNTAX     RowStatus 
   ACCESS     read-only
   STATUS     mandatory
   DESCRIPTION
     "This variable is used as the basis for SNMP naming of
      mscLpIlsFwdrLtFbIpxH components.
      These components cannot be added nor deleted."
::= { mscLpIlsFwdrLtFbIpxHRowStatusEntry 1 }

mscLpIlsFwdrLtFbIpxHComponentName OBJECT-TYPE
   SYNTAX     DisplayString 
   ACCESS     read-only
   STATUS     mandatory
   DESCRIPTION
     "This variable provides the component's string name for
      use with the ASCII Console Interface"
::= { mscLpIlsFwdrLtFbIpxHRowStatusEntry 2 }

mscLpIlsFwdrLtFbIpxHStorageType OBJECT-TYPE
   SYNTAX     StorageType 
   ACCESS     read-only
   STATUS     mandatory
   DESCRIPTION
     "This variable represents the storage type value for the
      mscLpIlsFwdrLtFbIpxH tables."
::= { mscLpIlsFwdrLtFbIpxHRowStatusEntry 4 }

mscLpIlsFwdrLtFbIpxHIndex OBJECT-TYPE
   SYNTAX     NonReplicated 
   ACCESS     not-accessible
   STATUS     mandatory
   DESCRIPTION
     "This variable represents the index for the mscLpIlsFwdrLtFbIpxH tables."
::= { mscLpIlsFwdrLtFbIpxHRowStatusEntry 10 }

mscLpIlsFwdrLtFbIpxHTopTable OBJECT-TYPE
   SYNTAX     SEQUENCE OF MscLpIlsFwdrLtFbIpxHTopEntry
   ACCESS     not-accessible
   STATUS     mandatory
   DESCRIPTION
     "This group contains the operational data for the LanTest component 
      and its subcomponents."
::= { mscLpIlsFwdrLtFbIpxH 10 }

mscLpIlsFwdrLtFbIpxHTopEntry OBJECT-TYPE
   SYNTAX     MscLpIlsFwdrLtFbIpxHTopEntry
   ACCESS     not-accessible
   STATUS     mandatory
   DESCRIPTION
     "An entry in the mscLpIlsFwdrLtFbIpxHTopTable."
   INDEX {
      mscLpIndex,
      mscLpIlsFwdrIndex,
      mscLpIlsFwdrLtIndex,
      mscLpIlsFwdrLtFbIndex,
      mscLpIlsFwdrLtFbIpxHIndex }
::= { mscLpIlsFwdrLtFbIpxHTopTable 1 }

MscLpIlsFwdrLtFbIpxHTopEntry ::= SEQUENCE {
   mscLpIlsFwdrLtFbIpxHTData
      AsciiString }

mscLpIlsFwdrLtFbIpxHTData OBJECT-TYPE
   SYNTAX     AsciiString (SIZE (0..255))
   ACCESS     read-write
   STATUS     mandatory
   DESCRIPTION
     "This attribute is used to display and set attributes."
::= { mscLpIlsFwdrLtFbIpxHTopEntry 1 }


-- LanTest Control
-- This component controls the overall testing by telling the 
-- FrameBuild component to start and check the FrameCompare 
-- component to see if the test is complete.

mscLpIlsFwdrLtCntl OBJECT IDENTIFIER ::= { mscLpIlsFwdrLt 6 }



mscLpIlsFwdrLtCntlRowStatusTable OBJECT-TYPE
   SYNTAX     SEQUENCE OF MscLpIlsFwdrLtCntlRowStatusEntry
   ACCESS     not-accessible
   STATUS     mandatory
   DESCRIPTION
     "This entry controls the addition and deletion of 
      mscLpIlsFwdrLtCntl components."
::= { mscLpIlsFwdrLtCntl 1 }

mscLpIlsFwdrLtCntlRowStatusEntry OBJECT-TYPE
   SYNTAX     MscLpIlsFwdrLtCntlRowStatusEntry
   ACCESS     not-accessible
   STATUS     mandatory
   DESCRIPTION
     "A single entry in the table represents a single 
      mscLpIlsFwdrLtCntl component."
   INDEX {
      mscLpIndex,
      mscLpIlsFwdrIndex,
      mscLpIlsFwdrLtIndex,
      mscLpIlsFwdrLtCntlIndex }
::= { mscLpIlsFwdrLtCntlRowStatusTable 1 }

MscLpIlsFwdrLtCntlRowStatusEntry ::= SEQUENCE {
   mscLpIlsFwdrLtCntlRowStatus
      RowStatus,
   mscLpIlsFwdrLtCntlComponentName
      DisplayString,
   mscLpIlsFwdrLtCntlStorageType
      StorageType,
   mscLpIlsFwdrLtCntlIndex
      NonReplicated }

mscLpIlsFwdrLtCntlRowStatus OBJECT-TYPE
   SYNTAX     RowStatus 
   ACCESS     read-only
   STATUS     mandatory
   DESCRIPTION
     "This variable is used as the basis for SNMP naming of
      mscLpIlsFwdrLtCntl components.
      These components cannot be added nor deleted."
::= { mscLpIlsFwdrLtCntlRowStatusEntry 1 }

mscLpIlsFwdrLtCntlComponentName OBJECT-TYPE
   SYNTAX     DisplayString 
   ACCESS     read-only
   STATUS     mandatory
   DESCRIPTION
     "This variable provides the component's string name for
      use with the ASCII Console Interface"
::= { mscLpIlsFwdrLtCntlRowStatusEntry 2 }

mscLpIlsFwdrLtCntlStorageType OBJECT-TYPE
   SYNTAX     StorageType 
   ACCESS     read-only
   STATUS     mandatory
   DESCRIPTION
     "This variable represents the storage type value for the
      mscLpIlsFwdrLtCntl tables."
::= { mscLpIlsFwdrLtCntlRowStatusEntry 4 }

mscLpIlsFwdrLtCntlIndex OBJECT-TYPE
   SYNTAX     NonReplicated 
   ACCESS     not-accessible
   STATUS     mandatory
   DESCRIPTION
     "This variable represents the index for the mscLpIlsFwdrLtCntl tables."
::= { mscLpIlsFwdrLtCntlRowStatusEntry 10 }

mscLpIlsFwdrLtCntlTopTable OBJECT-TYPE
   SYNTAX     SEQUENCE OF MscLpIlsFwdrLtCntlTopEntry
   ACCESS     not-accessible
   STATUS     mandatory
   DESCRIPTION
     "This group contains the operational data for the LanTest component 
      and its subcomponents."
::= { mscLpIlsFwdrLtCntl 10 }

mscLpIlsFwdrLtCntlTopEntry OBJECT-TYPE
   SYNTAX     MscLpIlsFwdrLtCntlTopEntry
   ACCESS     not-accessible
   STATUS     mandatory
   DESCRIPTION
     "An entry in the mscLpIlsFwdrLtCntlTopTable."
   INDEX {
      mscLpIndex,
      mscLpIlsFwdrIndex,
      mscLpIlsFwdrLtIndex,
      mscLpIlsFwdrLtCntlIndex }
::= { mscLpIlsFwdrLtCntlTopTable 1 }

MscLpIlsFwdrLtCntlTopEntry ::= SEQUENCE {
   mscLpIlsFwdrLtCntlTData
      AsciiString }

mscLpIlsFwdrLtCntlTData OBJECT-TYPE
   SYNTAX     AsciiString (SIZE (0..255))
   ACCESS     read-write
   STATUS     mandatory
   DESCRIPTION
     "This attribute is used to display and set attributes."
::= { mscLpIlsFwdrLtCntlTopEntry 1 }


-- Lp/n Fddi/n Test, or
-- Lp/n Ethernet/n Test, or
-- Lp/n TokenRing/n Test, or
-- Lp/n IlsForwarder/n Test
-- The Test component is used to do StartUp port test for LAN cards.

mscLpIlsFwdrTest OBJECT IDENTIFIER ::= { mscLpIlsFwdr 5 }



mscLpIlsFwdrTestRowStatusTable OBJECT-TYPE
   SYNTAX     SEQUENCE OF MscLpIlsFwdrTestRowStatusEntry
   ACCESS     not-accessible
   STATUS     mandatory
   DESCRIPTION
     "This entry controls the addition and deletion of 
      mscLpIlsFwdrTest components."
::= { mscLpIlsFwdrTest 1 }

mscLpIlsFwdrTestRowStatusEntry OBJECT-TYPE
   SYNTAX     MscLpIlsFwdrTestRowStatusEntry
   ACCESS     not-accessible
   STATUS     mandatory
   DESCRIPTION
     "A single entry in the table represents a single 
      mscLpIlsFwdrTest component."
   INDEX {
      mscLpIndex,
      mscLpIlsFwdrIndex,
      mscLpIlsFwdrTestIndex }
::= { mscLpIlsFwdrTestRowStatusTable 1 }

MscLpIlsFwdrTestRowStatusEntry ::= SEQUENCE {
   mscLpIlsFwdrTestRowStatus
      RowStatus,
   mscLpIlsFwdrTestComponentName
      DisplayString,
   mscLpIlsFwdrTestStorageType
      StorageType,
   mscLpIlsFwdrTestIndex
      NonReplicated }

mscLpIlsFwdrTestRowStatus OBJECT-TYPE
   SYNTAX     RowStatus 
   ACCESS     read-only
   STATUS     mandatory
   DESCRIPTION
     "This variable is used as the basis for SNMP naming of
      mscLpIlsFwdrTest components.
      These components cannot be added nor deleted."
::= { mscLpIlsFwdrTestRowStatusEntry 1 }

mscLpIlsFwdrTestComponentName OBJECT-TYPE
   SYNTAX     DisplayString 
   ACCESS     read-only
   STATUS     mandatory
   DESCRIPTION
     "This variable provides the component's string name for
      use with the ASCII Console Interface"
::= { mscLpIlsFwdrTestRowStatusEntry 2 }

mscLpIlsFwdrTestStorageType OBJECT-TYPE
   SYNTAX     StorageType 
   ACCESS     read-only
   STATUS     mandatory
   DESCRIPTION
     "This variable represents the storage type value for the
      mscLpIlsFwdrTest tables."
::= { mscLpIlsFwdrTestRowStatusEntry 4 }

mscLpIlsFwdrTestIndex OBJECT-TYPE
   SYNTAX     NonReplicated 
   ACCESS     not-accessible
   STATUS     mandatory
   DESCRIPTION
     "This variable represents the index for the mscLpIlsFwdrTest tables."
::= { mscLpIlsFwdrTestRowStatusEntry 10 }

mscLpIlsFwdrTestPTOTable OBJECT-TYPE
   SYNTAX     SEQUENCE OF MscLpIlsFwdrTestPTOEntry
   ACCESS     not-accessible
   STATUS     mandatory
   DESCRIPTION
     "This group contains the operational data for the LanPortTest 
      component."
::= { mscLpIlsFwdrTest 10 }

mscLpIlsFwdrTestPTOEntry OBJECT-TYPE
   SYNTAX     MscLpIlsFwdrTestPTOEntry
   ACCESS     not-accessible
   STATUS     mandatory
   DESCRIPTION
     "An entry in the mscLpIlsFwdrTestPTOTable."
   INDEX {
      mscLpIndex,
      mscLpIlsFwdrIndex,
      mscLpIlsFwdrTestIndex }
::= { mscLpIlsFwdrTestPTOTable 1 }

MscLpIlsFwdrTestPTOEntry ::= SEQUENCE {
   mscLpIlsFwdrTestType
      INTEGER,
   mscLpIlsFwdrTestFrmSize
      Unsigned32,
   mscLpIlsFwdrTestDuration
      Unsigned32 }

mscLpIlsFwdrTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { mscLpIlsFwdrTestPTOEntry 1 }

mscLpIlsFwdrTestFrmSize OBJECT-TYPE
   SYNTAX     Unsigned32 (4..4096)
   ACCESS     read-write
   STATUS     mandatory
   DESCRIPTION
     "This attribute defines the size of the test data frames in number of 
      bytes."
   DEFVAL     { 1024 }
::= { mscLpIlsFwdrTestPTOEntry 2 }

mscLpIlsFwdrTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { mscLpIlsFwdrTestPTOEntry 3 }

mscLpIlsFwdrTestResultsTable OBJECT-TYPE
   SYNTAX     SEQUENCE OF MscLpIlsFwdrTestResultsEntry
   ACCESS     not-accessible
   STATUS     mandatory
   DESCRIPTION
     "This group contains all the statistics related attributes of the Test 
      component."
::= { mscLpIlsFwdrTest 11 }

mscLpIlsFwdrTestResultsEntry OBJECT-TYPE
   SYNTAX     MscLpIlsFwdrTestResultsEntry
   ACCESS     not-accessible
   STATUS     mandatory
   DESCRIPTION
     "An entry in the mscLpIlsFwdrTestResultsTable."
   INDEX {
      mscLpIndex,
      mscLpIlsFwdrIndex,
      mscLpIlsFwdrTestIndex }
::= { mscLpIlsFwdrTestResultsTable 1 }

MscLpIlsFwdrTestResultsEntry ::= SEQUENCE {
   mscLpIlsFwdrTestElapsedTime
      Counter32,
   mscLpIlsFwdrTestTimeRemaining
      Unsigned32,
   mscLpIlsFwdrTestCauseOfTermination
      INTEGER,
   mscLpIlsFwdrTestFrmTx
      PassportCounter64,
   mscLpIlsFwdrTestBitsTx
      PassportCounter64,
   mscLpIlsFwdrTestFrmRx
      PassportCounter64,
   mscLpIlsFwdrTestBitsRx
      PassportCounter64,
   mscLpIlsFwdrTestErroredFrmRx
      PassportCounter64 }

mscLpIlsFwdrTestElapsedTime OBJECT-TYPE
   SYNTAX     Counter32 
   ACCESS     read-only
   STATUS     mandatory
   DESCRIPTION
     "This attribute is the number of minutes elapsed since the test started 
      for an externalLoop test. For a data test, this is the time since test 
      data was first transmitted."
::= { mscLpIlsFwdrTestResultsEntry 4 }

mscLpIlsFwdrTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { mscLpIlsFwdrTestResultsEntry 5 }

mscLpIlsFwdrTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { mscLpIlsFwdrTestResultsEntry 6 }

mscLpIlsFwdrTestFrmTx OBJECT-TYPE
   SYNTAX     PassportCounter64 
   ACCESS     read-only
   STATUS     mandatory
   DESCRIPTION
     "This attribute is the total number of frames sent during the test 
      period. This counter is not expected to reach its maximum value."
::= { mscLpIlsFwdrTestResultsEntry 7 }

mscLpIlsFwdrTestBitsTx OBJECT-TYPE
   SYNTAX     PassportCounter64 
   ACCESS     read-only
   STATUS     mandatory
   DESCRIPTION
     "This attribute is the total number of bits sent during the test period. 
      This counter is not expected to reach its maximum value."
::= { mscLpIlsFwdrTestResultsEntry 8 }

mscLpIlsFwdrTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { mscLpIlsFwdrTestResultsEntry 9 }

mscLpIlsFwdrTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { mscLpIlsFwdrTestResultsEntry 10 }

mscLpIlsFwdrTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { mscLpIlsFwdrTestResultsEntry 11 }


-- Lp/n Ethernet100BaseT/n
-- This component defines an instance of a 100BaseT Ethernet station 
-- attached to a bus. One instance of this component must be created for 
-- each hardware interface.

mscLpEth100 OBJECT IDENTIFIER ::= { mscLp 25 }



mscLpEth100RowStatusTable OBJECT-TYPE
   SYNTAX     SEQUENCE OF MscLpEth100RowStatusEntry
   ACCESS     not-accessible
   STATUS     mandatory
   DESCRIPTION
     "This entry controls the addition and deletion of 
      mscLpEth100 components."
::= { mscLpEth100 1 }

mscLpEth100RowStatusEntry OBJECT-TYPE
   SYNTAX     MscLpEth100RowStatusEntry
   ACCESS     not-accessible
   STATUS     mandatory
   DESCRIPTION
     "A single entry in the table represents a single 
      mscLpEth100 component."
   INDEX {
      mscLpIndex,
      mscLpEth100Index }
::= { mscLpEth100RowStatusTable 1 }

MscLpEth100RowStatusEntry ::= SEQUENCE {
   mscLpEth100RowStatus
      RowStatus,
   mscLpEth100ComponentName
      DisplayString,
   mscLpEth100StorageType
      StorageType,
   mscLpEth100Index
      Integer32 }

mscLpEth100RowStatus OBJECT-TYPE
   SYNTAX     RowStatus 
   ACCESS     read-write
   STATUS     mandatory
   DESCRIPTION
     "This variable is used as the basis for SNMP naming of
      mscLpEth100 components.
      These components can be added and deleted."
::= { mscLpEth100RowStatusEntry 1 }

mscLpEth100ComponentName OBJECT-TYPE
   SYNTAX     DisplayString 
   ACCESS     read-only
   STATUS     mandatory
   DESCRIPTION
     "This variable provides the component's string name for
      use with the ASCII Console Interface"
::= { mscLpEth100RowStatusEntry 2 }

mscLpEth100StorageType OBJECT-TYPE
   SYNTAX     StorageType 
   ACCESS     read-only
   STATUS     mandatory
   DESCRIPTION
     "This variable represents the storage type value for the
      mscLpEth100 tables."
::= { mscLpEth100RowStatusEntry 4 }

mscLpEth100Index OBJECT-TYPE
   SYNTAX     Integer32 (0..1)
   ACCESS     not-accessible
   STATUS     mandatory
   DESCRIPTION
     "This variable represents the index for the mscLpEth100 tables."
::= { mscLpEth100RowStatusEntry 10 }

mscLpEth100CidDataTable OBJECT-TYPE
   SYNTAX     SEQUENCE OF MscLpEth100CidDataEntry
   ACCESS     not-accessible
   STATUS     mandatory
   DESCRIPTION
     "This group contains the attribute for a component's Customer 
      Identifier (CID). Refer to the attribute description for a detailed 
      explanation of CIDs."
::= { mscLpEth100 10 }

mscLpEth100CidDataEntry OBJECT-TYPE
   SYNTAX     MscLpEth100CidDataEntry
   ACCESS     not-accessible
   STATUS     mandatory
   DESCRIPTION
     "An entry in the mscLpEth100CidDataTable."
   INDEX {
      mscLpIndex,
      mscLpEth100Index }
::= { mscLpEth100CidDataTable 1 }

MscLpEth100CidDataEntry ::= SEQUENCE {
   mscLpEth100CustomerIdentifier
      Unsigned32 }

mscLpEth100CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscLpEth100CidDataEntry 1 }

mscLpEth100IfEntryTable OBJECT-TYPE
   SYNTAX     SEQUENCE OF MscLpEth100IfEntryEntry
   ACCESS     not-accessible
   STATUS     mandatory
   DESCRIPTION
     "This group contains the provisionable attributes for the ifEntry."
::= { mscLpEth100 11 }

mscLpEth100IfEntryEntry OBJECT-TYPE
   SYNTAX     MscLpEth100IfEntryEntry
   ACCESS     not-accessible
   STATUS     mandatory
   DESCRIPTION
     "An entry in the mscLpEth100IfEntryTable."
   INDEX {
      mscLpIndex,
      mscLpEth100Index }
::= { mscLpEth100IfEntryTable 1 }

MscLpEth100IfEntryEntry ::= SEQUENCE {
   mscLpEth100IfAdminStatus
      INTEGER,
   mscLpEth100IfIndex
      InterfaceIndex }

mscLpEth100IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscLpEth100IfEntryEntry 1 }

mscLpEth100IfIndex OBJECT-TYPE
   SYNTAX     InterfaceIndex (1..65535)
   ACCESS     read-only
   STATUS     mandatory
   DESCRIPTION
     "This is the index for the IfEntry. Its value is automatically initialized 
      during the provisioning process."
::= { mscLpEth100IfEntryEntry 2 }

mscLpEth100ProvTable OBJECT-TYPE
   SYNTAX     SEQUENCE OF MscLpEth100ProvEntry
   ACCESS     not-accessible
   STATUS     mandatory
   DESCRIPTION
     "This group contains the provisionable attributes of the Eth100BaseT 
      component."
::= { mscLpEth100 12 }

mscLpEth100ProvEntry OBJECT-TYPE
   SYNTAX     MscLpEth100ProvEntry
   ACCESS     not-accessible
   STATUS     mandatory
   DESCRIPTION
     "An entry in the mscLpEth100ProvTable."
   INDEX {
      mscLpIndex,
      mscLpEth100Index }
::= { mscLpEth100ProvTable 1 }

MscLpEth100ProvEntry ::= SEQUENCE {
   mscLpEth100DuplexMode
      INTEGER,
   mscLpEth100LineSpeed
      Unsigned32,
   mscLpEth100AutoNegotiation
      INTEGER,
   mscLpEth100ApplicationFramerName
      Link }

mscLpEth100DuplexMode OBJECT-TYPE
   SYNTAX     INTEGER  {
                 half(1),
                 full(2) }
   ACCESS     read-write
   STATUS     mandatory
   DESCRIPTION
     "This attribute specifies the duplex mode of the port. This attribute is 
      ignored if auto negotiation is successful."
   DEFVAL     { half }
::= { mscLpEth100ProvEntry 1 }

mscLpEth100LineSpeed OBJECT-TYPE
   SYNTAX     Unsigned32 (10 | 100)
   ACCESS     read-write
   STATUS     mandatory
   DESCRIPTION
     "This attribute sets the operating speed for the Ethernet 100BaseT port. 
      This attribute is ignored if auto negotiation is successful."
   DEFVAL     { 100 }
::= { mscLpEth100ProvEntry 2 }

mscLpEth100AutoNegotiation OBJECT-TYPE
   SYNTAX     INTEGER  {
                 enabled(1),
                 disabled(2) }
   ACCESS     read-write
   STATUS     mandatory
   DESCRIPTION
     "This attribute is used to select whether or not the port does auto 
      negotiation. The provisionable values of duplexMode and lineSpeed are 
      ignored if auto negotiation is successful. Refer to the operational 
      attribute autoNegStatus for auto negotiation results."
   DEFVAL     { enabled }
::= { mscLpEth100ProvEntry 3 }

mscLpEth100ApplicationFramerName OBJECT-TYPE
   SYNTAX     Link 
   ACCESS     read-write
   STATUS     mandatory
   DESCRIPTION
     "This attribute contains the component name of a Framer which is 
      associated with the Eth100BaseT component. This defines which Lan 
      Application will be using this Eth100BaseT interface."
::= { mscLpEth100ProvEntry 4 }

mscLpEth100AdminInfoTable OBJECT-TYPE
   SYNTAX     SEQUENCE OF MscLpEth100AdminInfoEntry
   ACCESS     not-accessible
   STATUS     mandatory
   DESCRIPTION
     "This group contains the attributes pertaining to the vendor of the 
      equipment."
::= { mscLpEth100 13 }

mscLpEth100AdminInfoEntry OBJECT-TYPE
   SYNTAX     MscLpEth100AdminInfoEntry
   ACCESS     not-accessible
   STATUS     mandatory
   DESCRIPTION
     "An entry in the mscLpEth100AdminInfoTable."
   INDEX {
      mscLpIndex,
      mscLpEth100Index }
::= { mscLpEth100AdminInfoTable 1 }

MscLpEth100AdminInfoEntry ::= SEQUENCE {
   mscLpEth100Vendor
      AsciiString,
   mscLpEth100CommentText
      AsciiString }

mscLpEth100Vendor OBJECT-TYPE
   SYNTAX     AsciiString (SIZE (0..20))
   ACCESS     read-write
   STATUS     mandatory
   DESCRIPTION
     "This is the name of the vendor supplying the facility."
::= { mscLpEth100AdminInfoEntry 1 }

mscLpEth100CommentText OBJECT-TYPE
   SYNTAX     AsciiString (SIZE (0..60))
   ACCESS     read-write
   STATUS     mandatory
   DESCRIPTION
     "Any miscellaneous text about the facility."
::= { mscLpEth100AdminInfoEntry 2 }

mscLpEth100StateTable OBJECT-TYPE
   SYNTAX     SEQUENCE OF MscLpEth100StateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscLpEth100 15 }

mscLpEth100StateEntry OBJECT-TYPE
   SYNTAX     MscLpEth100StateEntry
   ACCESS     not-accessible
   STATUS     mandatory
   DESCRIPTION
     "An entry in the mscLpEth100StateTable."
   INDEX {
      mscLpIndex,
      mscLpEth100Index }
::= { mscLpEth100StateTable 1 }

MscLpEth100StateEntry ::= SEQUENCE {
   mscLpEth100AdminState
      INTEGER,
   mscLpEth100OperationalState
      INTEGER,
   mscLpEth100UsageState
      INTEGER }

mscLpEth100AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscLpEth100StateEntry 1 }

mscLpEth100OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscLpEth100StateEntry 2 }

mscLpEth100UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscLpEth100StateEntry 3 }

mscLpEth100OperStatusTable OBJECT-TYPE
   SYNTAX     SEQUENCE OF MscLpEth100OperStatusEntry
   ACCESS     not-accessible
   STATUS     mandatory
   DESCRIPTION
     "This group includes the Operational Status attribute. This attribute 
      defines the current operational state of this component."
::= { mscLpEth100 16 }

mscLpEth100OperStatusEntry OBJECT-TYPE
   SYNTAX     MscLpEth100OperStatusEntry
   ACCESS     not-accessible
   STATUS     mandatory
   DESCRIPTION
     "An entry in the mscLpEth100OperStatusTable."
   INDEX {
      mscLpIndex,
      mscLpEth100Index }
::= { mscLpEth100OperStatusTable 1 }

MscLpEth100OperStatusEntry ::= SEQUENCE {
   mscLpEth100SnmpOperStatus
      INTEGER }

mscLpEth100SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscLpEth100OperStatusEntry 1 }

mscLpEth100OperTable OBJECT-TYPE
   SYNTAX     SEQUENCE OF MscLpEth100OperEntry
   ACCESS     not-accessible
   STATUS     mandatory
   DESCRIPTION
     "This group contains the Port operational attributes of the Eth100BaseT 
      component."
::= { mscLpEth100 17 }

mscLpEth100OperEntry OBJECT-TYPE
   SYNTAX     MscLpEth100OperEntry
   ACCESS     not-accessible
   STATUS     mandatory
   DESCRIPTION
     "An entry in the mscLpEth100OperTable."
   INDEX {
      mscLpIndex,
      mscLpEth100Index }
::= { mscLpEth100OperTable 1 }

MscLpEth100OperEntry ::= SEQUENCE {
   mscLpEth100MacAddress
      MacAddress,
   mscLpEth100AutoNegStatus
      INTEGER,
   mscLpEth100ActualLineSpeed
      Unsigned32,
   mscLpEth100ActualDuplexMode
      INTEGER }

mscLpEth100MacAddress OBJECT-TYPE
   SYNTAX     MacAddress (SIZE (6))
   ACCESS     read-only
   STATUS     mandatory
   DESCRIPTION
     "This attribute indicates the medium access controller (MAC) address. 
      The MAC address is displayed in canonical format."
::= { mscLpEth100OperEntry 1 }

mscLpEth100AutoNegStatus OBJECT-TYPE
   SYNTAX     INTEGER  {
                 succeeded(1),
                 failed(2),
                 disabled(3) }
   ACCESS     read-only
   STATUS     mandatory
   DESCRIPTION
     "This attribute displays the status of the auto negotiation at the Phy level."
::= { mscLpEth100OperEntry 4 }

mscLpEth100ActualLineSpeed OBJECT-TYPE
   SYNTAX     Unsigned32 (10 | 100)
   ACCESS     read-only
   STATUS     mandatory
   DESCRIPTION
     "This attribute indicates the line speed of the Eth100BaseT port."
::= { mscLpEth100OperEntry 5 }

mscLpEth100ActualDuplexMode OBJECT-TYPE
   SYNTAX     INTEGER  {
                 half(1),
                 full(2) }
   ACCESS     read-only
   STATUS     mandatory
   DESCRIPTION
     "This attribute indicates whether the hardware is in half duplex or full 
      duplex mode."
::= { mscLpEth100OperEntry 6 }

mscLpEth100Eth100StatsTable OBJECT-TYPE
   SYNTAX     SEQUENCE OF MscLpEth100Eth100StatsEntry
   ACCESS     not-accessible
   STATUS     mandatory
   DESCRIPTION
     "This group contains the statistical attributes for the Eth100BaseT 
      component."
::= { mscLpEth100 18 }

mscLpEth100Eth100StatsEntry OBJECT-TYPE
   SYNTAX     MscLpEth100Eth100StatsEntry
   ACCESS     not-accessible
   STATUS     mandatory
   DESCRIPTION
     "An entry in the mscLpEth100Eth100StatsTable."
   INDEX {
      mscLpIndex,
      mscLpEth100Index }
::= { mscLpEth100Eth100StatsTable 1 }

MscLpEth100Eth100StatsEntry ::= SEQUENCE {
   mscLpEth100FramesTransmittedOk
      Counter32,
   mscLpEth100FramesReceivedOk
      Counter32,
   mscLpEth100OctetsTransmittedOk
      Counter32,
   mscLpEth100OctetsReceivedOk
      Counter32,
   mscLpEth100UndersizeFrames
      Counter32,
   mscLpEth100ReceivedOctetsIntoRouterBr
      Counter32,
   mscLpEth100ReceivedFramesIntoRouterBr
      Counter32 }

mscLpEth100FramesTransmittedOk OBJECT-TYPE
   SYNTAX     Counter32 
   ACCESS     read-only
   STATUS     mandatory
   DESCRIPTION
     "This attribute counts the number of frames which were transmitted 
      without errors. This counter wraps to zero after it reaches its maximum 
      value."
::= { mscLpEth100Eth100StatsEntry 1 }

mscLpEth100FramesReceivedOk OBJECT-TYPE
   SYNTAX     Counter32 
   ACCESS     read-only
   STATUS     mandatory
   DESCRIPTION
     "This attribute counts the number of frames which were received without 
      errors. This counter wraps to zero after it reaches its maximum value."
::= { mscLpEth100Eth100StatsEntry 2 }

mscLpEth100OctetsTransmittedOk OBJECT-TYPE
   SYNTAX     Counter32 
   ACCESS     read-only
   STATUS     mandatory
   DESCRIPTION
     "This attribute counts the number of octets which were transmitted 
      without errors. This counter wraps to zero after it reaches its maximum 
      value."
::= { mscLpEth100Eth100StatsEntry 3 }

mscLpEth100OctetsReceivedOk OBJECT-TYPE
   SYNTAX     Counter32 
   ACCESS     read-only
   STATUS     mandatory
   DESCRIPTION
     "This attribute counts the number of octets which were received without 
      errors. This counter wraps to zero after it reaches its maximum value."
::= { mscLpEth100Eth100StatsEntry 4 }

mscLpEth100UndersizeFrames OBJECT-TYPE
   SYNTAX     Counter32 
   ACCESS     read-only
   STATUS     mandatory
   DESCRIPTION
     "This attribute counts the number of frames that were received but were 
      less than the minimum size (64 bytes). This counter wraps to zero after 
      it reaches its maximum value."
::= { mscLpEth100Eth100StatsEntry 5 }

mscLpEth100ReceivedOctetsIntoRouterBr OBJECT-TYPE
   SYNTAX     Counter32 
   ACCESS     read-only
   STATUS     mandatory
   DESCRIPTION
     "This attribute counts the number of octets that were not hardware 
      switched but were passed the Router or Bridge software. This counter 
      wraps to zero after it reaches its maximum value."
::= { mscLpEth100Eth100StatsEntry 6 }

mscLpEth100ReceivedFramesIntoRouterBr OBJECT-TYPE
   SYNTAX     Counter32 
   ACCESS     read-only
   STATUS     mandatory
   DESCRIPTION
     "This attribute counts the number of frames which were not hardware 
      switched but were passed to the Router or Bridge software. This counter 
      wraps to zero after it reaches its maximum value."
::= { mscLpEth100Eth100StatsEntry 7 }

mscLpEth100StatsTable OBJECT-TYPE
   SYNTAX     SEQUENCE OF MscLpEth100StatsEntry
   ACCESS     not-accessible
   STATUS     mandatory
   DESCRIPTION
     "This group contains statistical attributes for the		 Ethernet component."
::= { mscLpEth100 19 }

mscLpEth100StatsEntry OBJECT-TYPE
   SYNTAX     MscLpEth100StatsEntry
   ACCESS     not-accessible
   STATUS     mandatory
   DESCRIPTION
     "An entry in the mscLpEth100StatsTable."
   INDEX {
      mscLpIndex,
      mscLpEth100Index }
::= { mscLpEth100StatsTable 1 }

MscLpEth100StatsEntry ::= SEQUENCE {
   mscLpEth100AlignmentErrors
      Counter32,
   mscLpEth100FcsErrors
      Counter32,
   mscLpEth100SingleCollisionFrames
      Counter32,
   mscLpEth100MultipleCollisionFrames
      Counter32,
   mscLpEth100SqeTestErrors
      Counter32,
   mscLpEth100DeferredTransmissions
      Counter32,
   mscLpEth100LateCollisions
      Counter32,
   mscLpEth100ExcessiveCollisions
      Counter32,
   mscLpEth100MacTransmitErrors
      Counter32,
   mscLpEth100CarrierSenseErrors
      Counter32,
   mscLpEth100FrameTooLongs
      Counter32,
   mscLpEth100MacReceiveErrors
      Counter32 }

mscLpEth100AlignmentErrors OBJECT-TYPE
   SYNTAX     Counter32 
   ACCESS     read-only
   STATUS     mandatory
   DESCRIPTION
     "The alignmentErrors counter indicates the number of frames received 
      which were not an integral number of octets in length. Frames will be 
      checked for alignmentErrors before they are checked for Frame Check 
      Sequence (FCS) errors. If there is an alignment error, the error will only 
      be counted here and not in fcsErrors. This counter wraps around after it 
      exceeds its maximum value."
::= { mscLpEth100StatsEntry 2 }

mscLpEth100FcsErrors OBJECT-TYPE
   SYNTAX     Counter32 
   ACCESS     read-only
   STATUS     mandatory
   DESCRIPTION
     "The fcsErrors, Frame Check Sequence (FCS) error, counter indicates the 
      number of frames received which were an integral number of octets in 
      length and did not pass the FCS check. This counter wraps around after 
      it exceeds its maximum value."
::= { mscLpEth100StatsEntry 3 }

mscLpEth100SingleCollisionFrames OBJECT-TYPE
   SYNTAX     Counter32 
   ACCESS     read-only
   STATUS     mandatory
   DESCRIPTION
     "The singleCollisionFrames counter indicates the number of frames 
      successfully transmitted which experienced exactly one collision. This 
      counter wraps around after it exceeds its maximum value."
::= { mscLpEth100StatsEntry 4 }

mscLpEth100MultipleCollisionFrames OBJECT-TYPE
   SYNTAX     Counter32 
   ACCESS     read-only
   STATUS     mandatory
   DESCRIPTION
     "The multipleCollisionFrames counter indicates the number of frames 
      successfully transmitted which experienced more than one collision. 
      This counter wraps around after it exceeds its maximum value."
::= { mscLpEth100StatsEntry 5 }

mscLpEth100SqeTestErrors OBJECT-TYPE
   SYNTAX     Counter32 
   ACCESS     read-only
   STATUS     mandatory
   DESCRIPTION
     "The sqeTestErrors, Signal Quality Error (SQE) Test errors, counter 
      indicates the number of times the 'SQE Test Error' message has been 
      generated for the station. This counter wraps around after it exceeds its 
      maximum value."
::= { mscLpEth100StatsEntry 6 }

mscLpEth100DeferredTransmissions OBJECT-TYPE
   SYNTAX     Counter32 
   ACCESS     read-only
   STATUS     mandatory
   DESCRIPTION
     "The deferredTransmissions counter indicates the number of frames 
      which experienced a transmission delay because the medium was busy. 
      This counter wraps around after it exceeds its maximum value."
::= { mscLpEth100StatsEntry 7 }

mscLpEth100LateCollisions OBJECT-TYPE
   SYNTAX     Counter32 
   ACCESS     read-only
   STATUS     mandatory
   DESCRIPTION
     "The lateCollisions counter indicates the number of times a collision was 
      detected later than 512 bit-times into the transmission of a packet. This 
      counter wraps around after it exceeds its maximum value."
::= { mscLpEth100StatsEntry 8 }

mscLpEth100ExcessiveCollisions OBJECT-TYPE
   SYNTAX     Counter32 
   ACCESS     read-only
   STATUS     mandatory
   DESCRIPTION
     "The excessiveCollisions counter indicates the number of frames which 
      failed to get transmitted due to excessive collisions. This counter wraps 
      around after it exceeds its maximum value."
::= { mscLpEth100StatsEntry 9 }

mscLpEth100MacTransmitErrors OBJECT-TYPE
   SYNTAX     Counter32 
   ACCESS     read-only
   STATUS     mandatory
   DESCRIPTION
     "The Medium Access Controller (MAC) transmit error counter indicates 
      the number of times that a transmission failed due to internal MAC 
      transmit errors. This counter wraps around after it exceeds its maximum 
      value."
::= { mscLpEth100StatsEntry 10 }

mscLpEth100CarrierSenseErrors OBJECT-TYPE
   SYNTAX     Counter32 
   ACCESS     read-only
   STATUS     mandatory
   DESCRIPTION
     "The carrier sense error counter indicates the number of times that the 
      carrier sense condition was lost or never asserted when attempting to 
      transmit a frame. This counter wraps around after it exceeds its 
      maximum value."
::= { mscLpEth100StatsEntry 11 }

mscLpEth100FrameTooLongs OBJECT-TYPE
   SYNTAX     Counter32 
   ACCESS     read-only
   STATUS     mandatory
   DESCRIPTION
     "The frame too long counter indicates the number of frames received 
      which exceeded the maximum frame size. This counter wraps around 
      after it exceeds its maximum value."
::= { mscLpEth100StatsEntry 12 }

mscLpEth100MacReceiveErrors OBJECT-TYPE
   SYNTAX     Counter32 
   ACCESS     read-only
   STATUS     mandatory
   DESCRIPTION
     "The Medium Access Controller (MAC) receive error counter indicates 
      the number of times a receive failed due to internal MAC receive errors. 
      This counter wraps around after it exceeds its maximum value."
::= { mscLpEth100StatsEntry 13 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

mscLpEth100Lt OBJECT IDENTIFIER ::= { mscLpEth100 2 }



mscLpEth100LtRowStatusTable OBJECT-TYPE
   SYNTAX     SEQUENCE OF MscLpEth100LtRowStatusEntry
   ACCESS     not-accessible
   STATUS     mandatory
   DESCRIPTION
     "This entry controls the addition and deletion of 
      mscLpEth100Lt components."
::= { mscLpEth100Lt 1 }

mscLpEth100LtRowStatusEntry OBJECT-TYPE
   SYNTAX     MscLpEth100LtRowStatusEntry
   ACCESS     not-accessible
   STATUS     mandatory
   DESCRIPTION
     "A single entry in the table represents a single 
      mscLpEth100Lt component."
   INDEX {
      mscLpIndex,
      mscLpEth100Index,
      mscLpEth100LtIndex }
::= { mscLpEth100LtRowStatusTable 1 }

MscLpEth100LtRowStatusEntry ::= SEQUENCE {
   mscLpEth100LtRowStatus
      RowStatus,
   mscLpEth100LtComponentName
      DisplayString,
   mscLpEth100LtStorageType
      StorageType,
   mscLpEth100LtIndex
      NonReplicated }

mscLpEth100LtRowStatus OBJECT-TYPE
   SYNTAX     RowStatus 
   ACCESS     read-only
