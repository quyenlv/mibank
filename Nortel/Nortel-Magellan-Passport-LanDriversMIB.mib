Nortel-Magellan-Passport-LanDriversMIB
DEFINITIONS ::= BEGIN



IMPORTS

      OBJECT-TYPE
   FROM RFC-1212

      components,
      passportMIBs
   FROM Nortel-Magellan-Passport-UsefulDefinitionsMIB

      FddiMACLongAddressType,
      Counter32,
      DisplayString,
      FddiTimeNano,
      StorageType,
      RowStatus,
      PassportCounter64,
      InterfaceIndex,
      Gauge32,
      Integer32,
      MacAddress,
      FddiTimeMilli,
      Unsigned32
   FROM Nortel-Magellan-Passport-StandardTextualConventionsMIB

      AsciiString,
      NonReplicated,
      EnterpriseDateAndTime,
      Link
   FROM Nortel-Magellan-Passport-TextualConventionsMIB

      lpIndex,
      lp
   FROM Nortel-Magellan-Passport-LogicalProcessorMIB;




-- LAST-UPDATED   "9903220000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     LanDrivers Enterprise MIB."

lanDriversMIB OBJECT IDENTIFIER ::= { passportMIBs 30 }










-- Lp/n Ethernet/n
-- This component defines an instance of an Ethernet station attached to a 
-- bus. One instance of this component will be created for each hardware 
-- port. Each station will be provisioned prior to operating on the bus.

lpEnet OBJECT IDENTIFIER ::= { lp 3 }



lpEnetRowStatusTable OBJECT-TYPE
   SYNTAX     SEQUENCE OF LpEnetRowStatusEntry
   ACCESS     not-accessible
   STATUS     mandatory
   DESCRIPTION
     "This entry controls the addition and deletion of 
      lpEnet components."
::= { lpEnet 1 }

lpEnetRowStatusEntry OBJECT-TYPE
   SYNTAX     LpEnetRowStatusEntry
   ACCESS     not-accessible
   STATUS     mandatory
   DESCRIPTION
     "A single entry in the table represents a single 
      lpEnet component."
   INDEX {
      lpIndex,
      lpEnetIndex }
::= { lpEnetRowStatusTable 1 }

LpEnetRowStatusEntry ::= SEQUENCE {
   lpEnetRowStatus
      RowStatus,
   lpEnetComponentName
      DisplayString,
   lpEnetStorageType
      StorageType,
   lpEnetIndex
      Integer32 }

lpEnetRowStatus OBJECT-TYPE
   SYNTAX     RowStatus 
   ACCESS     read-write
   STATUS     mandatory
   DESCRIPTION
     "This variable is used as the basis for SNMP naming of
      lpEnet components.
      These components can be added and deleted."
::= { lpEnetRowStatusEntry 1 }

lpEnetComponentName OBJECT-TYPE
   SYNTAX     DisplayString 
   ACCESS     read-only
   STATUS     mandatory
   DESCRIPTION
     "This variable provides the component's string name for
      use with the ASCII Console Interface"
::= { lpEnetRowStatusEntry 2 }

lpEnetStorageType OBJECT-TYPE
   SYNTAX     StorageType 
   ACCESS     read-only
   STATUS     mandatory
   DESCRIPTION
     "This variable represents the storage type value for the
      lpEnet tables."
::= { lpEnetRowStatusEntry 4 }

lpEnetIndex OBJECT-TYPE
   SYNTAX     Integer32 (0..5)
   ACCESS     not-accessible
   STATUS     mandatory
   DESCRIPTION
     "This variable represents the index for the lpEnet tables."
::= { lpEnetRowStatusEntry 10 }

lpEnetCidDataTable OBJECT-TYPE
   SYNTAX     SEQUENCE OF LpEnetCidDataEntry
   ACCESS     not-accessible
   STATUS     mandatory
   DESCRIPTION
     "This group contains the attribute for a component's Customer 
      Identifier (CID). Refer to the attribute description for a detailed 
      explanation of CIDs."
::= { lpEnet 10 }

lpEnetCidDataEntry OBJECT-TYPE
   SYNTAX     LpEnetCidDataEntry
   ACCESS     not-accessible
   STATUS     mandatory
   DESCRIPTION
     "An entry in the lpEnetCidDataTable."
   INDEX {
      lpIndex,
      lpEnetIndex }
::= { lpEnetCidDataTable 1 }

LpEnetCidDataEntry ::= SEQUENCE {
   lpEnetCustomerIdentifier
      Unsigned32 }

lpEnetCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpEnetCidDataEntry 1 }

lpEnetIfEntryTable OBJECT-TYPE
   SYNTAX     SEQUENCE OF LpEnetIfEntryEntry
   ACCESS     not-accessible
   STATUS     mandatory
   DESCRIPTION
     "This group contains the provisionable attributes for the ifEntry."
::= { lpEnet 11 }

lpEnetIfEntryEntry OBJECT-TYPE
   SYNTAX     LpEnetIfEntryEntry
   ACCESS     not-accessible
   STATUS     mandatory
   DESCRIPTION
     "An entry in the lpEnetIfEntryTable."
   INDEX {
      lpIndex,
      lpEnetIndex }
::= { lpEnetIfEntryTable 1 }

LpEnetIfEntryEntry ::= SEQUENCE {
   lpEnetIfAdminStatus
      INTEGER,
   lpEnetIfIndex
      InterfaceIndex }

lpEnetIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpEnetIfEntryEntry 1 }

lpEnetIfIndex OBJECT-TYPE
   SYNTAX     InterfaceIndex (1..65535)
   ACCESS     read-only
   STATUS     mandatory
   DESCRIPTION
     "This is the index for the IfEntry. Its value is automatically initialized 
      during the provisioning process."
::= { lpEnetIfEntryEntry 2 }

lpEnetProvTable OBJECT-TYPE
   SYNTAX     SEQUENCE OF LpEnetProvEntry
   ACCESS     not-accessible
   STATUS     mandatory
   DESCRIPTION
     "This group contains provisioned attributes for the 		Ethernet component."
::= { lpEnet 12 }

lpEnetProvEntry OBJECT-TYPE
   SYNTAX     LpEnetProvEntry
   ACCESS     not-accessible
   STATUS     mandatory
   DESCRIPTION
     "An entry in the lpEnetProvTable."
   INDEX {
      lpIndex,
      lpEnetIndex }
::= { lpEnetProvTable 1 }

LpEnetProvEntry ::= SEQUENCE {
   lpEnetHeartbeatPacket
      INTEGER,
   lpEnetApplicationFramerName
      Link }

lpEnetHeartbeatPacket OBJECT-TYPE
   SYNTAX     INTEGER  {
                 enabled(1),
                 disabled(2) }
   ACCESS     read-write
   STATUS     mandatory
   DESCRIPTION
     "The heartbeat packet feature is used to select whether or not the station 
      will generate a heartbeat packet. If enabled, the station will generate one 
      heartbeat packet every second. If disabled, the station will not generate 
      any heartbeat packets."
   DEFVAL     { enabled }
::= { lpEnetProvEntry 1 }

lpEnetApplicationFramerName OBJECT-TYPE
   SYNTAX     Link 
   ACCESS     read-write
   STATUS     mandatory
   DESCRIPTION
     "This attribute contains the component name of a Framer which is 
      associated with the Ethernet component. This link is used by the 
      component administration system (CAS) to identify which card the 
      application component (associated with the Framer component) is to be 
      created."
::= { lpEnetProvEntry 2 }

lpEnetAdminInfoTable OBJECT-TYPE
   SYNTAX     SEQUENCE OF LpEnetAdminInfoEntry
   ACCESS     not-accessible
   STATUS     mandatory
   DESCRIPTION
     "This group contains the attributes pertaining to the vendor of the 
      equipment."
::= { lpEnet 13 }

lpEnetAdminInfoEntry OBJECT-TYPE
   SYNTAX     LpEnetAdminInfoEntry
   ACCESS     not-accessible
   STATUS     mandatory
   DESCRIPTION
     "An entry in the lpEnetAdminInfoTable."
   INDEX {
      lpIndex,
      lpEnetIndex }
::= { lpEnetAdminInfoTable 1 }

LpEnetAdminInfoEntry ::= SEQUENCE {
   lpEnetVendor
      AsciiString,
   lpEnetCommentText
      AsciiString }

lpEnetVendor OBJECT-TYPE
   SYNTAX     AsciiString (SIZE (0..20))
   ACCESS     read-write
   STATUS     mandatory
   DESCRIPTION
     "This is the name of the vendor supplying the facility."
::= { lpEnetAdminInfoEntry 1 }

lpEnetCommentText OBJECT-TYPE
   SYNTAX     AsciiString (SIZE (0..60))
   ACCESS     read-write
   STATUS     mandatory
   DESCRIPTION
     "Any miscellaneous text about the facility."
::= { lpEnetAdminInfoEntry 2 }

lpEnetStateTable OBJECT-TYPE
   SYNTAX     SEQUENCE OF LpEnetStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpEnet 15 }

lpEnetStateEntry OBJECT-TYPE
   SYNTAX     LpEnetStateEntry
   ACCESS     not-accessible
   STATUS     mandatory
   DESCRIPTION
     "An entry in the lpEnetStateTable."
   INDEX {
      lpIndex,
      lpEnetIndex }
::= { lpEnetStateTable 1 }

LpEnetStateEntry ::= SEQUENCE {
   lpEnetAdminState
      INTEGER,
   lpEnetOperationalState
      INTEGER,
   lpEnetUsageState
      INTEGER }

lpEnetAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpEnetStateEntry 1 }

lpEnetOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpEnetStateEntry 2 }

lpEnetUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpEnetStateEntry 3 }

lpEnetOperStatusTable OBJECT-TYPE
   SYNTAX     SEQUENCE OF LpEnetOperStatusEntry
   ACCESS     not-accessible
   STATUS     mandatory
   DESCRIPTION
     "This group includes the Operational Status attribute. This attribute 
      defines the current operational state of this component."
::= { lpEnet 16 }

lpEnetOperStatusEntry OBJECT-TYPE
   SYNTAX     LpEnetOperStatusEntry
   ACCESS     not-accessible
   STATUS     mandatory
   DESCRIPTION
     "An entry in the lpEnetOperStatusTable."
   INDEX {
      lpIndex,
      lpEnetIndex }
::= { lpEnetOperStatusTable 1 }

LpEnetOperStatusEntry ::= SEQUENCE {
   lpEnetSnmpOperStatus
      INTEGER }

lpEnetSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpEnetOperStatusEntry 1 }

lpEnetOperTable OBJECT-TYPE
   SYNTAX     SEQUENCE OF LpEnetOperEntry
   ACCESS     not-accessible
   STATUS     mandatory
   DESCRIPTION
     "This group contains the operational attributes of the Ethernet 
      component."
::= { lpEnet 17 }

lpEnetOperEntry OBJECT-TYPE
   SYNTAX     LpEnetOperEntry
   ACCESS     not-accessible
   STATUS     mandatory
   DESCRIPTION
     "An entry in the lpEnetOperTable."
   INDEX {
      lpIndex,
      lpEnetIndex }
::= { lpEnetOperTable 1 }

LpEnetOperEntry ::= SEQUENCE {
   lpEnetMacAddress
      MacAddress }

lpEnetMacAddress OBJECT-TYPE
   SYNTAX     MacAddress (SIZE (6))
   ACCESS     read-only
   STATUS     mandatory
   DESCRIPTION
     "The medium access controller (MAC) address is an address that is only 
      recognized by one station on the network The value of this attribute will 
      be assigned by the system. MAC address is displayed in canonical 
      format."
::= { lpEnetOperEntry 1 }

lpEnetStatsTable OBJECT-TYPE
   SYNTAX     SEQUENCE OF LpEnetStatsEntry
   ACCESS     not-accessible
   STATUS     mandatory
   DESCRIPTION
     "This group contains statistical attributes for the		 Ethernet component."
::= { lpEnet 18 }

lpEnetStatsEntry OBJECT-TYPE
   SYNTAX     LpEnetStatsEntry
   ACCESS     not-accessible
   STATUS     mandatory
   DESCRIPTION
     "An entry in the lpEnetStatsTable."
   INDEX {
      lpIndex,
      lpEnetIndex }
::= { lpEnetStatsTable 1 }

LpEnetStatsEntry ::= SEQUENCE {
   lpEnetAlignmentErrors
      Counter32,
   lpEnetFcsErrors
      Counter32,
   lpEnetSingleCollisionFrames
      Counter32,
   lpEnetMultipleCollisionFrames
      Counter32,
   lpEnetSqeTestErrors
      Counter32,
   lpEnetDeferredTransmissions
      Counter32,
   lpEnetLateCollisions
      Counter32,
   lpEnetExcessiveCollisions
      Counter32,
   lpEnetMacTransmitErrors
      Counter32,
   lpEnetCarrierSenseErrors
      Counter32,
   lpEnetFrameTooLongs
      Counter32,
   lpEnetMacReceiveErrors
      Counter32 }

lpEnetAlignmentErrors OBJECT-TYPE
   SYNTAX     Counter32 
   ACCESS     read-only
   STATUS     mandatory
   DESCRIPTION
     "The alignmentErrors counter indicates the number of frames received 
      which were not an integral number of octets in length. Frames will be 
      checked for alignmentErrors before they are checked for Frame Check 
      Sequence (FCS) errors. If there is an alignment error, the error will only 
      be counted here and not in fcsErrors. This counter will wrap around 
      after it reaches its maximum value."
::= { lpEnetStatsEntry 2 }

lpEnetFcsErrors OBJECT-TYPE
   SYNTAX     Counter32 
   ACCESS     read-only
   STATUS     mandatory
   DESCRIPTION
     "The fcsErrors, Frame Check Sequence (FCS) error, counter indicates the 
      number of frames received which were an integral number of octets in 
      length and did not pass the FCS check. This counter will wrap around 
      after it reaches its maximum value."
::= { lpEnetStatsEntry 3 }

lpEnetSingleCollisionFrames OBJECT-TYPE
   SYNTAX     Counter32 
   ACCESS     read-only
   STATUS     mandatory
   DESCRIPTION
     "The singleCollisionFrames counter indicates the number of frames 
      successfully transmitted which experienced exactly one collision. This 
      counter will wrap around after it reaches its maximum value."
::= { lpEnetStatsEntry 4 }

lpEnetMultipleCollisionFrames OBJECT-TYPE
   SYNTAX     Counter32 
   ACCESS     read-only
   STATUS     mandatory
   DESCRIPTION
     "The multipleCollisionFrames counter indicates the number of frames 
      successfully transmitted which experienced more than one collision. 
      This counter will wrap around after it reaches its maximum value."
::= { lpEnetStatsEntry 5 }

lpEnetSqeTestErrors OBJECT-TYPE
   SYNTAX     Counter32 
   ACCESS     read-only
   STATUS     mandatory
   DESCRIPTION
     "The sqeTestErrors, Signal Quality Error (SQE) Test errors, counter 
      indicates the number of times the 'SQE Test Error' message has been 
      generated for the station. This counter will wrap around after it reaches 
      its maximum value."
::= { lpEnetStatsEntry 6 }

lpEnetDeferredTransmissions OBJECT-TYPE
   SYNTAX     Counter32 
   ACCESS     read-only
   STATUS     mandatory
   DESCRIPTION
     "The deferredTransmissions counter indicates the number of frames 
      which experienced a transmission delay because the medium was busy. 
      This counter will wrap around after it reaches its maximum value."
::= { lpEnetStatsEntry 7 }

lpEnetLateCollisions OBJECT-TYPE
   SYNTAX     Counter32 
   ACCESS     read-only
   STATUS     mandatory
   DESCRIPTION
     "The lateCollisions counter indicates the number of times a collision was 
      detected later than 512 bit-times into the transmission of a packet. This 
      counter will wrap around after it reaches its maximum value."
::= { lpEnetStatsEntry 8 }

lpEnetExcessiveCollisions OBJECT-TYPE
   SYNTAX     Counter32 
   ACCESS     read-only
   STATUS     mandatory
   DESCRIPTION
     "The excessiveCollisions counter indicates the number of frames which 
      failed to get transmitted due to excessive collisions. This counter will 
      wrap around after it reaches its maximum value."
::= { lpEnetStatsEntry 9 }

lpEnetMacTransmitErrors OBJECT-TYPE
   SYNTAX     Counter32 
   ACCESS     read-only
   STATUS     mandatory
   DESCRIPTION
     "The Medium Access Controller (MAC) transmit error counter indicates 
      the number of times that a transmission failed due to internal MAC 
      transmit errors. This counter will wrap around after it reaches its 
      maximum value."
::= { lpEnetStatsEntry 10 }

lpEnetCarrierSenseErrors OBJECT-TYPE
   SYNTAX     Counter32 
   ACCESS     read-only
   STATUS     mandatory
   DESCRIPTION
     "The carrier sense error counter indicates the number of times that the 
      carrier sense condition was lost or never asserted when attempting to 
      transmit a frame. This counter will wrap around after it reaches its 
      maximum value."
::= { lpEnetStatsEntry 11 }

lpEnetFrameTooLongs OBJECT-TYPE
   SYNTAX     Counter32 
   ACCESS     read-only
   STATUS     mandatory
   DESCRIPTION
     "The frame too long counter indicates the number of frames received 
      which exceeded the maximum frame size. This counter will wrap 
      around after it reaches its maximum value."
::= { lpEnetStatsEntry 12 }

lpEnetMacReceiveErrors OBJECT-TYPE
   SYNTAX     Counter32 
   ACCESS     read-only
   STATUS     mandatory
   DESCRIPTION
     "The Medium Access Controller (MAC) receive error counter indicates 
      the number of times a receive failed due to internal MAC receive errors. 
      This counter will wrap around after it reaches its maximum value."
::= { lpEnetStatsEntry 13 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

lpEnetLt OBJECT IDENTIFIER ::= { lpEnet 2 }



lpEnetLtRowStatusTable OBJECT-TYPE
   SYNTAX     SEQUENCE OF LpEnetLtRowStatusEntry
   ACCESS     not-accessible
   STATUS     mandatory
   DESCRIPTION
     "This entry controls the addition and deletion of 
      lpEnetLt components."
::= { lpEnetLt 1 }

lpEnetLtRowStatusEntry OBJECT-TYPE
   SYNTAX     LpEnetLtRowStatusEntry
   ACCESS     not-accessible
   STATUS     mandatory
   DESCRIPTION
     "A single entry in the table represents a single 
      lpEnetLt component."
   INDEX {
      lpIndex,
      lpEnetIndex,
      lpEnetLtIndex }
::= { lpEnetLtRowStatusTable 1 }

LpEnetLtRowStatusEntry ::= SEQUENCE {
   lpEnetLtRowStatus
      RowStatus,
   lpEnetLtComponentName
      DisplayString,
   lpEnetLtStorageType
      StorageType,
   lpEnetLtIndex
      NonReplicated }

lpEnetLtRowStatus OBJECT-TYPE
   SYNTAX     RowStatus 
   ACCESS     read-only
   STATUS     mandatory
   DESCRIPTION
     "This variable is used as the basis for SNMP naming of
      lpEnetLt components.
      These components cannot be added nor deleted."
::= { lpEnetLtRowStatusEntry 1 }

lpEnetLtComponentName OBJECT-TYPE
   SYNTAX     DisplayString 
   ACCESS     read-only
   STATUS     mandatory
   DESCRIPTION
     "This variable provides the component's string name for
      use with the ASCII Console Interface"
::= { lpEnetLtRowStatusEntry 2 }

lpEnetLtStorageType OBJECT-TYPE
   SYNTAX     StorageType 
   ACCESS     read-only
   STATUS     mandatory
   DESCRIPTION
     "This variable represents the storage type value for the
      lpEnetLt tables."
::= { lpEnetLtRowStatusEntry 4 }

lpEnetLtIndex OBJECT-TYPE
   SYNTAX     NonReplicated 
   ACCESS     not-accessible
   STATUS     mandatory
   DESCRIPTION
     "This variable represents the index for the lpEnetLt tables."
::= { lpEnetLtRowStatusEntry 10 }

lpEnetLtTopTable OBJECT-TYPE
   SYNTAX     SEQUENCE OF LpEnetLtTopEntry
   ACCESS     not-accessible
   STATUS     mandatory
   DESCRIPTION
     "This group contains the operational data for the LanTest component 
      and its subcomponents."
::= { lpEnetLt 20 }

lpEnetLtTopEntry OBJECT-TYPE
   SYNTAX     LpEnetLtTopEntry
   ACCESS     not-accessible
   STATUS     mandatory
   DESCRIPTION
     "An entry in the lpEnetLtTopTable."
   INDEX {
      lpIndex,
      lpEnetIndex,
      lpEnetLtIndex }
::= { lpEnetLtTopTable 1 }

LpEnetLtTopEntry ::= SEQUENCE {
   lpEnetLtTData
      AsciiString }

lpEnetLtTData OBJECT-TYPE
   SYNTAX     AsciiString (SIZE (0..255))
   ACCESS     read-write
   STATUS     mandatory
   DESCRIPTION
     "This attribute is used to display and set attributes."
::= { lpEnetLtTopEntry 1 }


-- This component compares frames received from the hardware and 
-- emulator during testing.

lpEnetLtFrmCmp OBJECT IDENTIFIER ::= { lpEnetLt 2 }



lpEnetLtFrmCmpRowStatusTable OBJECT-TYPE
   SYNTAX     SEQUENCE OF LpEnetLtFrmCmpRowStatusEntry
   ACCESS     not-accessible
   STATUS     mandatory
   DESCRIPTION
     "This entry controls the addition and deletion of 
      lpEnetLtFrmCmp components."
::= { lpEnetLtFrmCmp 1 }

lpEnetLtFrmCmpRowStatusEntry OBJECT-TYPE
   SYNTAX     LpEnetLtFrmCmpRowStatusEntry
   ACCESS     not-accessible
   STATUS     mandatory
   DESCRIPTION
     "A single entry in the table represents a single 
      lpEnetLtFrmCmp component."
   INDEX {
      lpIndex,
      lpEnetIndex,
      lpEnetLtIndex,
      lpEnetLtFrmCmpIndex }
::= { lpEnetLtFrmCmpRowStatusTable 1 }

LpEnetLtFrmCmpRowStatusEntry ::= SEQUENCE {
   lpEnetLtFrmCmpRowStatus
      RowStatus,
   lpEnetLtFrmCmpComponentName
      DisplayString,
   lpEnetLtFrmCmpStorageType
      StorageType,
   lpEnetLtFrmCmpIndex
      NonReplicated }

lpEnetLtFrmCmpRowStatus OBJECT-TYPE
   SYNTAX     RowStatus 
   ACCESS     read-only
   STATUS     mandatory
   DESCRIPTION
     "This variable is used as the basis for SNMP naming of
      lpEnetLtFrmCmp components.
      These components cannot be added nor deleted."
::= { lpEnetLtFrmCmpRowStatusEntry 1 }

lpEnetLtFrmCmpComponentName OBJECT-TYPE
   SYNTAX     DisplayString 
   ACCESS     read-only
   STATUS     mandatory
   DESCRIPTION
     "This variable provides the component's string name for
      use with the ASCII Console Interface"
::= { lpEnetLtFrmCmpRowStatusEntry 2 }

lpEnetLtFrmCmpStorageType OBJECT-TYPE
   SYNTAX     StorageType 
   ACCESS     read-only
   STATUS     mandatory
   DESCRIPTION
     "This variable represents the storage type value for the
      lpEnetLtFrmCmp tables."
::= { lpEnetLtFrmCmpRowStatusEntry 4 }

lpEnetLtFrmCmpIndex OBJECT-TYPE
   SYNTAX     NonReplicated 
   ACCESS     not-accessible
   STATUS     mandatory
   DESCRIPTION
     "This variable represents the index for the lpEnetLtFrmCmp tables."
::= { lpEnetLtFrmCmpRowStatusEntry 10 }

lpEnetLtFrmCmpTopTable OBJECT-TYPE
   SYNTAX     SEQUENCE OF LpEnetLtFrmCmpTopEntry
   ACCESS     not-accessible
   STATUS     mandatory
   DESCRIPTION
     "This group contains the operational data for the LanTest component 
      and its subcomponents."
::= { lpEnetLtFrmCmp 10 }

lpEnetLtFrmCmpTopEntry OBJECT-TYPE
   SYNTAX     LpEnetLtFrmCmpTopEntry
   ACCESS     not-accessible
   STATUS     mandatory
   DESCRIPTION
     "An entry in the lpEnetLtFrmCmpTopTable."
   INDEX {
      lpIndex,
      lpEnetIndex,
      lpEnetLtIndex,
      lpEnetLtFrmCmpIndex }
::= { lpEnetLtFrmCmpTopTable 1 }

LpEnetLtFrmCmpTopEntry ::= SEQUENCE {
   lpEnetLtFrmCmpTData
      AsciiString }

lpEnetLtFrmCmpTData OBJECT-TYPE
   SYNTAX     AsciiString (SIZE (0..255))
   ACCESS     read-write
   STATUS     mandatory
   DESCRIPTION
     "This attribute is used to display and set attributes."
::= { lpEnetLtFrmCmpTopEntry 1 }


-- This component receives its input from FrameBuild and places it 
-- upon the hardware which sends it to the appropriate emulator.

lpEnetLtFrmCpy OBJECT IDENTIFIER ::= { lpEnetLt 3 }



lpEnetLtFrmCpyRowStatusTable OBJECT-TYPE
   SYNTAX     SEQUENCE OF LpEnetLtFrmCpyRowStatusEntry
   ACCESS     not-accessible
   STATUS     mandatory
   DESCRIPTION
     "This entry controls the addition and deletion of 
      lpEnetLtFrmCpy components."
::= { lpEnetLtFrmCpy 1 }

lpEnetLtFrmCpyRowStatusEntry OBJECT-TYPE
   SYNTAX     LpEnetLtFrmCpyRowStatusEntry
   ACCESS     not-accessible
   STATUS     mandatory
   DESCRIPTION
     "A single entry in the table represents a single 
      lpEnetLtFrmCpy component."
   INDEX {
      lpIndex,
      lpEnetIndex,
      lpEnetLtIndex,
      lpEnetLtFrmCpyIndex }
::= { lpEnetLtFrmCpyRowStatusTable 1 }

LpEnetLtFrmCpyRowStatusEntry ::= SEQUENCE {
   lpEnetLtFrmCpyRowStatus
      RowStatus,
   lpEnetLtFrmCpyComponentName
      DisplayString,
   lpEnetLtFrmCpyStorageType
      StorageType,
   lpEnetLtFrmCpyIndex
      NonReplicated }

lpEnetLtFrmCpyRowStatus OBJECT-TYPE
   SYNTAX     RowStatus 
   ACCESS     read-only
   STATUS     mandatory
   DESCRIPTION
     "This variable is used as the basis for SNMP naming of
      lpEnetLtFrmCpy components.
      These components cannot be added nor deleted."
::= { lpEnetLtFrmCpyRowStatusEntry 1 }

lpEnetLtFrmCpyComponentName OBJECT-TYPE
   SYNTAX     DisplayString 
   ACCESS     read-only
   STATUS     mandatory
   DESCRIPTION
     "This variable provides the component's string name for
      use with the ASCII Console Interface"
::= { lpEnetLtFrmCpyRowStatusEntry 2 }

lpEnetLtFrmCpyStorageType OBJECT-TYPE
   SYNTAX     StorageType 
   ACCESS     read-only
   STATUS     mandatory
   DESCRIPTION
     "This variable represents the storage type value for the
      lpEnetLtFrmCpy tables."
::= { lpEnetLtFrmCpyRowStatusEntry 4 }

lpEnetLtFrmCpyIndex OBJECT-TYPE
   SYNTAX     NonReplicated 
   ACCESS     not-accessible
   STATUS     mandatory
   DESCRIPTION
     "This variable represents the index for the lpEnetLtFrmCpy tables."
::= { lpEnetLtFrmCpyRowStatusEntry 10 }

lpEnetLtFrmCpyTopTable OBJECT-TYPE
   SYNTAX     SEQUENCE OF LpEnetLtFrmCpyTopEntry
   ACCESS     not-accessible
   STATUS     mandatory
   DESCRIPTION
     "This group contains the operational data for the LanTest component 
      and its subcomponents."
::= { lpEnetLtFrmCpy 10 }

lpEnetLtFrmCpyTopEntry OBJECT-TYPE
   SYNTAX     LpEnetLtFrmCpyTopEntry
   ACCESS     not-accessible
   STATUS     mandatory
   DESCRIPTION
     "An entry in the lpEnetLtFrmCpyTopTable."
   INDEX {
      lpIndex,
      lpEnetIndex,
      lpEnetLtIndex,
      lpEnetLtFrmCpyIndex }
::= { lpEnetLtFrmCpyTopTable 1 }

LpEnetLtFrmCpyTopEntry ::= SEQUENCE {
   lpEnetLtFrmCpyTData
      AsciiString }

lpEnetLtFrmCpyTData OBJECT-TYPE
   SYNTAX     AsciiString (SIZE (0..255))
   ACCESS     read-write
   STATUS     mandatory
   DESCRIPTION
     "This attribute is used to display and set attributes."
::= { lpEnetLtFrmCpyTopEntry 1 }


-- This component controls the emulator and hardware to ensure 
-- frames output from each will match in FrameCompare.

lpEnetLtPrtCfg OBJECT IDENTIFIER ::= { lpEnetLt 4 }



lpEnetLtPrtCfgRowStatusTable OBJECT-TYPE
   SYNTAX     SEQUENCE OF LpEnetLtPrtCfgRowStatusEntry
   ACCESS     not-accessible
   STATUS     mandatory
   DESCRIPTION
     "This entry controls the addition and deletion of 
      lpEnetLtPrtCfg components."
::= { lpEnetLtPrtCfg 1 }

lpEnetLtPrtCfgRowStatusEntry OBJECT-TYPE
   SYNTAX     LpEnetLtPrtCfgRowStatusEntry
   ACCESS     not-accessible
   STATUS     mandatory
   DESCRIPTION
     "A single entry in the table represents a single 
      lpEnetLtPrtCfg component."
   INDEX {
      lpIndex,
      lpEnetIndex,
      lpEnetLtIndex,
      lpEnetLtPrtCfgIndex }
::= { lpEnetLtPrtCfgRowStatusTable 1 }

LpEnetLtPrtCfgRowStatusEntry ::= SEQUENCE {
   lpEnetLtPrtCfgRowStatus
      RowStatus,
   lpEnetLtPrtCfgComponentName
      DisplayString,
   lpEnetLtPrtCfgStorageType
      StorageType,
   lpEnetLtPrtCfgIndex
      NonReplicated }

lpEnetLtPrtCfgRowStatus OBJECT-TYPE
   SYNTAX     RowStatus 
   ACCESS     read-only
   STATUS     mandatory
   DESCRIPTION
     "This variable is used as the basis for SNMP naming of
      lpEnetLtPrtCfg components.
      These components cannot be added nor deleted."
::= { lpEnetLtPrtCfgRowStatusEntry 1 }

lpEnetLtPrtCfgComponentName OBJECT-TYPE
   SYNTAX     DisplayString 
   ACCESS     read-only
   STATUS     mandatory
   DESCRIPTION
     "This variable provides the component's string name for
      use with the ASCII Console Interface"
::= { lpEnetLtPrtCfgRowStatusEntry 2 }

lpEnetLtPrtCfgStorageType OBJECT-TYPE
   SYNTAX     StorageType 
   ACCESS     read-only
   STATUS     mandatory
   DESCRIPTION
     "This variable represents the storage type value for the
      lpEnetLtPrtCfg tables."
::= { lpEnetLtPrtCfgRowStatusEntry 4 }

lpEnetLtPrtCfgIndex OBJECT-TYPE
   SYNTAX     NonReplicated 
   ACCESS     not-accessible
   STATUS     mandatory
   DESCRIPTION
     "This variable represents the index for the lpEnetLtPrtCfg tables."
::= { lpEnetLtPrtCfgRowStatusEntry 10 }

lpEnetLtPrtCfgTopTable OBJECT-TYPE
   SYNTAX     SEQUENCE OF LpEnetLtPrtCfgTopEntry
   ACCESS     not-accessible
   STATUS     mandatory
   DESCRIPTION
     "This group contains the operational data for the LanTest component 
      and its subcomponents."
::= { lpEnetLtPrtCfg 10 }

lpEnetLtPrtCfgTopEntry OBJECT-TYPE
   SYNTAX     LpEnetLtPrtCfgTopEntry
   ACCESS     not-accessible
   STATUS     mandatory
   DESCRIPTION
     "An entry in the lpEnetLtPrtCfgTopTable."
   INDEX {
      lpIndex,
      lpEnetIndex,
      lpEnetLtIndex,
      lpEnetLtPrtCfgIndex }
::= { lpEnetLtPrtCfgTopTable 1 }

LpEnetLtPrtCfgTopEntry ::= SEQUENCE {
   lpEnetLtPrtCfgTData
      AsciiString }

lpEnetLtPrtCfgTData OBJECT-TYPE
   SYNTAX     AsciiString (SIZE (0..255))
   ACCESS     read-write
   STATUS     mandatory
   DESCRIPTION
     "This attribute is used to display and set attributes."
::= { lpEnetLtPrtCfgTopEntry 1 }


-- LanTest Framebuild
-- This component controls the building of all frames built and sent by 
-- the LanTest component. Each component under FrameBuild builds 
-- a portion of a packet or frame.

lpEnetLtFb OBJECT IDENTIFIER ::= { lpEnetLt 5 }



lpEnetLtFbRowStatusTable OBJECT-TYPE
   SYNTAX     SEQUENCE OF LpEnetLtFbRowStatusEntry
   ACCESS     not-accessible
   STATUS     mandatory
   DESCRIPTION
     "This entry controls the addition and deletion of 
      lpEnetLtFb components."
::= { lpEnetLtFb 1 }

lpEnetLtFbRowStatusEntry OBJECT-TYPE
   SYNTAX     LpEnetLtFbRowStatusEntry
   ACCESS     not-accessible
   STATUS     mandatory
   DESCRIPTION
     "A single entry in the table represents a single 
      lpEnetLtFb component."
   INDEX {
      lpIndex,
      lpEnetIndex,
      lpEnetLtIndex,
      lpEnetLtFbIndex }
::= { lpEnetLtFbRowStatusTable 1 }

LpEnetLtFbRowStatusEntry ::= SEQUENCE {
   lpEnetLtFbRowStatus
      RowStatus,
   lpEnetLtFbComponentName
      DisplayString,
   lpEnetLtFbStorageType
      StorageType,
   lpEnetLtFbIndex
      NonReplicated }

lpEnetLtFbRowStatus OBJECT-TYPE
   SYNTAX     RowStatus 
   ACCESS     read-only
   STATUS     mandatory
   DESCRIPTION
     "This variable is used as the basis for SNMP naming of
      lpEnetLtFb components.
      These components cannot be added nor deleted."
::= { lpEnetLtFbRowStatusEntry 1 }

lpEnetLtFbComponentName OBJECT-TYPE
   SYNTAX     DisplayString 
   ACCESS     read-only
   STATUS     mandatory
   DESCRIPTION
     "This variable provides the component's string name for
      use with the ASCII Console Interface"
::= { lpEnetLtFbRowStatusEntry 2 }

lpEnetLtFbStorageType OBJECT-TYPE
   SYNTAX     StorageType 
   ACCESS     read-only
   STATUS     mandatory
   DESCRIPTION
     "This variable represents the storage type value for the
      lpEnetLtFb tables."
::= { lpEnetLtFbRowStatusEntry 4 }

lpEnetLtFbIndex OBJECT-TYPE
   SYNTAX     NonReplicated 
   ACCESS     not-accessible
   STATUS     mandatory
   DESCRIPTION
     "This variable represents the index for the lpEnetLtFb tables."
::= { lpEnetLtFbRowStatusEntry 10 }

lpEnetLtFbTopTable OBJECT-TYPE
   SYNTAX     SEQUENCE OF LpEnetLtFbTopEntry
   ACCESS     not-accessible
   STATUS     mandatory
   DESCRIPTION
     "This group contains the operational data for the LanTest component 
      and its subcomponents."
::= { lpEnetLtFb 20 }

lpEnetLtFbTopEntry OBJECT-TYPE
   SYNTAX     LpEnetLtFbTopEntry
   ACCESS     not-accessible
   STATUS     mandatory
   DESCRIPTION
     "An entry in the lpEnetLtFbTopTable."
   INDEX {
      lpIndex,
      lpEnetIndex,
      lpEnetLtIndex,
      lpEnetLtFbIndex }
::= { lpEnetLtFbTopTable 1 }

LpEnetLtFbTopEntry ::= SEQUENCE {
   lpEnetLtFbTData
      AsciiString }

lpEnetLtFbTData OBJECT-TYPE
   SYNTAX     AsciiString (SIZE (0..255))
   ACCESS     read-write
   STATUS     mandatory
   DESCRIPTION
     "This attribute is used to display and set attributes."
::= { lpEnetLtFbTopEntry 1 }


-- LanTest TransmitInfo
-- This component builds a transmit header which is attached to all 
-- frames transmitted on LAN interfaces.

lpEnetLtFbTxInfo OBJECT IDENTIFIER ::= { lpEnetLtFb 2 }



lpEnetLtFbTxInfoRowStatusTable OBJECT-TYPE
   SYNTAX     SEQUENCE OF LpEnetLtFbTxInfoRowStatusEntry
   ACCESS     not-accessible
   STATUS     mandatory
   DESCRIPTION
     "This entry controls the addition and deletion of 
      lpEnetLtFbTxInfo components."
::= { lpEnetLtFbTxInfo 1 }

lpEnetLtFbTxInfoRowStatusEntry OBJECT-TYPE
   SYNTAX     LpEnetLtFbTxInfoRowStatusEntry
   ACCESS     not-accessible
   STATUS     mandatory
   DESCRIPTION
     "A single entry in the table represents a single 
      lpEnetLtFbTxInfo component."
   INDEX {
      lpIndex,
      lpEnetIndex,
      lpEnetLtIndex,
      lpEnetLtFbIndex,
      lpEnetLtFbTxInfoIndex }
::= { lpEnetLtFbTxInfoRowStatusTable 1 }

LpEnetLtFbTxInfoRowStatusEntry ::= SEQUENCE {
   lpEnetLtFbTxInfoRowStatus
      RowStatus,
   lpEnetLtFbTxInfoComponentName
      DisplayString,
   lpEnetLtFbTxInfoStorageType
      StorageType,
   lpEnetLtFbTxInfoIndex
      NonReplicated }

lpEnetLtFbTxInfoRowStatus OBJECT-TYPE
   SYNTAX     RowStatus 
   ACCESS     read-only
   STATUS     mandatory
   DESCRIPTION
     "This variable is used as the basis for SNMP naming of
      lpEnetLtFbTxInfo components.
      These components cannot be added nor deleted."
::= { lpEnetLtFbTxInfoRowStatusEntry 1 }

lpEnetLtFbTxInfoComponentName OBJECT-TYPE
   SYNTAX     DisplayString 
   ACCESS     read-only
   STATUS     mandatory
   DESCRIPTION
     "This variable provides the component's string name for
      use with the ASCII Console Interface"
::= { lpEnetLtFbTxInfoRowStatusEntry 2 }

lpEnetLtFbTxInfoStorageType OBJECT-TYPE
   SYNTAX     StorageType 
   ACCESS     read-only
   STATUS     mandatory
   DESCRIPTION
     "This variable represents the storage type value for the
      lpEnetLtFbTxInfo tables."
::= { lpEnetLtFbTxInfoRowStatusEntry 4 }

lpEnetLtFbTxInfoIndex OBJECT-TYPE
   SYNTAX     NonReplicated 
   ACCESS     not-accessible
   STATUS     mandatory
   DESCRIPTION
     "This variable represents the index for the lpEnetLtFbTxInfo tables."
::= { lpEnetLtFbTxInfoRowStatusEntry 10 }

lpEnetLtFbTxInfoTopTable OBJECT-TYPE
   SYNTAX     SEQUENCE OF LpEnetLtFbTxInfoTopEntry
   ACCESS     not-accessible
   STATUS     mandatory
   DESCRIPTION
     "This group contains the operational data for the LanTest component 
      and its subcomponents."
::= { lpEnetLtFbTxInfo 10 }

lpEnetLtFbTxInfoTopEntry OBJECT-TYPE
   SYNTAX     LpEnetLtFbTxInfoTopEntry
   ACCESS     not-accessible
   STATUS     mandatory
   DESCRIPTION
     "An entry in the lpEnetLtFbTxInfoTopTable."
   INDEX {
      lpIndex,
      lpEnetIndex,
      lpEnetLtIndex,
      lpEnetLtFbIndex,
      lpEnetLtFbTxInfoIndex }
::= { lpEnetLtFbTxInfoTopTable 1 }

LpEnetLtFbTxInfoTopEntry ::= SEQUENCE {
   lpEnetLtFbTxInfoTData
      AsciiString }

lpEnetLtFbTxInfoTData OBJECT-TYPE
   SYNTAX     AsciiString (SIZE (0..255))
   ACCESS     read-write
   STATUS     mandatory
   DESCRIPTION
     "This attribute is used to display and set attributes."
::= { lpEnetLtFbTxInfoTopEntry 1 }


-- LanTest FddiMac
-- This component builds an FDDI MAC header which is attached to 
-- all FDDI frames.

lpEnetLtFbFddiMac OBJECT IDENTIFIER ::= { lpEnetLtFb 3 }



lpEnetLtFbFddiMacRowStatusTable OBJECT-TYPE
   SYNTAX     SEQUENCE OF LpEnetLtFbFddiMacRowStatusEntry
   ACCESS     not-accessible
   STATUS     mandatory
   DESCRIPTION
     "This entry controls the addition and deletion of 
      lpEnetLtFbFddiMac components."
::= { lpEnetLtFbFddiMac 1 }

lpEnetLtFbFddiMacRowStatusEntry OBJECT-TYPE
   SYNTAX     LpEnetLtFbFddiMacRowStatusEntry
   ACCESS     not-accessible
   STATUS     mandatory
   DESCRIPTION
     "A single entry in the table represents a single 
      lpEnetLtFbFddiMac component."
   INDEX {
      lpIndex,
      lpEnetIndex,
      lpEnetLtIndex,
      lpEnetLtFbIndex,
      lpEnetLtFbFddiMacIndex }
::= { lpEnetLtFbFddiMacRowStatusTable 1 }

LpEnetLtFbFddiMacRowStatusEntry ::= SEQUENCE {
   lpEnetLtFbFddiMacRowStatus
      RowStatus,
   lpEnetLtFbFddiMacComponentName
      DisplayString,
   lpEnetLtFbFddiMacStorageType
      StorageType,
   lpEnetLtFbFddiMacIndex
      NonReplicated }

lpEnetLtFbFddiMacRowStatus OBJECT-TYPE
   SYNTAX     RowStatus 
   ACCESS     read-only
   STATUS     mandatory
   DESCRIPTION
     "This variable is used as the basis for SNMP naming of
      lpEnetLtFbFddiMac components.
      These components cannot be added nor deleted."
::= { lpEnetLtFbFddiMacRowStatusEntry 1 }

lpEnetLtFbFddiMacComponentName OBJECT-TYPE
   SYNTAX     DisplayString 
   ACCESS     read-only
   STATUS     mandatory
   DESCRIPTION
     "This variable provides the component's string name for
      use with the ASCII Console Interface"
::= { lpEnetLtFbFddiMacRowStatusEntry 2 }

lpEnetLtFbFddiMacStorageType OBJECT-TYPE
   SYNTAX     StorageType 
   ACCESS     read-only
   STATUS     mandatory
   DESCRIPTION
     "This variable represents the storage type value for the
      lpEnetLtFbFddiMac tables."
::= { lpEnetLtFbFddiMacRowStatusEntry 4 }

lpEnetLtFbFddiMacIndex OBJECT-TYPE
   SYNTAX     NonReplicated 
   ACCESS     not-accessible
   STATUS     mandatory
   DESCRIPTION
     "This variable represents the index for the lpEnetLtFbFddiMac tables."
::= { lpEnetLtFbFddiMacRowStatusEntry 10 }

lpEnetLtFbFddiMacTopTable OBJECT-TYPE
   SYNTAX     SEQUENCE OF LpEnetLtFbFddiMacTopEntry
   ACCESS     not-accessible
   STATUS     mandatory
   DESCRIPTION
     "This group contains the operational data for the LanTest component 
      and its subcomponents."
::= { lpEnetLtFbFddiMac 10 }

lpEnetLtFbFddiMacTopEntry OBJECT-TYPE
   SYNTAX     LpEnetLtFbFddiMacTopEntry
   ACCESS     not-accessible
   STATUS     mandatory
   DESCRIPTION
     "An entry in the lpEnetLtFbFddiMacTopTable."
   INDEX {
      lpIndex,
      lpEnetIndex,
      lpEnetLtIndex,
      lpEnetLtFbIndex,
      lpEnetLtFbFddiMacIndex }
::= { lpEnetLtFbFddiMacTopTable 1 }

LpEnetLtFbFddiMacTopEntry ::= SEQUENCE {
   lpEnetLtFbFddiMacTData
      AsciiString }

lpEnetLtFbFddiMacTData OBJECT-TYPE
   SYNTAX     AsciiString (SIZE (0..255))
   ACCESS     read-write
   STATUS     mandatory
   DESCRIPTION
     "This attribute is used to display and set attributes."
::= { lpEnetLtFbFddiMacTopEntry 1 }


-- LanTest EthernetMac
-- This component builds an Ethernet MAC header which is attached 
-- to all Ethernet frames.

lpEnetLtFbMacEnet OBJECT IDENTIFIER ::= { lpEnetLtFb 4 }



lpEnetLtFbMacEnetRowStatusTable OBJECT-TYPE
   SYNTAX     SEQUENCE OF LpEnetLtFbMacEnetRowStatusEntry
   ACCESS     not-accessible
   STATUS     mandatory
   DESCRIPTION
     "This entry controls the addition and deletion of 
      lpEnetLtFbMacEnet components."
::= { lpEnetLtFbMacEnet 1 }

lpEnetLtFbMacEnetRowStatusEntry OBJECT-TYPE
   SYNTAX     LpEnetLtFbMacEnetRowStatusEntry
   ACCESS     not-accessible
   STATUS     mandatory
   DESCRIPTION
     "A single entry in the table represents a single 
      lpEnetLtFbMacEnet component."
   INDEX {
      lpIndex,
      lpEnetIndex,
      lpEnetLtIndex,
      lpEnetLtFbIndex,
      lpEnetLtFbMacEnetIndex }
::= { lpEnetLtFbMacEnetRowStatusTable 1 }

LpEnetLtFbMacEnetRowStatusEntry ::= SEQUENCE {
   lpEnetLtFbMacEnetRowStatus
      RowStatus,
   lpEnetLtFbMacEnetComponentName
      DisplayString,
   lpEnetLtFbMacEnetStorageType
      StorageType,
   lpEnetLtFbMacEnetIndex
      NonReplicated }

lpEnetLtFbMacEnetRowStatus OBJECT-TYPE
   SYNTAX     RowStatus 
   ACCESS     read-only
   STATUS     mandatory
   DESCRIPTION
     "This variable is used as the basis for SNMP naming of
      lpEnetLtFbMacEnet components.
      These components cannot be added nor deleted."
::= { lpEnetLtFbMacEnetRowStatusEntry 1 }

lpEnetLtFbMacEnetComponentName OBJECT-TYPE
   SYNTAX     DisplayString 
   ACCESS     read-only
   STATUS     mandatory
   DESCRIPTION
     "This variable provides the component's string name for
      use with the ASCII Console Interface"
::= { lpEnetLtFbMacEnetRowStatusEntry 2 }

lpEnetLtFbMacEnetStorageType OBJECT-TYPE
   SYNTAX     StorageType 
   ACCESS     read-only
   STATUS     mandatory
   DESCRIPTION
     "This variable represents the storage type value for the
      lpEnetLtFbMacEnet tables."
::= { lpEnetLtFbMacEnetRowStatusEntry 4 }

lpEnetLtFbMacEnetIndex OBJECT-TYPE
   SYNTAX     NonReplicated 
   ACCESS     not-accessible
   STATUS     mandatory
   DESCRIPTION
     "This variable represents the index for the lpEnetLtFbMacEnet tables."
::= { lpEnetLtFbMacEnetRowStatusEntry 10 }

lpEnetLtFbMacEnetTopTable OBJECT-TYPE
   SYNTAX     SEQUENCE OF LpEnetLtFbMacEnetTopEntry
   ACCESS     not-accessible
   STATUS     mandatory
   DESCRIPTION
     "This group contains the operational data for the LanTest component 
      and its subcomponents."
::= { lpEnetLtFbMacEnet 10 }

lpEnetLtFbMacEnetTopEntry OBJECT-TYPE
   SYNTAX     LpEnetLtFbMacEnetTopEntry
   ACCESS     not-accessible
   STATUS     mandatory
   DESCRIPTION
     "An entry in the lpEnetLtFbMacEnetTopTable."
   INDEX {
      lpIndex,
      lpEnetIndex,
      lpEnetLtIndex,
      lpEnetLtFbIndex,
      lpEnetLtFbMacEnetIndex }
::= { lpEnetLtFbMacEnetTopTable 1 }

LpEnetLtFbMacEnetTopEntry ::= SEQUENCE {
   lpEnetLtFbMacEnetTData
      AsciiString }

lpEnetLtFbMacEnetTData OBJECT-TYPE
   SYNTAX     AsciiString (SIZE (0..255))
   ACCESS     read-write
   STATUS     mandatory
   DESCRIPTION
     "This attribute is used to display and set attributes."
::= { lpEnetLtFbMacEnetTopEntry 1 }


-- LanTest TokenRingMac
-- This component builds a Token Ring MAC header which is attached 
-- to all Token Ring frames.

lpEnetLtFbMacTr OBJECT IDENTIFIER ::= { lpEnetLtFb 5 }



lpEnetLtFbMacTrRowStatusTable OBJECT-TYPE
   SYNTAX     SEQUENCE OF LpEnetLtFbMacTrRowStatusEntry
   ACCESS     not-accessible
   STATUS     mandatory
   DESCRIPTION
     "This entry controls the addition and deletion of 
      lpEnetLtFbMacTr components."
::= { lpEnetLtFbMacTr 1 }

lpEnetLtFbMacTrRowStatusEntry OBJECT-TYPE
   SYNTAX     LpEnetLtFbMacTrRowStatusEntry
   ACCESS     not-accessible
   STATUS     mandatory
   DESCRIPTION
     "A single entry in the table represents a single 
      lpEnetLtFbMacTr component."
   INDEX {
      lpIndex,
      lpEnetIndex,
      lpEnetLtIndex,
      lpEnetLtFbIndex,
      lpEnetLtFbMacTrIndex }
::= { lpEnetLtFbMacTrRowStatusTable 1 }

LpEnetLtFbMacTrRowStatusEntry ::= SEQUENCE {
   lpEnetLtFbMacTrRowStatus
      RowStatus,
   lpEnetLtFbMacTrComponentName
      DisplayString,
   lpEnetLtFbMacTrStorageType
      StorageType,
   lpEnetLtFbMacTrIndex
      NonReplicated }

lpEnetLtFbMacTrRowStatus OBJECT-TYPE
   SYNTAX     RowStatus 
   ACCESS     read-only
   STATUS     mandatory
   DESCRIPTION
     "This variable is used as the basis for SNMP naming of
      lpEnetLtFbMacTr components.
      These components cannot be added nor deleted."
::= { lpEnetLtFbMacTrRowStatusEntry 1 }

lpEnetLtFbMacTrComponentName OBJECT-TYPE
   SYNTAX     DisplayString 
   ACCESS     read-only
   STATUS     mandatory
   DESCRIPTION
     "This variable provides the component's string name for
      use with the ASCII Console Interface"
::= { lpEnetLtFbMacTrRowStatusEntry 2 }

lpEnetLtFbMacTrStorageType OBJECT-TYPE
   SYNTAX     StorageType 
   ACCESS     read-only
   STATUS     mandatory
   DESCRIPTION
     "This variable represents the storage type value for the
      lpEnetLtFbMacTr tables."
::= { lpEnetLtFbMacTrRowStatusEntry 4 }

lpEnetLtFbMacTrIndex OBJECT-TYPE
   SYNTAX     NonReplicated 
   ACCESS     not-accessible
   STATUS     mandatory
   DESCRIPTION
     "This variable represents the index for the lpEnetLtFbMacTr tables."
::= { lpEnetLtFbMacTrRowStatusEntry 10 }

lpEnetLtFbMacTrTopTable OBJECT-TYPE
   SYNTAX     SEQUENCE OF LpEnetLtFbMacTrTopEntry
   ACCESS     not-accessible
   STATUS     mandatory
   DESCRIPTION
     "This group contains the operational data for the LanTest component 
      and its subcomponents."
::= { lpEnetLtFbMacTr 10 }

lpEnetLtFbMacTrTopEntry OBJECT-TYPE
   SYNTAX     LpEnetLtFbMacTrTopEntry
   ACCESS     not-accessible
   STATUS     mandatory
   DESCRIPTION
     "An entry in the lpEnetLtFbMacTrTopTable."
   INDEX {
      lpIndex,
      lpEnetIndex,
      lpEnetLtIndex,
      lpEnetLtFbIndex,
      lpEnetLtFbMacTrIndex }
::= { lpEnetLtFbMacTrTopTable 1 }

LpEnetLtFbMacTrTopEntry ::= SEQUENCE {
   lpEnetLtFbMacTrTData
      AsciiString }

lpEnetLtFbMacTrTData OBJECT-TYPE
   SYNTAX     AsciiString (SIZE (0..255))
   ACCESS     read-write
   STATUS     mandatory
   DESCRIPTION
     "This attribute is used to display and set attributes."
::= { lpEnetLtFbMacTrTopEntry 1 }


-- This component adds a data field to frame.

lpEnetLtFbData OBJECT IDENTIFIER ::= { lpEnetLtFb 6 }



lpEnetLtFbDataRowStatusTable OBJECT-TYPE
   SYNTAX     SEQUENCE OF LpEnetLtFbDataRowStatusEntry
   ACCESS     not-accessible
   STATUS     mandatory
   DESCRIPTION
     "This entry controls the addition and deletion of 
      lpEnetLtFbData components."
::= { lpEnetLtFbData 1 }

lpEnetLtFbDataRowStatusEntry OBJECT-TYPE
   SYNTAX     LpEnetLtFbDataRowStatusEntry
   ACCESS     not-accessible
   STATUS     mandatory
   DESCRIPTION
     "A single entry in the table represents a single 
      lpEnetLtFbData component."
   INDEX {
      lpIndex,
      lpEnetIndex,
      lpEnetLtIndex,
      lpEnetLtFbIndex,
      lpEnetLtFbDataIndex }
::= { lpEnetLtFbDataRowStatusTable 1 }

LpEnetLtFbDataRowStatusEntry ::= SEQUENCE {
   lpEnetLtFbDataRowStatus
      RowStatus,
   lpEnetLtFbDataComponentName
      DisplayString,
   lpEnetLtFbDataStorageType
      StorageType,
   lpEnetLtFbDataIndex
      NonReplicated }

lpEnetLtFbDataRowStatus OBJECT-TYPE
   SYNTAX     RowStatus 
   ACCESS     read-only
   STATUS     mandatory
   DESCRIPTION
     "This variable is used as the basis for SNMP naming of
      lpEnetLtFbData components.
      These components cannot be added nor deleted."
::= { lpEnetLtFbDataRowStatusEntry 1 }

lpEnetLtFbDataComponentName OBJECT-TYPE
   SYNTAX     DisplayString 
   ACCESS     read-only
   STATUS     mandatory
   DESCRIPTION
     "This variable provides the component's string name for
      use with the ASCII Console Interface"
::= { lpEnetLtFbDataRowStatusEntry 2 }

lpEnetLtFbDataStorageType OBJECT-TYPE
   SYNTAX     StorageType 
   ACCESS     read-only
   STATUS     mandatory
   DESCRIPTION
     "This variable represents the storage type value for the
      lpEnetLtFbData tables."
::= { lpEnetLtFbDataRowStatusEntry 4 }

lpEnetLtFbDataIndex OBJECT-TYPE
   SYNTAX     NonReplicated 
   ACCESS     not-accessible
   STATUS     mandatory
   DESCRIPTION
     "This variable represents the index for the lpEnetLtFbData tables."
::= { lpEnetLtFbDataRowStatusEntry 10 }

lpEnetLtFbDataTopTable OBJECT-TYPE
   SYNTAX     SEQUENCE OF LpEnetLtFbDataTopEntry
   ACCESS     not-accessible
   STATUS     mandatory
   DESCRIPTION
     "This group contains the operational data for the LanTest component 
      and its subcomponents."
::= { lpEnetLtFbData 10 }

lpEnetLtFbDataTopEntry OBJECT-TYPE
   SYNTAX     LpEnetLtFbDataTopEntry
   ACCESS     not-accessible
   STATUS     mandatory
   DESCRIPTION
     "An entry in the lpEnetLtFbDataTopTable."
   INDEX {
      lpIndex,
      lpEnetIndex,
      lpEnetLtIndex,
      lpEnetLtFbIndex,
      lpEnetLtFbDataIndex }
::= { lpEnetLtFbDataTopTable 1 }

LpEnetLtFbDataTopEntry ::= SEQUENCE {
   lpEnetLtFbDataTData
      AsciiString }

lpEnetLtFbDataTData OBJECT-TYPE
   SYNTAX     AsciiString (SIZE (0..255))
   ACCESS     read-write
   STATUS     mandatory
   DESCRIPTION
     "This attribute is used to display and set attributes."
::= { lpEnetLtFbDataTopEntry 1 }


-- LanTest IpHeader
-- This component adds an IP header to a frame or packet.

lpEnetLtFbIpH OBJECT IDENTIFIER ::= { lpEnetLtFb 7 }



lpEnetLtFbIpHRowStatusTable OBJECT-TYPE
   SYNTAX     SEQUENCE OF LpEnetLtFbIpHRowStatusEntry
   ACCESS     not-accessible
   STATUS     mandatory
   DESCRIPTION
     "This entry controls the addition and deletion of 
      lpEnetLtFbIpH components."
::= { lpEnetLtFbIpH 1 }

lpEnetLtFbIpHRowStatusEntry OBJECT-TYPE
   SYNTAX     LpEnetLtFbIpHRowStatusEntry
   ACCESS     not-accessible
   STATUS     mandatory
   DESCRIPTION
     "A single entry in the table represents a single 
      lpEnetLtFbIpH component."
   INDEX {
      lpIndex,
      lpEnetIndex,
      lpEnetLtIndex,
      lpEnetLtFbIndex,
      lpEnetLtFbIpHIndex }
::= { lpEnetLtFbIpHRowStatusTable 1 }

LpEnetLtFbIpHRowStatusEntry ::= SEQUENCE {
   lpEnetLtFbIpHRowStatus
      RowStatus,
   lpEnetLtFbIpHComponentName
      DisplayString,
   lpEnetLtFbIpHStorageType
      StorageType,
   lpEnetLtFbIpHIndex
      NonReplicated }

lpEnetLtFbIpHRowStatus OBJECT-TYPE
   SYNTAX     RowStatus 
   ACCESS     read-only
   STATUS     mandatory
   DESCRIPTION
     "This variable is used as the basis for SNMP naming of
      lpEnetLtFbIpH components.
      These components cannot be added nor deleted."
::= { lpEnetLtFbIpHRowStatusEntry 1 }

lpEnetLtFbIpHComponentName OBJECT-TYPE
   SYNTAX     DisplayString 
   ACCESS     read-only
   STATUS     mandatory
   DESCRIPTION
     "This variable provides the component's string name for
      use with the ASCII Console Interface"
::= { lpEnetLtFbIpHRowStatusEntry 2 }

lpEnetLtFbIpHStorageType OBJECT-TYPE
   SYNTAX     StorageType 
   ACCESS     read-only
   STATUS     mandatory
   DESCRIPTION
     "This variable represents the storage type value for the
      lpEnetLtFbIpH tables."
::= { lpEnetLtFbIpHRowStatusEntry 4 }

lpEnetLtFbIpHIndex OBJECT-TYPE
   SYNTAX     NonReplicated 
   ACCESS     not-accessible
   STATUS     mandatory
   DESCRIPTION
     "This variable represents the index for the lpEnetLtFbIpH tables."
::= { lpEnetLtFbIpHRowStatusEntry 10 }

lpEnetLtFbIpHTopTable OBJECT-TYPE
   SYNTAX     SEQUENCE OF LpEnetLtFbIpHTopEntry
   ACCESS     not-accessible
   STATUS     mandatory
   DESCRIPTION
     "This group contains the operational data for the LanTest component 
      and its subcomponents."
::= { lpEnetLtFbIpH 10 }

lpEnetLtFbIpHTopEntry OBJECT-TYPE
   SYNTAX     LpEnetLtFbIpHTopEntry
   ACCESS     not-accessible
   STATUS     mandatory
   DESCRIPTION
     "An entry in the lpEnetLtFbIpHTopTable."
   INDEX {
      lpIndex,
      lpEnetIndex,
      lpEnetLtIndex,
      lpEnetLtFbIndex,
      lpEnetLtFbIpHIndex }
::= { lpEnetLtFbIpHTopTable 1 }

LpEnetLtFbIpHTopEntry ::= SEQUENCE {
   lpEnetLtFbIpHTData
      AsciiString }

lpEnetLtFbIpHTData OBJECT-TYPE
   SYNTAX     AsciiString (SIZE (0..255))
   ACCESS     read-write
   STATUS     mandatory
   DESCRIPTION
     "This attribute is used to display and set attributes."
::= { lpEnetLtFbIpHTopEntry 1 }


-- LanTest LlcHeader
-- This component adds an LLC 802.2 or Ethernet header to a frame 
-- or packet.

lpEnetLtFbLlch OBJECT IDENTIFIER ::= { lpEnetLtFb 8 }



lpEnetLtFbLlchRowStatusTable OBJECT-TYPE
   SYNTAX     SEQUENCE OF LpEnetLtFbLlchRowStatusEntry
   ACCESS     not-accessible
   STATUS     mandatory
   DESCRIPTION
     "This entry controls the addition and deletion of 
      lpEnetLtFbLlch components."
::= { lpEnetLtFbLlch 1 }

lpEnetLtFbLlchRowStatusEntry OBJECT-TYPE
   SYNTAX     LpEnetLtFbLlchRowStatusEntry
   ACCESS     not-accessible
   STATUS     mandatory
   DESCRIPTION
     "A single entry in the table represents a single 
      lpEnetLtFbLlch component."
   INDEX {
      lpIndex,
      lpEnetIndex,
      lpEnetLtIndex,
      lpEnetLtFbIndex,
      lpEnetLtFbLlchIndex }
::= { lpEnetLtFbLlchRowStatusTable 1 }

LpEnetLtFbLlchRowStatusEntry ::= SEQUENCE {
   lpEnetLtFbLlchRowStatus
      RowStatus,
   lpEnetLtFbLlchComponentName
      DisplayString,
   lpEnetLtFbLlchStorageType
      StorageType,
   lpEnetLtFbLlchIndex
      NonReplicated }

lpEnetLtFbLlchRowStatus OBJECT-TYPE
   SYNTAX     RowStatus 
   ACCESS     read-only
   STATUS     mandatory
   DESCRIPTION
     "This variable is used as the basis for SNMP naming of
      lpEnetLtFbLlch components.
      These components cannot be added nor deleted."
::= { lpEnetLtFbLlchRowStatusEntry 1 }

lpEnetLtFbLlchComponentName OBJECT-TYPE
   SYNTAX     DisplayString 
   ACCESS     read-only
   STATUS     mandatory
   DESCRIPTION
     "This variable provides the component's string name for
      use with the ASCII Console Interface"
::= { lpEnetLtFbLlchRowStatusEntry 2 }

lpEnetLtFbLlchStorageType OBJECT-TYPE
   SYNTAX     StorageType 
   ACCESS     read-only
   STATUS     mandatory
   DESCRIPTION
     "This variable represents the storage type value for the
      lpEnetLtFbLlch tables."
::= { lpEnetLtFbLlchRowStatusEntry 4 }

lpEnetLtFbLlchIndex OBJECT-TYPE
   SYNTAX     NonReplicated 
   ACCESS     not-accessible
   STATUS     mandatory
   DESCRIPTION
     "This variable represents the index for the lpEnetLtFbLlch tables."
::= { lpEnetLtFbLlchRowStatusEntry 10 }

lpEnetLtFbLlchTopTable OBJECT-TYPE
   SYNTAX     SEQUENCE OF LpEnetLtFbLlchTopEntry
   ACCESS     not-accessible
   STATUS     mandatory
   DESCRIPTION
     "This group contains the operational data for the LanTest component 
      and its subcomponents."
::= { lpEnetLtFbLlch 10 }

lpEnetLtFbLlchTopEntry OBJECT-TYPE
   SYNTAX     LpEnetLtFbLlchTopEntry
   ACCESS     not-accessible
   STATUS     mandatory
   DESCRIPTION
     "An entry in the lpEnetLtFbLlchTopTable."
   INDEX {
      lpIndex,
      lpEnetIndex,
      lpEnetLtIndex,
      lpEnetLtFbIndex,
      lpEnetLtFbLlchIndex }
::= { lpEnetLtFbLlchTopTable 1 }

LpEnetLtFbLlchTopEntry ::= SEQUENCE {
   lpEnetLtFbLlchTData
      AsciiString }

lpEnetLtFbLlchTData OBJECT-TYPE
   SYNTAX     AsciiString (SIZE (0..255))
   ACCESS     read-write
   STATUS     mandatory
   DESCRIPTION
     "This attribute is used to display and set attributes."
::= { lpEnetLtFbLlchTopEntry 1 }


-- This component adds an AppleTalk header to a frame or packet.

lpEnetLtFbAppleH OBJECT IDENTIFIER ::= { lpEnetLtFb 9 }



lpEnetLtFbAppleHRowStatusTable OBJECT-TYPE
   SYNTAX     SEQUENCE OF LpEnetLtFbAppleHRowStatusEntry
   ACCESS     not-accessible
   STATUS     mandatory
   DESCRIPTION
     "This entry controls the addition and deletion of 
      lpEnetLtFbAppleH components."
::= { lpEnetLtFbAppleH 1 }

lpEnetLtFbAppleHRowStatusEntry OBJECT-TYPE
   SYNTAX     LpEnetLtFbAppleHRowStatusEntry
   ACCESS     not-accessible
   STATUS     mandatory
   DESCRIPTION
     "A single entry in the table represents a single 
      lpEnetLtFbAppleH component."
   INDEX {
      lpIndex,
      lpEnetIndex,
      lpEnetLtIndex,
      lpEnetLtFbIndex,
      lpEnetLtFbAppleHIndex }
::= { lpEnetLtFbAppleHRowStatusTable 1 }

LpEnetLtFbAppleHRowStatusEntry ::= SEQUENCE {
   lpEnetLtFbAppleHRowStatus
      RowStatus,
   lpEnetLtFbAppleHComponentName
      DisplayString,
   lpEnetLtFbAppleHStorageType
      StorageType,
   lpEnetLtFbAppleHIndex
      NonReplicated }

lpEnetLtFbAppleHRowStatus OBJECT-TYPE
   SYNTAX     RowStatus 
   ACCESS     read-only
   STATUS     mandatory
   DESCRIPTION
     "This variable is used as the basis for SNMP naming of
      lpEnetLtFbAppleH components.
      These components cannot be added nor deleted."
::= { lpEnetLtFbAppleHRowStatusEntry 1 }

lpEnetLtFbAppleHComponentName OBJECT-TYPE
   SYNTAX     DisplayString 
   ACCESS     read-only
   STATUS     mandatory
   DESCRIPTION
     "This variable provides the component's string name for
      use with the ASCII Console Interface"
::= { lpEnetLtFbAppleHRowStatusEntry 2 }

lpEnetLtFbAppleHStorageType OBJECT-TYPE
   SYNTAX     StorageType 
   ACCESS     read-only
   STATUS     mandatory
   DESCRIPTION
     "This variable represents the storage type value for the
      lpEnetLtFbAppleH tables."
::= { lpEnetLtFbAppleHRowStatusEntry 4 }

lpEnetLtFbAppleHIndex OBJECT-TYPE
   SYNTAX     NonReplicated 
   ACCESS     not-accessible
   STATUS     mandatory
   DESCRIPTION
     "This variable represents the index for the lpEnetLtFbAppleH tables."
::= { lpEnetLtFbAppleHRowStatusEntry 10 }

lpEnetLtFbAppleHTopTable OBJECT-TYPE
   SYNTAX     SEQUENCE OF LpEnetLtFbAppleHTopEntry
   ACCESS     not-accessible
   STATUS     mandatory
   DESCRIPTION
     "This group contains the operational data for the LanTest component 
      and its subcomponents."
::= { lpEnetLtFbAppleH 10 }

lpEnetLtFbAppleHTopEntry OBJECT-TYPE
   SYNTAX     LpEnetLtFbAppleHTopEntry
   ACCESS     not-accessible
   STATUS     mandatory
   DESCRIPTION
     "An entry in the lpEnetLtFbAppleHTopTable."
   INDEX {
      lpIndex,
      lpEnetIndex,
      lpEnetLtIndex,
      lpEnetLtFbIndex,
      lpEnetLtFbAppleHIndex }
::= { lpEnetLtFbAppleHTopTable 1 }

LpEnetLtFbAppleHTopEntry ::= SEQUENCE {
   lpEnetLtFbAppleHTData
      AsciiString }

lpEnetLtFbAppleHTData OBJECT-TYPE
   SYNTAX     AsciiString (SIZE (0..255))
   ACCESS     read-write
   STATUS     mandatory
   DESCRIPTION
     "This attribute is used to display and set attributes."
::= { lpEnetLtFbAppleHTopEntry 1 }


-- This component adds an IPX header to a frame or packet.

lpEnetLtFbIpxH OBJECT IDENTIFIER ::= { lpEnetLtFb 10 }



lpEnetLtFbIpxHRowStatusTable OBJECT-TYPE
   SYNTAX     SEQUENCE OF LpEnetLtFbIpxHRowStatusEntry
   ACCESS     not-accessible
   STATUS     mandatory
   DESCRIPTION
     "This entry controls the addition and deletion of 
      lpEnetLtFbIpxH components."
::= { lpEnetLtFbIpxH 1 }

lpEnetLtFbIpxHRowStatusEntry OBJECT-TYPE
   SYNTAX     LpEnetLtFbIpxHRowStatusEntry
   ACCESS     not-accessible
   STATUS     mandatory
   DESCRIPTION
     "A single entry in the table represents a single 
      lpEnetLtFbIpxH component."
   INDEX {
      lpIndex,
      lpEnetIndex,
      lpEnetLtIndex,
      lpEnetLtFbIndex,
      lpEnetLtFbIpxHIndex }
::= { lpEnetLtFbIpxHRowStatusTable 1 }

LpEnetLtFbIpxHRowStatusEntry ::= SEQUENCE {
   lpEnetLtFbIpxHRowStatus
      RowStatus,
   lpEnetLtFbIpxHComponentName
      DisplayString,
   lpEnetLtFbIpxHStorageType
      StorageType,
   lpEnetLtFbIpxHIndex
      NonReplicated }

lpEnetLtFbIpxHRowStatus OBJECT-TYPE
   SYNTAX     RowStatus 
   ACCESS     read-only
   STATUS     mandatory
   DESCRIPTION
     "This variable is used as the basis for SNMP naming of
      lpEnetLtFbIpxH components.
      These components cannot be added nor deleted."
::= { lpEnetLtFbIpxHRowStatusEntry 1 }

lpEnetLtFbIpxHComponentName OBJECT-TYPE
   SYNTAX     DisplayString 
   ACCESS     read-only
   STATUS     mandatory
   DESCRIPTION
     "This variable provides the component's string name for
      use with the ASCII Console Interface"
::= { lpEnetLtFbIpxHRowStatusEntry 2 }

lpEnetLtFbIpxHStorageType OBJECT-TYPE
   SYNTAX     StorageType 
   ACCESS     read-only
   STATUS     mandatory
   DESCRIPTION
     "This variable represents the storage type value for the
      lpEnetLtFbIpxH tables."
::= { lpEnetLtFbIpxHRowStatusEntry 4 }

lpEnetLtFbIpxHIndex OBJECT-TYPE
   SYNTAX     NonReplicated 
   ACCESS     not-accessible
   STATUS     mandatory
   DESCRIPTION
     "This variable represents the index for the lpEnetLtFbIpxH tables."
::= { lpEnetLtFbIpxHRowStatusEntry 10 }

lpEnetLtFbIpxHTopTable OBJECT-TYPE
   SYNTAX     SEQUENCE OF LpEnetLtFbIpxHTopEntry
   ACCESS     not-accessible
   STATUS     mandatory
   DESCRIPTION
     "This group contains the operational data for the LanTest component 
      and its subcomponents."
::= { lpEnetLtFbIpxH 10 }

lpEnetLtFbIpxHTopEntry OBJECT-TYPE
   SYNTAX     LpEnetLtFbIpxHTopEntry
   ACCESS     not-accessible
   STATUS     mandatory
   DESCRIPTION
     "An entry in the lpEnetLtFbIpxHTopTable."
   INDEX {
      lpIndex,
      lpEnetIndex,
      lpEnetLtIndex,
      lpEnetLtFbIndex,
      lpEnetLtFbIpxHIndex }
::= { lpEnetLtFbIpxHTopTable 1 }

LpEnetLtFbIpxHTopEntry ::= SEQUENCE {
   lpEnetLtFbIpxHTData
      AsciiString }

lpEnetLtFbIpxHTData OBJECT-TYPE
   SYNTAX     AsciiString (SIZE (0..255))
   ACCESS     read-write
   STATUS     mandatory
   DESCRIPTION
     "This attribute is used to display and set attributes."
::= { lpEnetLtFbIpxHTopEntry 1 }


-- LanTest Control
-- This component controls the overall testing by telling the 
-- FrameBuild component to start and check the FrameCompare 
-- component to see if the test is complete.

lpEnetLtCntl OBJECT IDENTIFIER ::= { lpEnetLt 6 }



lpEnetLtCntlRowStatusTable OBJECT-TYPE
   SYNTAX     SEQUENCE OF LpEnetLtCntlRowStatusEntry
   ACCESS     not-accessible
   STATUS     mandatory
   DESCRIPTION
     "This entry controls the addition and deletion of 
      lpEnetLtCntl components."
::= { lpEnetLtCntl 1 }

lpEnetLtCntlRowStatusEntry OBJECT-TYPE
   SYNTAX     LpEnetLtCntlRowStatusEntry
   ACCESS     not-accessible
   STATUS     mandatory
   DESCRIPTION
     "A single entry in the table represents a single 
      lpEnetLtCntl component."
   INDEX {
      lpIndex,
      lpEnetIndex,
      lpEnetLtIndex,
      lpEnetLtCntlIndex }
::= { lpEnetLtCntlRowStatusTable 1 }

LpEnetLtCntlRowStatusEntry ::= SEQUENCE {
   lpEnetLtCntlRowStatus
      RowStatus,
   lpEnetLtCntlComponentName
      DisplayString,
   lpEnetLtCntlStorageType
      StorageType,
   lpEnetLtCntlIndex
      NonReplicated }

lpEnetLtCntlRowStatus OBJECT-TYPE
   SYNTAX     RowStatus 
   ACCESS     read-only
   STATUS     mandatory
   DESCRIPTION
     "This variable is used as the basis for SNMP naming of
      lpEnetLtCntl components.
      These components cannot be added nor deleted."
::= { lpEnetLtCntlRowStatusEntry 1 }

lpEnetLtCntlComponentName OBJECT-TYPE
   SYNTAX     DisplayString 
   ACCESS     read-only
   STATUS     mandatory
   DESCRIPTION
     "This variable provides the component's string name for
      use with the ASCII Console Interface"
::= { lpEnetLtCntlRowStatusEntry 2 }

lpEnetLtCntlStorageType OBJECT-TYPE
   SYNTAX     StorageType 
   ACCESS     read-only
   STATUS     mandatory
   DESCRIPTION
     "This variable represents the storage type value for the
      lpEnetLtCntl tables."
::= { lpEnetLtCntlRowStatusEntry 4 }

lpEnetLtCntlIndex OBJECT-TYPE
   SYNTAX     NonReplicated 
   ACCESS     not-accessible
   STATUS     mandatory
   DESCRIPTION
     "This variable represents the index for the lpEnetLtCntl tables."
::= { lpEnetLtCntlRowStatusEntry 10 }

lpEnetLtCntlTopTable OBJECT-TYPE
   SYNTAX     SEQUENCE OF LpEnetLtCntlTopEntry
   ACCESS     not-accessible
   STATUS     mandatory
   DESCRIPTION
     "This group contains the operational data for the LanTest component 
      and its subcomponents."
::= { lpEnetLtCntl 10 }

lpEnetLtCntlTopEntry OBJECT-TYPE
   SYNTAX     LpEnetLtCntlTopEntry
   ACCESS     not-accessible
   STATUS     mandatory
   DESCRIPTION
     "An entry in the lpEnetLtCntlTopTable."
   INDEX {
      lpIndex,
      lpEnetIndex,
      lpEnetLtIndex,
      lpEnetLtCntlIndex }
::= { lpEnetLtCntlTopTable 1 }

LpEnetLtCntlTopEntry ::= SEQUENCE {
   lpEnetLtCntlTData
      AsciiString }

lpEnetLtCntlTData OBJECT-TYPE
   SYNTAX     AsciiString (SIZE (0..255))
   ACCESS     read-write
   STATUS     mandatory
   DESCRIPTION
     "This attribute is used to display and set attributes."
::= { lpEnetLtCntlTopEntry 1 }


-- Lp/n Fddi/n Test, or
-- Lp/n Ethernet/n Test, or
-- Lp/n TokenRing/n Test, or
-- Lp/n IlsForwarder/n Test
-- The Test component is used to do StartUp port test for LAN cards.

lpEnetTest OBJECT IDENTIFIER ::= { lpEnet 5 }



lpEnetTestRowStatusTable OBJECT-TYPE
   SYNTAX     SEQUENCE OF LpEnetTestRowStatusEntry
   ACCESS     not-accessible
   STATUS     mandatory
   DESCRIPTION
     "This entry controls the addition and deletion of 
      lpEnetTest components."
::= { lpEnetTest 1 }

lpEnetTestRowStatusEntry OBJECT-TYPE
   SYNTAX     LpEnetTestRowStatusEntry
   ACCESS     not-accessible
   STATUS     mandatory
   DESCRIPTION
     "A single entry in the table represents a single 
      lpEnetTest component."
   INDEX {
      lpIndex,
      lpEnetIndex,
      lpEnetTestIndex }
::= { lpEnetTestRowStatusTable 1 }

LpEnetTestRowStatusEntry ::= SEQUENCE {
   lpEnetTestRowStatus
      RowStatus,
   lpEnetTestComponentName
      DisplayString,
   lpEnetTestStorageType
      StorageType,
   lpEnetTestIndex
      NonReplicated }

lpEnetTestRowStatus OBJECT-TYPE
   SYNTAX     RowStatus 
   ACCESS     read-only
   STATUS     mandatory
   DESCRIPTION
     "This variable is used as the basis for SNMP naming of
      lpEnetTest components.
      These components cannot be added nor deleted."
::= { lpEnetTestRowStatusEntry 1 }

lpEnetTestComponentName OBJECT-TYPE
   SYNTAX     DisplayString 
   ACCESS     read-only
   STATUS     mandatory
   DESCRIPTION
     "This variable provides the component's string name for
      use with the ASCII Console Interface"
::= { lpEnetTestRowStatusEntry 2 }

lpEnetTestStorageType OBJECT-TYPE
   SYNTAX     StorageType 
   ACCESS     read-only
   STATUS     mandatory
   DESCRIPTION
     "This variable represents the storage type value for the
      lpEnetTest tables."
::= { lpEnetTestRowStatusEntry 4 }

lpEnetTestIndex OBJECT-TYPE
   SYNTAX     NonReplicated 
   ACCESS     not-accessible
   STATUS     mandatory
   DESCRIPTION
     "This variable represents the index for the lpEnetTest tables."
::= { lpEnetTestRowStatusEntry 10 }

lpEnetTestPTOTable OBJECT-TYPE
   SYNTAX     SEQUENCE OF LpEnetTestPTOEntry
   ACCESS     not-accessible
   STATUS     mandatory
   DESCRIPTION
     "This group contains the operational data for the LanPortTest 
      component."
::= { lpEnetTest 10 }

lpEnetTestPTOEntry OBJECT-TYPE
   SYNTAX     LpEnetTestPTOEntry
   ACCESS     not-accessible
   STATUS     mandatory
   DESCRIPTION
     "An entry in the lpEnetTestPTOTable."
   INDEX {
      lpIndex,
      lpEnetIndex,
      lpEnetTestIndex }
::= { lpEnetTestPTOTable 1 }

LpEnetTestPTOEntry ::= SEQUENCE {
   lpEnetTestType
      INTEGER,
   lpEnetTestFrmSize
      Unsigned32,
   lpEnetTestDuration
      Unsigned32 }

lpEnetTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { lpEnetTestPTOEntry 1 }

lpEnetTestFrmSize OBJECT-TYPE
   SYNTAX     Unsigned32 (4..4096)
   ACCESS     read-write
   STATUS     mandatory
   DESCRIPTION
     "This attribute defines the size of the test data frames in number of 
      bytes."
   DEFVAL     { 1024 }
::= { lpEnetTestPTOEntry 2 }

lpEnetTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpEnetTestPTOEntry 3 }

lpEnetTestResultsTable OBJECT-TYPE
   SYNTAX     SEQUENCE OF LpEnetTestResultsEntry
   ACCESS     not-accessible
   STATUS     mandatory
   DESCRIPTION
     "This group contains all the statistics related attributes of the Test 
      component."
::= { lpEnetTest 11 }

lpEnetTestResultsEntry OBJECT-TYPE
   SYNTAX     LpEnetTestResultsEntry
   ACCESS     not-accessible
   STATUS     mandatory
   DESCRIPTION
     "An entry in the lpEnetTestResultsTable."
   INDEX {
      lpIndex,
      lpEnetIndex,
      lpEnetTestIndex }
::= { lpEnetTestResultsTable 1 }

LpEnetTestResultsEntry ::= SEQUENCE {
   lpEnetTestElapsedTime
      Counter32,
   lpEnetTestTimeRemaining
      Unsigned32,
   lpEnetTestCauseOfTermination
      INTEGER,
   lpEnetTestFrmTx
      PassportCounter64,
   lpEnetTestBitsTx
      PassportCounter64,
   lpEnetTestFrmRx
      PassportCounter64,
   lpEnetTestBitsRx
      PassportCounter64,
   lpEnetTestErroredFrmRx
      PassportCounter64 }

lpEnetTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpEnetTestResultsEntry 4 }

lpEnetTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpEnetTestResultsEntry 5 }

lpEnetTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { lpEnetTestResultsEntry 6 }

lpEnetTestFrmTx OBJECT-TYPE
   SYNTAX     PassportCounter64 
   ACCESS     read-only
   STATUS     mandatory
   DESCRIPTION
     "This attribute is the total number of frames sent during the test 
      period. This counter is not expected to reach its maximum value."
::= { lpEnetTestResultsEntry 7 }

lpEnetTestBitsTx OBJECT-TYPE
   SYNTAX     PassportCounter64 
   ACCESS     read-only
   STATUS     mandatory
   DESCRIPTION
     "This attribute is the total number of bits sent during the test period. 
      This counter is not expected to reach its maximum value."
::= { lpEnetTestResultsEntry 8 }

lpEnetTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpEnetTestResultsEntry 9 }

lpEnetTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { lpEnetTestResultsEntry 10 }

lpEnetTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { lpEnetTestResultsEntry 11 }


-- Lp/n Fddi/n
-- This component defines an instance of a FDDI station attached to a ring. 
-- One instance of this component must be created for each hardware 
-- interface. Each station must be provisioned prior to inserting into the 
-- ring.

lpFi OBJECT IDENTIFIER ::= { lp 4 }



lpFiRowStatusTable OBJECT-TYPE
   SYNTAX     SEQUENCE OF LpFiRowStatusEntry
   ACCESS     not-accessible
   STATUS     mandatory
   DESCRIPTION
     "This entry controls the addition and deletion of 
      lpFi components."
::= { lpFi 1 }

lpFiRowStatusEntry OBJECT-TYPE
   SYNTAX     LpFiRowStatusEntry
   ACCESS     not-accessible
   STATUS     mandatory
   DESCRIPTION
     "A single entry in the table represents a single 
      lpFi component."
   INDEX {
      lpIndex,
      lpFiIndex }
::= { lpFiRowStatusTable 1 }

LpFiRowStatusEntry ::= SEQUENCE {
   lpFiRowStatus
      RowStatus,
   lpFiComponentName
      DisplayString,
   lpFiStorageType
      StorageType,
   lpFiIndex
      Integer32 }

lpFiRowStatus OBJECT-TYPE
   SYNTAX     RowStatus 
   ACCESS     read-write
   STATUS     mandatory
   DESCRIPTION
     "This variable is used as the basis for SNMP naming of
      lpFi components.
      These components can be added and deleted."
::= { lpFiRowStatusEntry 1 }

lpFiComponentName OBJECT-TYPE
   SYNTAX     DisplayString 
   ACCESS     read-only
   STATUS     mandatory
   DESCRIPTION
     "This variable provides the component's string name for
      use with the ASCII Console Interface"
::= { lpFiRowStatusEntry 2 }

lpFiStorageType OBJECT-TYPE
   SYNTAX     StorageType 
   ACCESS     read-only
   STATUS     mandatory
   DESCRIPTION
     "This variable represents the storage type value for the
      lpFi tables."
::= { lpFiRowStatusEntry 4 }

lpFiIndex OBJECT-TYPE
   SYNTAX     Integer32 (0)
   ACCESS     not-accessible
   STATUS     mandatory
   DESCRIPTION
     "This variable represents the index for the lpFi tables."
::= { lpFiRowStatusEntry 10 }

lpFiCidDataTable OBJECT-TYPE
   SYNTAX     SEQUENCE OF LpFiCidDataEntry
   ACCESS     not-accessible
   STATUS     mandatory
   DESCRIPTION
     "This group contains the attribute for a component's Customer 
      Identifier (CID). Refer to the attribute description for a detailed 
      explanation of CIDs."
::= { lpFi 10 }

lpFiCidDataEntry OBJECT-TYPE
   SYNTAX     LpFiCidDataEntry
   ACCESS     not-accessible
   STATUS     mandatory
   DESCRIPTION
     "An entry in the lpFiCidDataTable."
   INDEX {
      lpIndex,
      lpFiIndex }
::= { lpFiCidDataTable 1 }

LpFiCidDataEntry ::= SEQUENCE {
   lpFiCustomerIdentifier
      Unsigned32 }

lpFiCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpFiCidDataEntry 1 }

lpFiIfEntryTable OBJECT-TYPE
   SYNTAX     SEQUENCE OF LpFiIfEntryEntry
   ACCESS     not-accessible
   STATUS     mandatory
   DESCRIPTION
     "This group contains the provisionable attributes for the ifEntry."
::= { lpFi 11 }

lpFiIfEntryEntry OBJECT-TYPE
   SYNTAX     LpFiIfEntryEntry
   ACCESS     not-accessible
   STATUS     mandatory
   DESCRIPTION
     "An entry in the lpFiIfEntryTable."
   INDEX {
      lpIndex,
      lpFiIndex }
::= { lpFiIfEntryTable 1 }

LpFiIfEntryEntry ::= SEQUENCE {
   lpFiIfAdminStatus
      INTEGER,
   lpFiIfIndex
      InterfaceIndex }

lpFiIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpFiIfEntryEntry 1 }

lpFiIfIndex OBJECT-TYPE
   SYNTAX     InterfaceIndex (1..65535)
   ACCESS     read-only
   STATUS     mandatory
   DESCRIPTION
     "This is the index for the IfEntry. Its value is automatically initialized 
      during the provisioning process."
::= { lpFiIfEntryEntry 2 }

lpFiSmtProvTable OBJECT-TYPE
   SYNTAX     SEQUENCE OF LpFiSmtProvEntry
   ACCESS     not-accessible
   STATUS     mandatory
   DESCRIPTION
     "This group contains the provisionable Station Management (SMT) 
      attributes of the Fddi component."
::= { lpFi 12 }

lpFiSmtProvEntry OBJECT-TYPE
   SYNTAX     LpFiSmtProvEntry
   ACCESS     not-accessible
   STATUS     mandatory
   DESCRIPTION
     "An entry in the lpFiSmtProvTable."
   INDEX {
      lpIndex,
      lpFiIndex }
::= { lpFiSmtProvTable 1 }

LpFiSmtProvEntry ::= SEQUENCE {
   lpFiUserData
      AsciiString,
   lpFiAcceptAa
      INTEGER,
   lpFiAcceptBb
      INTEGER,
   lpFiAcceptAs
      INTEGER,
   lpFiAcceptBs
      INTEGER,
   lpFiAcceptAm
      INTEGER,
   lpFiAcceptBm
      INTEGER,
   lpFiUseThruBa
      INTEGER,
   lpFiNeighborNotifyInterval
      Unsigned32,
   lpFiStatusReportPolicy
      INTEGER,
   lpFiTraceMaxExpirationTimer
      FddiTimeMilli,
   lpFiApplicationFramerName
      Link }

lpFiUserData OBJECT-TYPE
   SYNTAX     AsciiString (SIZE (0..32))
   ACCESS     read-write
   STATUS     mandatory
   DESCRIPTION
     "The user data field is used to identify the FDDI interface on the ring. 
      The user data contains a message with a maximum of 32 characters."
   DEFVAL     { '46444449'H }  -- "FDDI"
::= { lpFiSmtProvEntry 1 }

lpFiAcceptAa OBJECT-TYPE
   SYNTAX     INTEGER  {
                 enabled(1),
                 disabled(2) }
   ACCESS     read-write
   STATUS     mandatory
   DESCRIPTION
     "The acceptAa attribute defines the station type A to station type A 
      connection policy. If enabled, the connection will be accepted. If 
      disabled, the connection will be rejected."
   DEFVAL     { disabled }
::= { lpFiSmtProvEntry 2 }

lpFiAcceptBb OBJECT-TYPE
   SYNTAX     INTEGER  {
                 enabled(1),
                 disabled(2) }
   ACCESS     read-write
   STATUS     mandatory
   DESCRIPTION
     "The acceptBb attribute defines the station type B to station type B 
      connection policy. If enabled, the connection will be accepted. If 
      disabled, the connection will be rejected."
   DEFVAL     { disabled }
::= { lpFiSmtProvEntry 3 }

lpFiAcceptAs OBJECT-TYPE
   SYNTAX     INTEGER  {
                 enabled(1),
                 disabled(2) }
   ACCESS     read-write
   STATUS     mandatory
   DESCRIPTION
     "The acceptAs attribute defines the station type A to station type S 
      connection policy. If enabled, the connection will be accepted. If 
      disabled, the connection will be rejected."
   DEFVAL     { disabled }
::= { lpFiSmtProvEntry 4 }

lpFiAcceptBs OBJECT-TYPE
   SYNTAX     INTEGER  {
                 enabled(1),
                 disabled(2) }
   ACCESS     read-write
   STATUS     mandatory
   DESCRIPTION
     "The acceptBs attribute defines the station type B to station type S 
      connection policy. If enabled, the connection will be accepted. If 
      disabled, the connection will be rejected."
   DEFVAL     { disabled }
::= { lpFiSmtProvEntry 5 }

lpFiAcceptAm OBJECT-TYPE
   SYNTAX     INTEGER  {
                 enabled(1),
                 disabled(2) }
   ACCESS     read-write
   STATUS     mandatory
   DESCRIPTION
     "The acceptAm attribute defines the station type A to station type M 
      connection policy. If enabled, the connection will be accepted. If 
      disabled, the connection will be rejected."
   DEFVAL     { enabled }
::= { lpFiSmtProvEntry 6 }

lpFiAcceptBm OBJECT-TYPE
   SYNTAX     INTEGER  {
                 enabled(1),
                 disabled(2) }
   ACCESS     read-write
   STATUS     mandatory
   DESCRIPTION
     "The acceptBm attribute defines the station type B to station type M 
      connection policy. If enabled, the connection will be accepted. If 
      disabled, the connection will be rejected."
   DEFVAL     { enabled }
::= { lpFiSmtProvEntry 7 }

lpFiUseThruBa OBJECT-TYPE
   SYNTAX     INTEGER  {
                 enabled(1),
                 disabled(2) }
   ACCESS     read-write
   STATUS     mandatory
   DESCRIPTION
     "The useThruBa attribute is used to configure the requested path of the 
      associated station. If enabled, only the secondary preferred path is 
      permitted. If disabled, only the primary preferred path is permitted."
   DEFVAL     { disabled }
::= { lpFiSmtProvEntry 8 }

lpFiNeighborNotifyInterval OBJECT-TYPE
   SYNTAX     Unsigned32 (2..30)
   ACCESS     read-write
   STATUS     mandatory
   DESCRIPTION
     "The neighborNotifyInterval attribute contains the amount of time, 
      expressed in seconds, between neighbor notification frames."
   DEFVAL     { 30 }
::= { lpFiSmtProvEntry 10 }

lpFiStatusReportPolicy OBJECT-TYPE
   SYNTAX     INTEGER  {
                 true(1),
                 false(2) }
   ACCESS     read-write
   STATUS     mandatory
   DESCRIPTION
     "The statusReportPolicy attribute indicates whether or not the station will 
      generate status reporting frames for its implemented events and 
      conditions. If true, the station will generate the status frames. If false, 
      the station will not generate the status frames."
   DEFVAL     { true }
::= { lpFiSmtProvEntry 11 }

lpFiTraceMaxExpirationTimer OBJECT-TYPE
   SYNTAX     FddiTimeMilli (0..1000000)
   ACCESS     read-write
   STATUS     mandatory
   DESCRIPTION
     "The traceMaxExpirationTimer attribute is used to configure the 
      maximum propagation time, expressed in milliseconds, for a trace on a 
      FDDI topology. This value places a lower bound on the detection time 
      for an unrecovered ring."
   DEFVAL     { 7000 }
::= { lpFiSmtProvEntry 12 }

lpFiApplicationFramerName OBJECT-TYPE
   SYNTAX     Link 
   ACCESS     read-write
   STATUS     mandatory
   DESCRIPTION
     "This attribute contains the component name of a Framer which is 
      associated with the Fddi component. This defines which 
      LanApplication/n Framer will be using this Fddi interface."
::= { lpFiSmtProvEntry 13 }

lpFiMacProvTable OBJECT-TYPE
   SYNTAX     SEQUENCE OF LpFiMacProvEntry
   ACCESS     not-accessible
   STATUS     mandatory
   DESCRIPTION
     "This group contains the provisionable MAC attributes of the Fddi 
      component."
::= { lpFi 13 }

lpFiMacProvEntry OBJECT-TYPE
   SYNTAX     LpFiMacProvEntry
   ACCESS     not-accessible
   STATUS     mandatory
   DESCRIPTION
     "An entry in the lpFiMacProvTable."
   INDEX {
      lpIndex,
      lpFiIndex }
::= { lpFiMacProvTable 1 }

LpFiMacProvEntry ::= SEQUENCE {
   lpFiTokenRequestTimer
      FddiTimeNano,
   lpFiTokenMaxTimer
      FddiTimeNano,
   lpFiValidTransmissionTimer
      FddiTimeNano }

lpFiTokenRequestTimer OBJECT-TYPE
   SYNTAX     FddiTimeNano (20480..1340000000)
   ACCESS     read-write
   STATUS     mandatory
   DESCRIPTION
     "The tokenRequestTimer value contains the token request value assigned 
      to the associated medium access controller (MAC).
      
      Warning:
      Changes to this attribute can have adverse effects on the performance of 
      the FDDI ring. Therefore it is recommended that this parameter only be 
      modified by personnel with a thorough understanding of the 
      consequences that may result from changes to this attribute."
   DEFVAL     { 165290000 }
::= { lpFiMacProvEntry 1 }

lpFiTokenMaxTimer OBJECT-TYPE
   SYNTAX     FddiTimeNano (40960..1342200000)
   ACCESS     read-write
   STATUS     mandatory
   DESCRIPTION
     "The tokenMaxTimer value is the maximum timer value the negotiated 
      token rotation time may assume.
      
      Warning:
      Changes to this attribute can have adverse effects on the performance of 
      the FDDI ring. Therefore it is recommended that this parameter only be 
      modified by personnel with a thorough understanding of the 
      consequences that may result from changes to this attribute."
   DEFVAL     { 167770000 }
::= { lpFiMacProvEntry 2 }

lpFiValidTransmissionTimer OBJECT-TYPE
   SYNTAX     FddiTimeNano (40960..1342200000)
   ACCESS     read-write
   STATUS     mandatory
   DESCRIPTION
     "The validTransmissionTimer (Tvx) value specifies the amount of time 
      required for a valid transmission. The station must receive a valid 
      transmission once every Tvx. 
      
      Warning:
      Changes to this attribute can have adverse effects on the performance of 
      the FDDI ring. Therefore it is recommended that this parameter only be 
      modified by personnel with a thorough understanding of the 
      consequences that may result from changes to this attribute."
   DEFVAL     { 2621400 }
::= { lpFiMacProvEntry 3 }

lpFiAdminInfoTable OBJECT-TYPE
   SYNTAX     SEQUENCE OF LpFiAdminInfoEntry
   ACCESS     not-accessible
   STATUS     mandatory
   DESCRIPTION
     "This group contains the attributes pertaining to the vendor of the 
      equipment."
::= { lpFi 14 }

lpFiAdminInfoEntry OBJECT-TYPE
   SYNTAX     LpFiAdminInfoEntry
   ACCESS     not-accessible
   STATUS     mandatory
   DESCRIPTION
     "An entry in the lpFiAdminInfoTable."
   INDEX {
      lpIndex,
      lpFiIndex }
::= { lpFiAdminInfoTable 1 }

LpFiAdminInfoEntry ::= SEQUENCE {
   lpFiVendor
      AsciiString,
   lpFiCommentText
      AsciiString }

lpFiVendor OBJECT-TYPE
   SYNTAX     AsciiString (SIZE (0..20))
   ACCESS     read-write
   STATUS     mandatory
   DESCRIPTION
     "This is the name of the vendor supplying the facility."
::= { lpFiAdminInfoEntry 1 }

lpFiCommentText OBJECT-TYPE
   SYNTAX     AsciiString (SIZE (0..60))
   ACCESS     read-write
   STATUS     mandatory
   DESCRIPTION
     "Any miscellaneous text about the facility."
::= { lpFiAdminInfoEntry 2 }

lpFiStateTable OBJECT-TYPE
   SYNTAX     SEQUENCE OF LpFiStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpFi 16 }

lpFiStateEntry OBJECT-TYPE
   SYNTAX     LpFiStateEntry
   ACCESS     not-accessible
   STATUS     mandatory
   DESCRIPTION
     "An entry in the lpFiStateTable."
   INDEX {
      lpIndex,
      lpFiIndex }
::= { lpFiStateTable 1 }

LpFiStateEntry ::= SEQUENCE {
   lpFiAdminState
      INTEGER,
   lpFiOperationalState
      INTEGER,
   lpFiUsageState
      INTEGER }

lpFiAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpFiStateEntry 1 }

lpFiOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpFiStateEntry 2 }

lpFiUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpFiStateEntry 3 }

lpFiOperStatusTable OBJECT-TYPE
   SYNTAX     SEQUENCE OF LpFiOperStatusEntry
   ACCESS     not-accessible
   STATUS     mandatory
   DESCRIPTION
     "This group includes the Operational Status attribute. This attribute 
      defines the current operational state of this component."
::= { lpFi 17 }

lpFiOperStatusEntry OBJECT-TYPE
   SYNTAX     LpFiOperStatusEntry
   ACCESS     not-accessible
   STATUS     mandatory
   DESCRIPTION
     "An entry in the lpFiOperStatusTable."
   INDEX {
      lpIndex,
      lpFiIndex }
::= { lpFiOperStatusTable 1 }

LpFiOperStatusEntry ::= SEQUENCE {
   lpFiSnmpOperStatus
      INTEGER }

lpFiSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpFiOperStatusEntry 1 }

lpFiSmtOperTable OBJECT-TYPE
   SYNTAX     SEQUENCE OF LpFiSmtOperEntry
   ACCESS     not-accessible
   STATUS     mandatory
   DESCRIPTION
     "This group contains the operational station management (SMT) 
      attributes of the Fddi component."
::= { lpFi 18 }

lpFiSmtOperEntry OBJECT-TYPE
   SYNTAX     LpFiSmtOperEntry
   ACCESS     not-accessible
   STATUS     mandatory
   DESCRIPTION
     "An entry in the lpFiSmtOperTable."
   INDEX {
      lpIndex,
      lpFiIndex }
::= { lpFiSmtOperTable 1 }

LpFiSmtOperEntry ::= SEQUENCE {
   lpFiVersion
      AsciiString,
   lpFiBypassPresent
      INTEGER,
   lpFiEcmState
      INTEGER,
   lpFiCfState
      INTEGER }

lpFiVersion OBJECT-TYPE
   SYNTAX     AsciiString (SIZE (0..32))
   ACCESS     read-only
   STATUS     mandatory
   DESCRIPTION
     "The version attribute contains a copy of the currently supported version 
      numbers of the management information base (MIB) and the station 
      management (SMT)."
::= { lpFiSmtOperEntry 1 }

lpFiBypassPresent OBJECT-TYPE
   SYNTAX     INTEGER  {
                 true(1),
                 false(2) }
   ACCESS     read-only
   STATUS     mandatory
   DESCRIPTION
     "The bypassPresent attribute indicates whether the optical bypass switch 
      is present on its AB port pair. If true, the optical bypass switch is 
      present. If false, it is not present."
::= { lpFiSmtOperEntry 14 }

lpFiEcmState OBJECT-TYPE
   SYNTAX     INTEGER  {
                 out(1),
                 in(2),
                 trace(3),
                 leave(4),
                 pathTest(5),
                 insert(6),
                 check(7),
                 deinsert(8) }
   ACCESS     read-only
   STATUS     mandatory
   DESCRIPTION
     "The ecmState, Entity Coordination Manager (ECM), state indicates the 
      current state of the ECM state machine."
::= { lpFiSmtOperEntry 15 }

lpFiCfState OBJECT-TYPE
   SYNTAX     INTEGER  {
                 isolated(1),
                 localA(2),
                 localB(3),
                 localAB(4),
                 localS(5),
                 wrapA(6),
                 wrapB(7),
                 wrapAB(8),
                 wrapS(9),
                 cWrapA(10),
                 cWrapB(11),
                 cWrapS(12),
                 thru(13) }
   ACCESS     read-only
   STATUS     mandatory
   DESCRIPTION
     "The cfState attribute indicates the current state of the configuration 
      management (CFM) state machine."
::= { lpFiSmtOperEntry 16 }

lpFiMacOperTable OBJECT-TYPE
   SYNTAX     SEQUENCE OF LpFiMacOperEntry
   ACCESS     not-accessible
   STATUS     mandatory
   DESCRIPTION
     "This group contains the operational Medium Access Controller (MAC) 
      attributes of the of the Fddi component."
::= { lpFi 19 }

lpFiMacOperEntry OBJECT-TYPE
   SYNTAX     LpFiMacOperEntry
   ACCESS     not-accessible
   STATUS     mandatory
   DESCRIPTION
     "An entry in the lpFiMacOperTable."
   INDEX {
      lpIndex,
      lpFiIndex }
::= { lpFiMacOperTable 1 }

LpFiMacOperEntry ::= SEQUENCE {
   lpFiRingLatency
      Gauge32,
   lpFiMacAddress
      FddiMACLongAddressType,
   lpFiUpstreamNeighbor
      FddiMACLongAddressType,
   lpFiDownstreamNeighbor
      FddiMACLongAddressType,
   lpFiOldUpstreamNeighbor
      FddiMACLongAddressType,
   lpFiOldDownstreamNeighbor
      FddiMACLongAddressType,
   lpFiDupAddressTest
      INTEGER,
   lpFiTokenNegotiatedTimer
      FddiTimeNano,
   lpFiFrameCounts
      Counter32,
   lpFiCopiedCounts
      Counter32,
   lpFiTransmitCounts
      Counter32,
   lpFiErrorCounts
      Counter32,
   lpFiLostCounts
      Counter32,
   lpFiRmtState
      INTEGER,
   lpFiFrameErrorFlag
      INTEGER }

lpFiRingLatency OBJECT-TYPE
   SYNTAX     Gauge32 (1280..1342000000)
   ACCESS     read-only
   STATUS     mandatory
   DESCRIPTION
     "The ringLatency attribute contains the measured ring latency of the ring 
      the station is attached to."
::= { lpFiMacOperEntry 1 }

lpFiMacAddress OBJECT-TYPE
   SYNTAX     FddiMACLongAddressType (SIZE (6))
   ACCESS     read-only
   STATUS     mandatory
   DESCRIPTION
     "The medium access controller (MAC) address is an address that is 
      recognized by only one station on the attached ring. The value of this 
      attribute is assigned by the system. This attribute is displayed in 
      canonical format. The non-canonical version of this address is indicated 
      in ncMacAddress."
::= { lpFiMacOperEntry 10 }

lpFiUpstreamNeighbor OBJECT-TYPE
   SYNTAX     FddiMACLongAddressType (SIZE (6))
   ACCESS     read-only
   STATUS     mandatory
   DESCRIPTION
     "The upstreamNeighbor attribute contains the MAC address associated 
      with the upstream neighbor station on the ring. This attribute is 
      displayed in canonical format. The non-canonical version of this address 
      is indicated in ncUpstreamNeighbor."
::= { lpFiMacOperEntry 11 }

lpFiDownstreamNeighbor OBJECT-TYPE
   SYNTAX     FddiMACLongAddressType (SIZE (6))
   ACCESS     read-only
   STATUS     mandatory
   DESCRIPTION
     "The downstreamNeighbor attribute contains the MAC address 
      associated with the downstream station on the ring. This attribute is 
      displayed in canonical format. The non-canonical version of this address 
      is indicated in ncDownstreamNeighbor."
::= { lpFiMacOperEntry 12 }

lpFiOldUpstreamNeighbor OBJECT-TYPE
   SYNTAX     FddiMACLongAddressType (SIZE (6))
   ACCESS     read-only
   STATUS     mandatory
   DESCRIPTION
     "The oldUpstreamNeighbor attribute contains the previous value of the 
      MAC address associated with the upstream station on the ring. This 
      attribute is displayed in canonical format. The non-canonical version of 
      this address is indicated in ncOldUpstreamNeighbor."
::= { lpFiMacOperEntry 13 }

lpFiOldDownstreamNeighbor OBJECT-TYPE
   SYNTAX     FddiMACLongAddressType (SIZE (6))
   ACCESS     read-only
   STATUS     mandatory
   DESCRIPTION
     "The oldDownstreamNeighbor attribute contains the previous value of 
      the MAC address associated with the downstream station on the ring. 
      This attribute is displayed in canonical format. The non-canonical 
      version of this address is indicated in ncOldDownstreamNeighbor."
::= { lpFiMacOperEntry 14 }

lpFiDupAddressTest OBJECT-TYPE
   SYNTAX     INTEGER  {
                 notDone(1),
                 pass(2),
                 fail(3) }
   ACCESS     read-only
   STATUS     mandatory
   DESCRIPTION
     "The dupAddressTest attribute indicates the condition results of the 
      duplicate address test. If notDone, the test has not been executed. If 
      pass, the test has successfully executed. If fail, the test has failed."
::= { lpFiMacOperEntry 15 }

lpFiTokenNegotiatedTimer OBJECT-TYPE
   SYNTAX     FddiTimeNano (80..1340000000)
   ACCESS     read-only
   STATUS     mandatory
   DESCRIPTION
     "The tokenNegotiatedTimer specifies the negotiated token rotation time."
   DEFVAL     { 167772000 }
::= { lpFiMacOperEntry 18 }

lpFiFrameCounts OBJECT-TYPE
   SYNTAX     Counter32 
   ACCESS     read-only
   STATUS     mandatory
   DESCRIPTION
     "The frameCounts attribute contains the number of frames that have been 
      received by the station. This counter will wrap around after it reaches its 
      maximum value."
::= { lpFiMacOperEntry 19 }

lpFiCopiedCounts OBJECT-TYPE
   SYNTAX     Counter32 
   ACCESS     read-only
   STATUS     mandatory
   DESCRIPTION
     "The copiedCounts attribute contains the number of frames successfully 
      copied into this station's receive buffers, not including MAC control 
      frames. This counter will wrap around after it reaches its maximum 
      value."
::= { lpFiMacOperEntry 20 }

lpFiTransmitCounts OBJECT-TYPE
   SYNTAX     Counter32 
   ACCESS     read-only
   STATUS     mandatory
   DESCRIPTION
     "The transmitCounts attribute contains the number of frames transmitted 
      by this station, not including MAC control frames. This counter will 
      wrap around after it reaches its maximum value."
::= { lpFiMacOperEntry 21 }

lpFiErrorCounts OBJECT-TYPE
   SYNTAX     Counter32 
   ACCESS     read-only
   STATUS     mandatory
   DESCRIPTION
     "The errorCounts attribute contains the number of error frames first 
      detected by this station. This counter will wrap around after it reaches its 
      maximum value."
::= { lpFiMacOperEntry 22 }

lpFiLostCounts OBJECT-TYPE
   SYNTAX     Counter32 
   ACCESS     read-only
   STATUS     mandatory
   DESCRIPTION
     "The lostCounts attribute contains the number of instances that the station 
      has detected a format error during frame reception such that the frame 
      was stripped. This counter will wrap around after it reaches its 
      maximum value."
::= { lpFiMacOperEntry 23 }

lpFiRmtState OBJECT-TYPE
   SYNTAX     INTEGER  {
                 isolated(1),
                 nonOp(2),
                 ringOp(3),
                 detect(4),
                 nonOpDup(5),
                 ringOpDup(6),
                 directed(7),
                 trace(8) }
   ACCESS     read-only
   STATUS     mandatory
   DESCRIPTION
     "The rmtState, ring management (RMT), state indicates the current state 
      of the RMT state machine."
::= { lpFiMacOperEntry 25 }

lpFiFrameErrorFlag OBJECT-TYPE
   SYNTAX     INTEGER  {
                 true(1),
                 false(2) }
   ACCESS     read-only
   STATUS     mandatory
   DESCRIPTION
     "The frameErrorFlag attribute indicates the MAC frame error condition 
      status. If true, a MAC frame error is present. If false, a MAC frame 
      error condition is not present."
::= { lpFiMacOperEntry 28 }

lpFiMacCOperTable OBJECT-TYPE
   SYNTAX     SEQUENCE OF LpFiMacCOperEntry
   ACCESS     not-accessible
   STATUS     mandatory
   DESCRIPTION
     "This group contains the operational attributes of the Medium Access 
      Controller (MAC) Counters Table of the Fddi component."
::= { lpFi 20 }

lpFiMacCOperEntry OBJECT-TYPE
   SYNTAX     LpFiMacCOperEntry
   ACCESS     not-accessible
   STATUS     mandatory
   DESCRIPTION
     "An entry in the lpFiMacCOperTable."
   INDEX {
      lpIndex,
      lpFiIndex }
::= { lpFiMacCOperTable 1 }

LpFiMacCOperEntry ::= SEQUENCE {
   lpFiTokenCounts
      Counter32,
   lpFiTvxExpiredCounts
      Counter32,
   lpFiNotCopiedCounts
      Counter32,
   lpFiLateCounts
      Counter32,
   lpFiRingOpCounts
      Counter32 }

lpFiTokenCounts OBJECT-TYPE
   SYNTAX     Counter32 
   ACCESS     read-only
   STATUS     mandatory
   DESCRIPTION
     "The tokenCounts attribute contains the number of times the station has 
      received a token. This counter will wrap around after it reaches its 
      maximum value."
::= { lpFiMacCOperEntry 1 }

lpFiTvxExpiredCounts OBJECT-TYPE
   SYNTAX     Counter32 
   ACCESS     read-only
   STATUS     mandatory
   DESCRIPTION
     "The tvxExpiredCounts, Transmission Valid eXpired (TVX), attribute 
      contains the number of times that TVX timer has expired. This counter 
      may increment as stations go on and off the ring. A rapidly increasing 
      value may indicate a problem. This counter will wrap around after it 
      reaches its maximum value."
::= { lpFiMacCOperEntry 2 }

lpFiNotCopiedCounts OBJECT-TYPE
   SYNTAX     Counter32 
   ACCESS     read-only
   STATUS     mandatory
   DESCRIPTION
     "The notCopiedCounts attribute contains the number of times that the 
      station has detected a frame addressed to itself but did not copy it due to 
      local buffer congestion. This counter will wrap around after it reaches its 
      maximum value."
::= { lpFiMacCOperEntry 3 }

lpFiLateCounts OBJECT-TYPE
   SYNTAX     Counter32 
   ACCESS     read-only
   STATUS     mandatory
   DESCRIPTION
     "The lateCounts attribute contains the number of token rotation time 
      (TRT) expirations since the station was reset or a token was received. 
      This counter may increment as stations go on and off the ring. A rapidly 
      increasing value may indicate a problem. This counter will wrap around 
      after it reaches its maximum value."
::= { lpFiMacCOperEntry 4 }

lpFiRingOpCounts OBJECT-TYPE
   SYNTAX     Counter32 
   ACCESS     read-only
   STATUS     mandatory
   DESCRIPTION
     "The ringOpCounts attribute contains the number of times the station has 
      made the transition from the ring not operational state to the ring 
      operational state."
::= { lpFiMacCOperEntry 5 }

lpFiNcMacOperTable OBJECT-TYPE
   SYNTAX     SEQUENCE OF LpFiNcMacOperEntry
   ACCESS     not-accessible
   STATUS     mandatory
   DESCRIPTION
     "This group contains the operational attributes of the Fddi component 
      related to non-canonical MAC addresses."
::= { lpFi 26 }

lpFiNcMacOperEntry OBJECT-TYPE
   SYNTAX     LpFiNcMacOperEntry
   ACCESS     not-accessible
   STATUS     mandatory
   DESCRIPTION
     "An entry in the lpFiNcMacOperTable."
   INDEX {
      lpIndex,
      lpFiIndex }
::= { lpFiNcMacOperTable 1 }

LpFiNcMacOperEntry ::= SEQUENCE {
   lpFiNcMacAddress
      MacAddress,
   lpFiNcUpstreamNeighbor
      MacAddress,
   lpFiNcDownstreamNeighbor
      MacAddress,
   lpFiNcOldUpstreamNeighbor
      MacAddress,
   lpFiNcOldDownstreamNeighbor
      MacAddress }

lpFiNcMacAddress OBJECT-TYPE
   SYNTAX     MacAddress (SIZE (6))
   ACCESS     read-only
   STATUS     mandatory
   DESCRIPTION
     "The medium access controller (MAC) address is an address that is 
      recognized by only one station on the attached ring. The value of this 
      attribute is assigned by the system. This attribute is displayed in non-
      canonical format. The canonical version of this address is indicated in 
      macAddress."
::= { lpFiNcMacOperEntry 1 }

lpFiNcUpstreamNeighbor OBJECT-TYPE
   SYNTAX     MacAddress (SIZE (6))
   ACCESS     read-only
   STATUS     mandatory
   DESCRIPTION
     "The ncUpstreamNeighbor attribute contains the MAC address 
      associated with the upstream neighbor station on the ring. This attribute 
      is displayed in non-canonical format. The canonical version of this 
      address is indicated in upstreamNeighbor."
::= { lpFiNcMacOperEntry 2 }

lpFiNcDownstreamNeighbor OBJECT-TYPE
   SYNTAX     MacAddress (SIZE (6))
   ACCESS     read-only
   STATUS     mandatory
   DESCRIPTION
     "The ncDownstreamNeighbor attribute contains the MAC address 
      associated with the downstream station on the ring. This attribute is 
      displayed in non-canonical format. The canonical version of this address 
      is indicated in downstreamNeighbor"
::= { lpFiNcMacOperEntry 3 }

lpFiNcOldUpstreamNeighbor OBJECT-TYPE
   SYNTAX     MacAddress (SIZE (6))
   ACCESS     read-only
   STATUS     mandatory
   DESCRIPTION
     "The ncOldUpstreamNeighbor attribute contains the previous value of the 
      MAC address associated with the upstream station on the ring. This 
      attribute is displayed in non-canonical format. The canonical version of 
      this address is indicated in oldUpstreamNeighbor."
::= { lpFiNcMacOperEntry 4 }

lpFiNcOldDownstreamNeighbor OBJECT-TYPE
   SYNTAX     MacAddress (SIZE (6))
   ACCESS     read-only
   STATUS     mandatory
   DESCRIPTION
     "The ncOldDownstreamNeighbor attribute contains the previous value of 
      the MAC address associated with the downstream station on the ring. 
      This attribute is displayed in non-canonical format. The canonical 
      version of this address is indicated in oldDownstreamNeighbor."
::= { lpFiNcMacOperEntry 5 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

lpFiLt OBJECT IDENTIFIER ::= { lpFi 2 }



lpFiLtRowStatusTable OBJECT-TYPE
   SYNTAX     SEQUENCE OF LpFiLtRowStatusEntry
   ACCESS     not-accessible
   STATUS     mandatory
   DESCRIPTION
     "This entry controls the addition and deletion of 
      lpFiLt components."
::= { lpFiLt 1 }

lpFiLtRowStatusEntry OBJECT-TYPE
   SYNTAX     LpFiLtRowStatusEntry
   ACCESS     not-accessible
   STATUS     mandatory
   DESCRIPTION
     "A single entry in the table represents a single 
      lpFiLt component."
   INDEX {
      lpIndex,
      lpFiIndex,
      lpFiLtIndex }
::= { lpFiLtRowStatusTable 1 }

LpFiLtRowStatusEntry ::= SEQUENCE {
   lpFiLtRowStatus
      RowStatus,
   lpFiLtComponentName
      DisplayString,
   lpFiLtStorageType
      StorageType,
   lpFiLtIndex
      NonReplicated }

lpFiLtRowStatus OBJECT-TYPE
   SYNTAX     RowStatus 
   ACCESS     read-only
   STATUS     mandatory
   DESCRIPTION
     "This variable is used as the basis for SNMP naming of
      lpFiLt components.
      These components cannot be added nor deleted."
::= { lpFiLtRowStatusEntry 1 }

lpFiLtComponentName OBJECT-TYPE
   SYNTAX     DisplayString 
   ACCESS     read-only
   STATUS     mandatory
   DESCRIPTION
     "This variable provides the component's string name for
      use with the ASCII Console Interface"
::= { lpFiLtRowStatusEntry 2 }

lpFiLtStorageType OBJECT-TYPE
   SYNTAX     StorageType 
   ACCESS     read-only
   STATUS     mandatory
   DESCRIPTION
     "This variable represents the storage type value for the
      lpFiLt tables."
::= { lpFiLtRowStatusEntry 4 }

lpFiLtIndex OBJECT-TYPE
   SYNTAX     NonReplicated 
   ACCESS     not-accessible
   STATUS     mandatory
   DESCRIPTION
     "This variable represents the index for the lpFiLt tables."
::= { lpFiLtRowStatusEntry 10 }

lpFiLtTopTable OBJECT-TYPE
   SYNTAX     SEQUENCE OF LpFiLtTopEntry
   ACCESS     not-accessible
   STATUS     mandatory
   DESCRIPTION
     "This group contains the operational data for the LanTest component 
      and its subcomponents."
::= { lpFiLt 20 }

lpFiLtTopEntry OBJECT-TYPE
   SYNTAX     LpFiLtTopEntry
   ACCESS     not-accessible
   STATUS     mandatory
   DESCRIPTION
     "An entry in the lpFiLtTopTable."
   INDEX {
      lpIndex,
      lpFiIndex,
      lpFiLtIndex }
::= { lpFiLtTopTable 1 }

LpFiLtTopEntry ::= SEQUENCE {
   lpFiLtTData
      AsciiString }

lpFiLtTData OBJECT-TYPE
   SYNTAX     AsciiString (SIZE (0..255))
   ACCESS     read-write
   STATUS     mandatory
   DESCRIPTION
     "This attribute is used to display and set attributes."
::= { lpFiLtTopEntry 1 }


-- This component compares frames received from the hardware and 
-- emulator during testing.

lpFiLtFrmCmp OBJECT IDENTIFIER ::= { lpFiLt 2 }



lpFiLtFrmCmpRowStatusTable OBJECT-TYPE
   SYNTAX     SEQUENCE OF LpFiLtFrmCmpRowStatusEntry
   ACCESS     not-accessible
   STATUS     mandatory
   DESCRIPTION
     "This entry controls the addition and deletion of 
      lpFiLtFrmCmp components."
::= { lpFiLtFrmCmp 1 }

lpFiLtFrmCmpRowStatusEntry OBJECT-TYPE
   SYNTAX     LpFiLtFrmCmpRowStatusEntry
   ACCESS     not-accessible
   STATUS     mandatory
   DESCRIPTION
     "A single entry in the table represents a single 
      lpFiLtFrmCmp component."
   INDEX {
      lpIndex,
      lpFiIndex,
      lpFiLtIndex,
      lpFiLtFrmCmpIndex }
::= { lpFiLtFrmCmpRowStatusTable 1 }

LpFiLtFrmCmpRowStatusEntry ::= SEQUENCE {
   lpFiLtFrmCmpRowStatus
      RowStatus,
   lpFiLtFrmCmpComponentName
      DisplayString,
   lpFiLtFrmCmpStorageType
      StorageType,
   lpFiLtFrmCmpIndex
      NonReplicated }

lpFiLtFrmCmpRowStatus OBJECT-TYPE
   SYNTAX     RowStatus 
   ACCESS     read-only
   STATUS     mandatory
   DESCRIPTION
     "This variable is used as the basis for SNMP naming of
      lpFiLtFrmCmp components.
      These components cannot be added nor deleted."
::= { lpFiLtFrmCmpRowStatusEntry 1 }

lpFiLtFrmCmpComponentName OBJECT-TYPE
   SYNTAX     DisplayString 
   ACCESS     read-only
   STATUS     mandatory
   DESCRIPTION
     "This variable provides the component's string name for
      use with the ASCII Console Interface"
::= { lpFiLtFrmCmpRowStatusEntry 2 }

lpFiLtFrmCmpStorageType OBJECT-TYPE
   SYNTAX     StorageType 
   ACCESS     read-only
   STATUS     mandatory
   DESCRIPTION
     "This variable represents the storage type value for the
      lpFiLtFrmCmp tables."
::= { lpFiLtFrmCmpRowStatusEntry 4 }

lpFiLtFrmCmpIndex OBJECT-TYPE
   SYNTAX     NonReplicated 
   ACCESS     not-accessible
   STATUS     mandatory
   DESCRIPTION
     "This variable represents the index for the lpFiLtFrmCmp tables."
::= { lpFiLtFrmCmpRowStatusEntry 10 }

lpFiLtFrmCmpTopTable OBJECT-TYPE
   SYNTAX     SEQUENCE OF LpFiLtFrmCmpTopEntry
   ACCESS     not-accessible
   STATUS     mandatory
   DESCRIPTION
     "This group contains the operational data for the LanTest component 
      and its subcomponents."
::= { lpFiLtFrmCmp 10 }

lpFiLtFrmCmpTopEntry OBJECT-TYPE
   SYNTAX     LpFiLtFrmCmpTopEntry
   ACCESS     not-accessible
   STATUS     mandatory
   DESCRIPTION
     "An entry in the lpFiLtFrmCmpTopTable."
   INDEX {
      lpIndex,
      lpFiIndex,
      lpFiLtIndex,
      lpFiLtFrmCmpIndex }
::= { lpFiLtFrmCmpTopTable 1 }

LpFiLtFrmCmpTopEntry ::= SEQUENCE {
   lpFiLtFrmCmpTData
      AsciiString }

lpFiLtFrmCmpTData OBJECT-TYPE
   SYNTAX     AsciiString (SIZE (0..255))
   ACCESS     read-write
   STATUS     mandatory
   DESCRIPTION
     "This attribute is used to display and set attributes."
::= { lpFiLtFrmCmpTopEntry 1 }


-- This component receives its input from FrameBuild and places it 
-- upon the hardware which sends it to the appropriate emulator.

lpFiLtFrmCpy OBJECT IDENTIFIER ::= { lpFiLt 3 }



lpFiLtFrmCpyRowStatusTable OBJECT-TYPE
   SYNTAX     SEQUENCE OF LpFiLtFrmCpyRowStatusEntry
   ACCESS     not-accessible
   STATUS     mandatory
   DESCRIPTION
     "This entry controls the addition and deletion of 
      lpFiLtFrmCpy components."
::= { lpFiLtFrmCpy 1 }

lpFiLtFrmCpyRowStatusEntry OBJECT-TYPE
   SYNTAX     LpFiLtFrmCpyRowStatusEntry
   ACCESS     not-accessible
   STATUS     mandatory
   DESCRIPTION
     "A single entry in the table represents a single 
      lpFiLtFrmCpy component."
   INDEX {
      lpIndex,
      lpFiIndex,
      lpFiLtIndex,
      lpFiLtFrmCpyIndex }
::= { lpFiLtFrmCpyRowStatusTable 1 }

LpFiLtFrmCpyRowStatusEntry ::= SEQUENCE {
   lpFiLtFrmCpyRowStatus
      RowStatus,
   lpFiLtFrmCpyComponentName
      DisplayString,
   lpFiLtFrmCpyStorageType
      StorageType,
   lpFiLtFrmCpyIndex
      NonReplicated }

lpFiLtFrmCpyRowStatus OBJECT-TYPE
   SYNTAX     RowStatus 
   ACCESS     read-only
   STATUS     mandatory
   DESCRIPTION
     "This variable is used as the basis for SNMP naming of
      lpFiLtFrmCpy components.
      These components cannot be added nor deleted."
::= { lpFiLtFrmCpyRowStatusEntry 1 }

lpFiLtFrmCpyComponentName OBJECT-TYPE
   SYNTAX     DisplayString 
   ACCESS     read-only
   STATUS     mandatory
   DESCRIPTION
     "This variable provides the component's string name for
      use with the ASCII Console Interface"
::= { lpFiLtFrmCpyRowStatusEntry 2 }

lpFiLtFrmCpyStorageType OBJECT-TYPE
   SYNTAX     StorageType 
   ACCESS     read-only
   STATUS     mandatory
   DESCRIPTION
     "This variable represents the storage type value for the
      lpFiLtFrmCpy tables."
::= { lpFiLtFrmCpyRowStatusEntry 4 }

lpFiLtFrmCpyIndex OBJECT-TYPE
   SYNTAX     NonReplicated 
   ACCESS     not-accessible
   STATUS     mandatory
   DESCRIPTION
     "This variable represents the index for the lpFiLtFrmCpy tables."
::= { lpFiLtFrmCpyRowStatusEntry 10 }

lpFiLtFrmCpyTopTable OBJECT-TYPE
   SYNTAX     SEQUENCE OF LpFiLtFrmCpyTopEntry
   ACCESS     not-accessible
   STATUS     mandatory
   DESCRIPTION
     "This group contains the operational data for the LanTest component 
      and its subcomponents."
::= { lpFiLtFrmCpy 10 }

lpFiLtFrmCpyTopEntry OBJECT-TYPE
   SYNTAX     LpFiLtFrmCpyTopEntry
   ACCESS     not-accessible
   STATUS     mandatory
   DESCRIPTION
     "An entry in the lpFiLtFrmCpyTopTable."
   INDEX {
      lpIndex,
      lpFiIndex,
      lpFiLtIndex,
      lpFiLtFrmCpyIndex }
::= { lpFiLtFrmCpyTopTable 1 }

LpFiLtFrmCpyTopEntry ::= SEQUENCE {
   lpFiLtFrmCpyTData
      AsciiString }

lpFiLtFrmCpyTData OBJECT-TYPE
   SYNTAX     AsciiString (SIZE (0..255))
   ACCESS     read-write
   STATUS     mandatory
   DESCRIPTION
     "This attribute is used to display and set attributes."
::= { lpFiLtFrmCpyTopEntry 1 }


-- This component controls the emulator and hardware to ensure 
-- frames output from each will match in FrameCompare.

lpFiLtPrtCfg OBJECT IDENTIFIER ::= { lpFiLt 4 }



lpFiLtPrtCfgRowStatusTable OBJECT-TYPE
   SYNTAX     SEQUENCE OF LpFiLtPrtCfgRowStatusEntry
   ACCESS     not-accessible
   STATUS     mandatory
   DESCRIPTION
     "This entry controls the addition and deletion of 
      lpFiLtPrtCfg components."
::= { lpFiLtPrtCfg 1 }

lpFiLtPrtCfgRowStatusEntry OBJECT-TYPE
   SYNTAX     LpFiLtPrtCfgRowStatusEntry
   ACCESS     not-accessible
   STATUS     mandatory
   DESCRIPTION
     "A single entry in the table represents a single 
      lpFiLtPrtCfg component."
   INDEX {
      lpIndex,
      lpFiIndex,
      lpFiLtIndex,
      lpFiLtPrtCfgIndex }
::= { lpFiLtPrtCfgRowStatusTable 1 }

LpFiLtPrtCfgRowStatusEntry ::= SEQUENCE {
   lpFiLtPrtCfgRowStatus
      RowStatus,
   lpFiLtPrtCfgComponentName
      DisplayString,
   lpFiLtPrtCfgStorageType
      StorageType,
   lpFiLtPrtCfgIndex
      NonReplicated }

lpFiLtPrtCfgRowStatus OBJECT-TYPE
   SYNTAX     RowStatus 
   ACCESS     read-only
   STATUS     mandatory
   DESCRIPTION
     "This variable is used as the basis for SNMP naming of
      lpFiLtPrtCfg components.
      These components cannot be added nor deleted."
::= { lpFiLtPrtCfgRowStatusEntry 1 }

lpFiLtPrtCfgComponentName OBJECT-TYPE
   SYNTAX     DisplayString 
   ACCESS     read-only
   STATUS     mandatory
   DESCRIPTION
     "This variable provides the component's string name for
      use with the ASCII Console Interface"
::= { lpFiLtPrtCfgRowStatusEntry 2 }

lpFiLtPrtCfgStorageType OBJECT-TYPE
   SYNTAX     StorageType 
   ACCESS     read-only
   STATUS     mandatory
   DESCRIPTION
     "This variable represents the storage type value for the
      lpFiLtPrtCfg tables."
::= { lpFiLtPrtCfgRowStatusEntry 4 }

lpFiLtPrtCfgIndex OBJECT-TYPE
   SYNTAX     NonReplicated 
   ACCESS     not-accessible
   STATUS     mandatory
   DESCRIPTION
     "This variable represents the index for the lpFiLtPrtCfg tables."
::= { lpFiLtPrtCfgRowStatusEntry 10 }

lpFiLtPrtCfgTopTable OBJECT-TYPE
   SYNTAX     SEQUENCE OF LpFiLtPrtCfgTopEntry
   ACCESS     not-accessible
   STATUS     mandatory
   DESCRIPTION
     "This group contains the operational data for the LanTest component 
      and its subcomponents."
::= { lpFiLtPrtCfg 10 }

lpFiLtPrtCfgTopEntry OBJECT-TYPE
   SYNTAX     LpFiLtPrtCfgTopEntry
   ACCESS     not-accessible
   STATUS     mandatory
   DESCRIPTION
     "An entry in the lpFiLtPrtCfgTopTable."
   INDEX {
      lpIndex,
      lpFiIndex,
      lpFiLtIndex,
      lpFiLtPrtCfgIndex }
::= { lpFiLtPrtCfgTopTable 1 }

LpFiLtPrtCfgTopEntry ::= SEQUENCE {
   lpFiLtPrtCfgTData
      AsciiString }

lpFiLtPrtCfgTData OBJECT-TYPE
   SYNTAX     AsciiString (SIZE (0..255))
   ACCESS     read-write
   STATUS     mandatory
   DESCRIPTION
     "This attribute is used to display and set attributes."
::= { lpFiLtPrtCfgTopEntry 1 }


-- LanTest Framebuild
-- This component controls the building of all frames built and sent by 
-- the LanTest component. Each component under FrameBuild builds 
-- a portion of a packet or frame.

lpFiLtFb OBJECT IDENTIFIER ::= { lpFiLt 5 }



lpFiLtFbRowStatusTable OBJECT-TYPE
   SYNTAX     SEQUENCE OF LpFiLtFbRowStatusEntry
   ACCESS     not-accessible
   STATUS     mandatory
   DESCRIPTION
     "This entry controls the addition and deletion of 
      lpFiLtFb components."
::= { lpFiLtFb 1 }

lpFiLtFbRowStatusEntry OBJECT-TYPE
   SYNTAX     LpFiLtFbRowStatusEntry
   ACCESS     not-accessible
   STATUS     mandatory
   DESCRIPTION
     "A single entry in the table represents a single 
      lpFiLtFb component."
   INDEX {
      lpIndex,
      lpFiIndex,
      lpFiLtIndex,
      lpFiLtFbIndex }
::= { lpFiLtFbRowStatusTable 1 }

LpFiLtFbRowStatusEntry ::= SEQUENCE {
   lpFiLtFbRowStatus
      RowStatus,
   lpFiLtFbComponentName
      DisplayString,
   lpFiLtFbStorageType
      StorageType,
   lpFiLtFbIndex
      NonReplicated }

lpFiLtFbRowStatus OBJECT-TYPE
   SYNTAX     RowStatus 
   ACCESS     read-only
   STATUS     mandatory
   DESCRIPTION
     "This variable is used as the basis for SNMP naming of
      lpFiLtFb components.
      These components cannot be added nor deleted."
::= { lpFiLtFbRowStatusEntry 1 }

lpFiLtFbComponentName OBJECT-TYPE
   SYNTAX     DisplayString 
   ACCESS     read-only
   STATUS     mandatory
   DESCRIPTION
     "This variable provides the component's string name for
      use with the ASCII Console Interface"
::= { lpFiLtFbRowStatusEntry 2 }

lpFiLtFbStorageType OBJECT-TYPE
   SYNTAX     StorageType 
   ACCESS     read-only
   STATUS     mandatory
   DESCRIPTION
     "This variable represents the storage type value for the
      lpFiLtFb tables."
::= { lpFiLtFbRowStatusEntry 4 }

lpFiLtFbIndex OBJECT-TYPE
   SYNTAX     NonReplicated 
   ACCESS     not-accessible
   STATUS     mandatory
   DESCRIPTION
     "This variable represents the index for the lpFiLtFb tables."
::= { lpFiLtFbRowStatusEntry 10 }

lpFiLtFbTopTable OBJECT-TYPE
   SYNTAX     SEQUENCE OF LpFiLtFbTopEntry
   ACCESS     not-accessible
   STATUS     mandatory
   DESCRIPTION
     "This group contains the operational data for the LanTest component 
      and its subcomponents."
::= { lpFiLtFb 20 }

lpFiLtFbTopEntry OBJECT-TYPE
   SYNTAX     LpFiLtFbTopEntry
   ACCESS     not-accessible
   STATUS     mandatory
   DESCRIPTION
     "An entry in the lpFiLtFbTopTable."
   INDEX {
      lpIndex,
      lpFiIndex,
      lpFiLtIndex,
      lpFiLtFbIndex }
::= { lpFiLtFbTopTable 1 }

LpFiLtFbTopEntry ::= SEQUENCE {
   lpFiLtFbTData
      AsciiString }

lpFiLtFbTData OBJECT-TYPE
   SYNTAX     AsciiString (SIZE (0..255))
   ACCESS     read-write
   STATUS     mandatory
   DESCRIPTION
     "This attribute is used to display and set attributes."
::= { lpFiLtFbTopEntry 1 }


-- LanTest TransmitInfo
-- This component builds a transmit header which is attached to all 
-- frames transmitted on LAN interfaces.

lpFiLtFbTxInfo OBJECT IDENTIFIER ::= { lpFiLtFb 2 }



lpFiLtFbTxInfoRowStatusTable OBJECT-TYPE
   SYNTAX     SEQUENCE OF LpFiLtFbTxInfoRowStatusEntry
   ACCESS     not-accessible
   STATUS     mandatory
   DESCRIPTION
     "This entry controls the addition and deletion of 
      lpFiLtFbTxInfo components."
::= { lpFiLtFbTxInfo 1 }

lpFiLtFbTxInfoRowStatusEntry OBJECT-TYPE
   SYNTAX     LpFiLtFbTxInfoRowStatusEntry
   ACCESS     not-accessible
   STATUS     mandatory
   DESCRIPTION
     "A single entry in the table represents a single 
      lpFiLtFbTxInfo component."
   INDEX {
      lpIndex,
      lpFiIndex,
      lpFiLtIndex,
      lpFiLtFbIndex,
      lpFiLtFbTxInfoIndex }
::= { lpFiLtFbTxInfoRowStatusTable 1 }

LpFiLtFbTxInfoRowStatusEntry ::= SEQUENCE {
   lpFiLtFbTxInfoRowStatus
      RowStatus,
   lpFiLtFbTxInfoComponentName
      DisplayString,
   lpFiLtFbTxInfoStorageType
      StorageType,
   lpFiLtFbTxInfoIndex
      NonReplicated }

lpFiLtFbTxInfoRowStatus OBJECT-TYPE
   SYNTAX     RowStatus 
   ACCESS     read-only
   STATUS     mandatory
   DESCRIPTION
     "This variable is used as the basis for SNMP naming of
      lpFiLtFbTxInfo components.
      These components cannot be added nor deleted."
::= { lpFiLtFbTxInfoRowStatusEntry 1 }

lpFiLtFbTxInfoComponentName OBJECT-TYPE
   SYNTAX     DisplayString 
   ACCESS     read-only
   STATUS     mandatory
   DESCRIPTION
     "This variable provides the component's string name for
      use with the ASCII Console Interface"
::= { lpFiLtFbTxInfoRowStatusEntry 2 }

lpFiLtFbTxInfoStorageType OBJECT-TYPE
   SYNTAX     StorageType 
   ACCESS     read-only
   STATUS     mandatory
   DESCRIPTION
     "This variable represents the storage type value for the
      lpFiLtFbTxInfo tables."
::= { lpFiLtFbTxInfoRowStatusEntry 4 }

lpFiLtFbTxInfoIndex OBJECT-TYPE
   SYNTAX     NonReplicated 
   ACCESS     not-accessible
   STATUS     mandatory
   DESCRIPTION
     "This variable represents the index for the lpFiLtFbTxInfo tables."
::= { lpFiLtFbTxInfoRowStatusEntry 10 }

lpFiLtFbTxInfoTopTable OBJECT-TYPE
   SYNTAX     SEQUENCE OF LpFiLtFbTxInfoTopEntry
   ACCESS     not-accessible
   STATUS     mandatory
   DESCRIPTION
     "This group contains the operational data for the LanTest component 
      and its subcomponents."
::= { lpFiLtFbTxInfo 10 }

lpFiLtFbTxInfoTopEntry OBJECT-TYPE
   SYNTAX     LpFiLtFbTxInfoTopEntry
   ACCESS     not-accessible
   STATUS     mandatory
   DESCRIPTION
     "An entry in the lpFiLtFbTxInfoTopTable."
   INDEX {
      lpIndex,
      lpFiIndex,
      lpFiLtIndex,
      lpFiLtFbIndex,
      lpFiLtFbTxInfoIndex }
::= { lpFiLtFbTxInfoTopTable 1 }

LpFiLtFbTxInfoTopEntry ::= SEQUENCE {
   lpFiLtFbTxInfoTData
      AsciiString }

lpFiLtFbTxInfoTData OBJECT-TYPE
   SYNTAX     AsciiString (SIZE (0..255))
   ACCESS     read-write
   STATUS     mandatory
   DESCRIPTION
     "This attribute is used to display and set attributes."
::= { lpFiLtFbTxInfoTopEntry 1 }


-- LanTest FddiMac
-- This component builds an FDDI MAC header which is attached to 
-- all FDDI frames.

lpFiLtFbFddiMac OBJECT IDENTIFIER ::= { lpFiLtFb 3 }



lpFiLtFbFddiMacRowStatusTable OBJECT-TYPE
   SYNTAX     SEQUENCE OF LpFiLtFbFddiMacRowStatusEntry
   ACCESS     not-accessible
   STATUS     mandatory
   DESCRIPTION
     "This entry controls the addition and deletion of 
      lpFiLtFbFddiMac components."
::= { lpFiLtFbFddiMac 1 }

lpFiLtFbFddiMacRowStatusEntry OBJECT-TYPE
   SYNTAX     LpFiLtFbFddiMacRowStatusEntry
   ACCESS     not-accessible
   STATUS     mandatory
   DESCRIPTION
     "A single entry in the table represents a single 
      lpFiLtFbFddiMac component."
   INDEX {
      lpIndex,
      lpFiIndex,
      lpFiLtIndex,
      lpFiLtFbIndex,
      lpFiLtFbFddiMacIndex }
::= { lpFiLtFbFddiMacRowStatusTable 1 }

LpFiLtFbFddiMacRowStatusEntry ::= SEQUENCE {
   lpFiLtFbFddiMacRowStatus
      RowStatus,
   lpFiLtFbFddiMacComponentName
      DisplayString,
   lpFiLtFbFddiMacStorageType
      StorageType,
   lpFiLtFbFddiMacIndex
      NonReplicated }

lpFiLtFbFddiMacRowStatus OBJECT-TYPE
   SYNTAX     RowStatus 
   ACCESS     read-only
   STATUS     mandatory
   DESCRIPTION
     "This variable is used as the basis for SNMP naming of
      lpFiLtFbFddiMac components.
      These components cannot be added nor deleted."
::= { lpFiLtFbFddiMacRowStatusEntry 1 }

lpFiLtFbFddiMacComponentName OBJECT-TYPE
   SYNTAX     DisplayString 
   ACCESS     read-only
   STATUS     mandatory
   DESCRIPTION
     "This variable provides the component's string name for
      use with the ASCII Console Interface"
::= { lpFiLtFbFddiMacRowStatusEntry 2 }

lpFiLtFbFddiMacStorageType OBJECT-TYPE
   SYNTAX     StorageType 
   ACCESS     read-only
   STATUS     mandatory
   DESCRIPTION
     "This variable represents the storage type value for the
      lpFiLtFbFddiMac tables."
::= { lpFiLtFbFddiMacRowStatusEntry 4 }

lpFiLtFbFddiMacIndex OBJECT-TYPE
   SYNTAX     NonReplicated 
   ACCESS     not-accessible
   STATUS     mandatory
   DESCRIPTION
     "This variable represents the index for the lpFiLtFbFddiMac tables."
::= { lpFiLtFbFddiMacRowStatusEntry 10 }

lpFiLtFbFddiMacTopTable OBJECT-TYPE
   SYNTAX     SEQUENCE OF LpFiLtFbFddiMacTopEntry
   ACCESS     not-accessible
   STATUS     mandatory
   DESCRIPTION
     "This group contains the operational data for the LanTest component 
      and its subcomponents."
::= { lpFiLtFbFddiMac 10 }

lpFiLtFbFddiMacTopEntry OBJECT-TYPE
   SYNTAX     LpFiLtFbFddiMacTopEntry
   ACCESS     not-accessible
   STATUS     mandatory
   DESCRIPTION
     "An entry in the lpFiLtFbFddiMacTopTable."
   INDEX {
      lpIndex,
      lpFiIndex,
      lpFiLtIndex,
      lpFiLtFbIndex,
      lpFiLtFbFddiMacIndex }
::= { lpFiLtFbFddiMacTopTable 1 }

LpFiLtFbFddiMacTopEntry ::= SEQUENCE {
   lpFiLtFbFddiMacTData
      AsciiString }

lpFiLtFbFddiMacTData OBJECT-TYPE
   SYNTAX     AsciiString (SIZE (0..255))
   ACCESS     read-write
   STATUS     mandatory
   DESCRIPTION
     "This attribute is used to display and set attributes."
::= { lpFiLtFbFddiMacTopEntry 1 }


-- LanTest EthernetMac
-- This component builds an Ethernet MAC header which is attached 
-- to all Ethernet frames.

lpFiLtFbMacEnet OBJECT IDENTIFIER ::= { lpFiLtFb 4 }



lpFiLtFbMacEnetRowStatusTable OBJECT-TYPE
   SYNTAX     SEQUENCE OF LpFiLtFbMacEnetRowStatusEntry
   ACCESS     not-accessible
   STATUS     mandatory
   DESCRIPTION
     "This entry controls the addition and deletion of 
      lpFiLtFbMacEnet components."
::= { lpFiLtFbMacEnet 1 }

lpFiLtFbMacEnetRowStatusEntry OBJECT-TYPE
   SYNTAX     LpFiLtFbMacEnetRowStatusEntry
   ACCESS     not-accessible
   STATUS     mandatory
   DESCRIPTION
     "A single entry in the table represents a single 
      lpFiLtFbMacEnet component."
   INDEX {
      lpIndex,
      lpFiIndex,
      lpFiLtIndex,
      lpFiLtFbIndex,
      lpFiLtFbMacEnetIndex }
::= { lpFiLtFbMacEnetRowStatusTable 1 }

LpFiLtFbMacEnetRowStatusEntry ::= SEQUENCE {
   lpFiLtFbMacEnetRowStatus
      RowStatus,
   lpFiLtFbMacEnetComponentName
      DisplayString,
   lpFiLtFbMacEnetStorageType
      StorageType,
   lpFiLtFbMacEnetIndex
      NonReplicated }

lpFiLtFbMacEnetRowStatus OBJECT-TYPE
   SYNTAX     RowStatus 
   ACCESS     read-only
   STATUS     mandatory
   DESCRIPTION
     "This variable is used as the basis for SNMP naming of
      lpFiLtFbMacEnet components.
      These components cannot be added nor deleted."
::= { lpFiLtFbMacEnetRowStatusEntry 1 }

lpFiLtFbMacEnetComponentName OBJECT-TYPE
   SYNTAX     DisplayString 
   ACCESS     read-only
   STATUS     mandatory
   DESCRIPTION
     "This variable provides the component's string name for
      use with the ASCII Console Interface"
::= { lpFiLtFbMacEnetRowStatusEntry 2 }

lpFiLtFbMacEnetStorageType OBJECT-TYPE
   SYNTAX     StorageType 
   ACCESS     read-only
   STATUS     mandatory
   DESCRIPTION
     "This variable represents the storage type value for the
      lpFiLtFbMacEnet tables."
::= { lpFiLtFbMacEnetRowStatusEntry 4 }

lpFiLtFbMacEnetIndex OBJECT-TYPE
   SYNTAX     NonReplicated 
   ACCESS     not-accessible
   STATUS     mandatory
   DESCRIPTION
     "This variable represents the index for the lpFiLtFbMacEnet tables."
::= { lpFiLtFbMacEnetRowStatusEntry 10 }

lpFiLtFbMacEnetTopTable OBJECT-TYPE
   SYNTAX     SEQUENCE OF LpFiLtFbMacEnetTopEntry
   ACCESS     not-accessible
   STATUS     mandatory
   DESCRIPTION
     "This group contains the operational data for the LanTest component 
      and its subcomponents."
::= { lpFiLtFbMacEnet 10 }

lpFiLtFbMacEnetTopEntry OBJECT-TYPE
   SYNTAX     LpFiLtFbMacEnetTopEntry
   ACCESS     not-accessible
   STATUS     mandatory
   DESCRIPTION
     "An entry in the lpFiLtFbMacEnetTopTable."
   INDEX {
      lpIndex,
      lpFiIndex,
      lpFiLtIndex,
      lpFiLtFbIndex,
      lpFiLtFbMacEnetIndex }
::= { lpFiLtFbMacEnetTopTable 1 }

LpFiLtFbMacEnetTopEntry ::= SEQUENCE {
   lpFiLtFbMacEnetTData
      AsciiString }

lpFiLtFbMacEnetTData OBJECT-TYPE
   SYNTAX     AsciiString (SIZE (0..255))
   ACCESS     read-write
   STATUS     mandatory
   DESCRIPTION
     "This attribute is used to display and set attributes."
::= { lpFiLtFbMacEnetTopEntry 1 }


-- LanTest TokenRingMac
-- This component builds a Token Ring MAC header which is attached 
-- to all Token Ring frames.

lpFiLtFbMacTr OBJECT IDENTIFIER ::= { lpFiLtFb 5 }



lpFiLtFbMacTrRowStatusTable OBJECT-TYPE
   SYNTAX     SEQUENCE OF LpFiLtFbMacTrRowStatusEntry
   ACCESS     not-accessible
   STATUS     mandatory
   DESCRIPTION
     "This entry controls the addition and deletion of 
      lpFiLtFbMacTr components."
::= { lpFiLtFbMacTr 1 }

lpFiLtFbMacTrRowStatusEntry OBJECT-TYPE
   SYNTAX     LpFiLtFbMacTrRowStatusEntry
   ACCESS     not-accessible
   STATUS     mandatory
   DESCRIPTION
     "A single entry in the table represents a single 
      lpFiLtFbMacTr component."
   INDEX {
      lpIndex,
      lpFiIndex,
      lpFiLtIndex,
      lpFiLtFbIndex,
      lpFiLtFbMacTrIndex }
::= { lpFiLtFbMacTrRowStatusTable 1 }

LpFiLtFbMacTrRowStatusEntry ::= SEQUENCE {
   lpFiLtFbMacTrRowStatus
      RowStatus,
   lpFiLtFbMacTrComponentName
      DisplayString,
   lpFiLtFbMacTrStorageType
      StorageType,
   lpFiLtFbMacTrIndex
      NonReplicated }

lpFiLtFbMacTrRowStatus OBJECT-TYPE
   SYNTAX     RowStatus 
   ACCESS     read-only
   STATUS     mandatory
   DESCRIPTION
     "This variable is used as the basis for SNMP naming of
      lpFiLtFbMacTr components.
      These components cannot be added nor deleted."
::= { lpFiLtFbMacTrRowStatusEntry 1 }

lpFiLtFbMacTrComponentName OBJECT-TYPE
   SYNTAX     DisplayString 
   ACCESS     read-only
   STATUS     mandatory
   DESCRIPTION
     "This variable provides the component's string name for
      use with the ASCII Console Interface"
::= { lpFiLtFbMacTrRowStatusEntry 2 }

lpFiLtFbMacTrStorageType OBJECT-TYPE
   SYNTAX     StorageType 
   ACCESS     read-only
   STATUS     mandatory
   DESCRIPTION
     "This variable represents the storage type value for the
      lpFiLtFbMacTr tables."
::= { lpFiLtFbMacTrRowStatusEntry 4 }

lpFiLtFbMacTrIndex OBJECT-TYPE
   SYNTAX     NonReplicated 
   ACCESS     not-accessible
   STATUS     mandatory
   DESCRIPTION
     "This variable represents the index for the lpFiLtFbMacTr tables."
::= { lpFiLtFbMacTrRowStatusEntry 10 }

lpFiLtFbMacTrTopTable OBJECT-TYPE
   SYNTAX     SEQUENCE OF LpFiLtFbMacTrTopEntry
   ACCESS     not-accessible
   STATUS     mandatory
   DESCRIPTION
     "This group contains the operational data for the LanTest component 
      and its subcomponents."
::= { lpFiLtFbMacTr 10 }

lpFiLtFbMacTrTopEntry OBJECT-TYPE
   SYNTAX     LpFiLtFbMacTrTopEntry
   ACCESS     not-accessible
   STATUS     mandatory
   DESCRIPTION
     "An entry in the lpFiLtFbMacTrTopTable."
   INDEX {
      lpIndex,
      lpFiIndex,
      lpFiLtIndex,
      lpFiLtFbIndex,
      lpFiLtFbMacTrIndex }
::= { lpFiLtFbMacTrTopTable 1 }

LpFiLtFbMacTrTopEntry ::= SEQUENCE {
   lpFiLtFbMacTrTData
      AsciiString }

lpFiLtFbMacTrTData OBJECT-TYPE
   SYNTAX     AsciiString (SIZE (0..255))
   ACCESS     read-write
   STATUS     mandatory
   DESCRIPTION
     "This attribute is used to display and set attributes."
::= { lpFiLtFbMacTrTopEntry 1 }


-- This component adds a data field to frame.

lpFiLtFbData OBJECT IDENTIFIER ::= { lpFiLtFb 6 }



lpFiLtFbDataRowStatusTable OBJECT-TYPE
   SYNTAX     SEQUENCE OF LpFiLtFbDataRowStatusEntry
   ACCESS     not-accessible
   STATUS     mandatory
   DESCRIPTION
     "This entry controls the addition and deletion of 
      lpFiLtFbData components."
::= { lpFiLtFbData 1 }

lpFiLtFbDataRowStatusEntry OBJECT-TYPE
   SYNTAX     LpFiLtFbDataRowStatusEntry
   ACCESS     not-accessible
   STATUS     mandatory
   DESCRIPTION
     "A single entry in the table represents a single 
      lpFiLtFbData component."
   INDEX {
      lpIndex,
      lpFiIndex,
      lpFiLtIndex,
      lpFiLtFbIndex,
      lpFiLtFbDataIndex }
::= { lpFiLtFbDataRowStatusTable 1 }

LpFiLtFbDataRowStatusEntry ::= SEQUENCE {
   lpFiLtFbDataRowStatus
      RowStatus,
   lpFiLtFbDataComponentName
      DisplayString,
   lpFiLtFbDataStorageType
      StorageType,
   lpFiLtFbDataIndex
      NonReplicated }

lpFiLtFbDataRowStatus OBJECT-TYPE
   SYNTAX     RowStatus 
   ACCESS     read-only
   STATUS     mandatory
   DESCRIPTION
     "This variable is used as the basis for SNMP naming of
      lpFiLtFbData components.
      These components cannot be added nor deleted."
::= { lpFiLtFbDataRowStatusEntry 1 }

lpFiLtFbDataComponentName OBJECT-TYPE
   SYNTAX     DisplayString 
   ACCESS     read-only
   STATUS     mandatory
   DESCRIPTION
     "This variable provides the component's string name for
      use with the ASCII Console Interface"
::= { lpFiLtFbDataRowStatusEntry 2 }

lpFiLtFbDataStorageType OBJECT-TYPE
   SYNTAX     StorageType 
   ACCESS     read-only
   STATUS     mandatory
   DESCRIPTION
     "This variable represents the storage type value for the
      lpFiLtFbData tables."
::= { lpFiLtFbDataRowStatusEntry 4 }

lpFiLtFbDataIndex OBJECT-TYPE
   SYNTAX     NonReplicated 
   ACCESS     not-accessible
   STATUS     mandatory
   DESCRIPTION
     "This variable represents the index for the lpFiLtFbData tables."
::= { lpFiLtFbDataRowStatusEntry 10 }

lpFiLtFbDataTopTable OBJECT-TYPE
   SYNTAX     SEQUENCE OF LpFiLtFbDataTopEntry
   ACCESS     not-accessible
   STATUS     mandatory
   DESCRIPTION
     "This group contains the operational data for the LanTest component 
      and its subcomponents."
::= { lpFiLtFbData 10 }

lpFiLtFbDataTopEntry OBJECT-TYPE
   SYNTAX     LpFiLtFbDataTopEntry
   ACCESS     not-accessible
   STATUS     mandatory
   DESCRIPTION
     "An entry in the lpFiLtFbDataTopTable."
   INDEX {
      lpIndex,
      lpFiIndex,
      lpFiLtIndex,
      lpFiLtFbIndex,
      lpFiLtFbDataIndex }
::= { lpFiLtFbDataTopTable 1 }

LpFiLtFbDataTopEntry ::= SEQUENCE {
   lpFiLtFbDataTData
      AsciiString }

lpFiLtFbDataTData OBJECT-TYPE
   SYNTAX     AsciiString (SIZE (0..255))
   ACCESS     read-write
   STATUS     mandatory
   DESCRIPTION
     "This attribute is used to display and set attributes."
::= { lpFiLtFbDataTopEntry 1 }


-- LanTest IpHeader
-- This component adds an IP header to a frame or packet.

lpFiLtFbIpH OBJECT IDENTIFIER ::= { lpFiLtFb 7 }



lpFiLtFbIpHRowStatusTable OBJECT-TYPE
   SYNTAX     SEQUENCE OF LpFiLtFbIpHRowStatusEntry
   ACCESS     not-accessible
   STATUS     mandatory
   DESCRIPTION
     "This entry controls the addition and deletion of 
      lpFiLtFbIpH components."
::= { lpFiLtFbIpH 1 }

lpFiLtFbIpHRowStatusEntry OBJECT-TYPE
   SYNTAX     LpFiLtFbIpHRowStatusEntry
   ACCESS     not-accessible
   STATUS     mandatory
   DESCRIPTION
     "A single entry in the table represents a single 
      lpFiLtFbIpH component."
   INDEX {
      lpIndex,
      lpFiIndex,
      lpFiLtIndex,
      lpFiLtFbIndex,
      lpFiLtFbIpHIndex }
::= { lpFiLtFbIpHRowStatusTable 1 }

LpFiLtFbIpHRowStatusEntry ::= SEQUENCE {
   lpFiLtFbIpHRowStatus
      RowStatus,
   lpFiLtFbIpHComponentName
      DisplayString,
   lpFiLtFbIpHStorageType
      StorageType,
   lpFiLtFbIpHIndex
      NonReplicated }

lpFiLtFbIpHRowStatus OBJECT-TYPE
   SYNTAX     RowStatus 
   ACCESS     read-only
   STATUS     mandatory
   DESCRIPTION
     "This variable is used as the basis for SNMP naming of
      lpFiLtFbIpH components.
      These components cannot be added nor deleted."
::= { lpFiLtFbIpHRowStatusEntry 1 }

lpFiLtFbIpHComponentName OBJECT-TYPE
   SYNTAX     DisplayString 
   ACCESS     read-only
   STATUS     mandatory
   DESCRIPTION
     "This variable provides the component's string name for
      use with the ASCII Console Interface"
::= { lpFiLtFbIpHRowStatusEntry 2 }

lpFiLtFbIpHStorageType OBJECT-TYPE
   SYNTAX     StorageType 
   ACCESS     read-only
   STATUS     mandatory
   DESCRIPTION
     "This variable represents the storage type value for the
      lpFiLtFbIpH tables."
::= { lpFiLtFbIpHRowStatusEntry 4 }

lpFiLtFbIpHIndex OBJECT-TYPE
   SYNTAX     NonReplicated 
   ACCESS     not-accessible
   STATUS     mandatory
   DESCRIPTION
     "This variable represents the index for the lpFiLtFbIpH tables."
::= { lpFiLtFbIpHRowStatusEntry 10 }

lpFiLtFbIpHTopTable OBJECT-TYPE
   SYNTAX     SEQUENCE OF LpFiLtFbIpHTopEntry
   ACCESS     not-accessible
   STATUS     mandatory
   DESCRIPTION
     "This group contains the operational data for the LanTest component 
      and its subcomponents."
::= { lpFiLtFbIpH 10 }

lpFiLtFbIpHTopEntry OBJECT-TYPE
   SYNTAX     LpFiLtFbIpHTopEntry
   ACCESS     not-accessible
   STATUS     mandatory
   DESCRIPTION
     "An entry in the lpFiLtFbIpHTopTable."
   INDEX {
      lpIndex,
      lpFiIndex,
      lpFiLtIndex,
      lpFiLtFbIndex,
      lpFiLtFbIpHIndex }
::= { lpFiLtFbIpHTopTable 1 }

LpFiLtFbIpHTopEntry ::= SEQUENCE {
   lpFiLtFbIpHTData
      AsciiString }

lpFiLtFbIpHTData OBJECT-TYPE
   SYNTAX     AsciiString (SIZE (0..255))
   ACCESS     read-write
   STATUS     mandatory
   DESCRIPTION
     "This attribute is used to display and set attributes."
::= { lpFiLtFbIpHTopEntry 1 }


-- LanTest LlcHeader
-- This component adds an LLC 802.2 or Ethernet header to a frame 
-- or packet.

lpFiLtFbLlch OBJECT IDENTIFIER ::= { lpFiLtFb 8 }



lpFiLtFbLlchRowStatusTable OBJECT-TYPE
   SYNTAX     SEQUENCE OF LpFiLtFbLlchRowStatusEntry
   ACCESS     not-accessible
   STATUS     mandatory
   DESCRIPTION
     "This entry controls the addition and deletion of 
      lpFiLtFbLlch components."
::= { lpFiLtFbLlch 1 }

lpFiLtFbLlchRowStatusEntry OBJECT-TYPE
   SYNTAX     LpFiLtFbLlchRowStatusEntry
   ACCESS     not-accessible
   STATUS     mandatory
   DESCRIPTION
     "A single entry in the table represents a single 
      lpFiLtFbLlch component."
   INDEX {
      lpIndex,
      lpFiIndex,
      lpFiLtIndex,
      lpFiLtFbIndex,
      lpFiLtFbLlchIndex }
::= { lpFiLtFbLlchRowStatusTable 1 }

LpFiLtFbLlchRowStatusEntry ::= SEQUENCE {
   lpFiLtFbLlchRowStatus
      RowStatus,
   lpFiLtFbLlchComponentName
      DisplayString,
   lpFiLtFbLlchStorageType
      StorageType,
   lpFiLtFbLlchIndex
      NonReplicated }

lpFiLtFbLlchRowStatus OBJECT-TYPE
   SYNTAX     RowStatus 
   ACCESS     read-only
   STATUS     mandatory
   DESCRIPTION
     "This variable is used as the basis for SNMP naming of
      lpFiLtFbLlch components.
      These components cannot be added nor deleted."
::= { lpFiLtFbLlchRowStatusEntry 1 }

lpFiLtFbLlchComponentName OBJECT-TYPE
   SYNTAX     DisplayString 
   ACCESS     read-only
   STATUS     mandatory
   DESCRIPTION
     "This variable provides the component's string name for
      use with the ASCII Console Interface"
::= { lpFiLtFbLlchRowStatusEntry 2 }

lpFiLtFbLlchStorageType OBJECT-TYPE
   SYNTAX     StorageType 
   ACCESS     read-only
   STATUS     mandatory
   DESCRIPTION
     "This variable represents the storage type value for the
      lpFiLtFbLlch tables."
::= { lpFiLtFbLlchRowStatusEntry 4 }

lpFiLtFbLlchIndex OBJECT-TYPE
   SYNTAX     NonReplicated 
   ACCESS     not-accessible
   STATUS     mandatory
   DESCRIPTION
     "This variable represents the index for the lpFiLtFbLlch tables."
::= { lpFiLtFbLlchRowStatusEntry 10 }

lpFiLtFbLlchTopTable OBJECT-TYPE
   SYNTAX     SEQUENCE OF LpFiLtFbLlchTopEntry
   ACCESS     not-accessible
   STATUS     mandatory
   DESCRIPTION
     "This group contains the operational data for the LanTest component 
      and its subcomponents."
::= { lpFiLtFbLlch 10 }

lpFiLtFbLlchTopEntry OBJECT-TYPE
   SYNTAX     LpFiLtFbLlchTopEntry
   ACCESS     not-accessible
   STATUS     mandatory
   DESCRIPTION
     "An entry in the lpFiLtFbLlchTopTable."
   INDEX {
      lpIndex,
      lpFiIndex,
      lpFiLtIndex,
      lpFiLtFbIndex,
      lpFiLtFbLlchIndex }
::= { lpFiLtFbLlchTopTable 1 }

LpFiLtFbLlchTopEntry ::= SEQUENCE {
   lpFiLtFbLlchTData
      AsciiString }

lpFiLtFbLlchTData OBJECT-TYPE
   SYNTAX     AsciiString (SIZE (0..255))
   ACCESS     read-write
   STATUS     mandatory
   DESCRIPTION
     "This attribute is used to display and set attributes."
::= { lpFiLtFbLlchTopEntry 1 }


-- This component adds an AppleTalk header to a frame or packet.

lpFiLtFbAppleH OBJECT IDENTIFIER ::= { lpFiLtFb 9 }



lpFiLtFbAppleHRowStatusTable OBJECT-TYPE
   SYNTAX     SEQUENCE OF LpFiLtFbAppleHRowStatusEntry
   ACCESS     not-accessible
   STATUS     mandatory
   DESCRIPTION
     "This entry controls the addition and deletion of 
      lpFiLtFbAppleH components."
::= { lpFiLtFbAppleH 1 }

lpFiLtFbAppleHRowStatusEntry OBJECT-TYPE
   SYNTAX     LpFiLtFbAppleHRowStatusEntry
   ACCESS     not-accessible
   STATUS     mandatory
   DESCRIPTION
     "A single entry in the table represents a single 
      lpFiLtFbAppleH component."
   INDEX {
      lpIndex,
      lpFiIndex,
      lpFiLtIndex,
      lpFiLtFbIndex,
      lpFiLtFbAppleHIndex }
::= { lpFiLtFbAppleHRowStatusTable 1 }

LpFiLtFbAppleHRowStatusEntry ::= SEQUENCE {
   lpFiLtFbAppleHRowStatus
      RowStatus,
   lpFiLtFbAppleHComponentName
      DisplayString,
   lpFiLtFbAppleHStorageType
      StorageType,
   lpFiLtFbAppleHIndex
      NonReplicated }

lpFiLtFbAppleHRowStatus OBJECT-TYPE
   SYNTAX     RowStatus 
   ACCESS     read-only
   STATUS     mandatory
   DESCRIPTION
     "This variable is used as the basis for SNMP naming of
      lpFiLtFbAppleH components.
      These components cannot be added nor deleted."
::= { lpFiLtFbAppleHRowStatusEntry 1 }

lpFiLtFbAppleHComponentName OBJECT-TYPE
   SYNTAX     DisplayString 
   ACCESS     read-only
   STATUS     mandatory
   DESCRIPTION
     "This variable provides the component's string name for
      use with the ASCII Console Interface"
::= { lpFiLtFbAppleHRowStatusEntry 2 }

lpFiLtFbAppleHStorageType OBJECT-TYPE
   SYNTAX     StorageType 
   ACCESS     read-only
   STATUS     mandatory
   DESCRIPTION
     "This variable represents the storage type value for the
      lpFiLtFbAppleH tables."
::= { lpFiLtFbAppleHRowStatusEntry 4 }

lpFiLtFbAppleHIndex OBJECT-TYPE
   SYNTAX     NonReplicated 
   ACCESS     not-accessible
   STATUS     mandatory
   DESCRIPTION
     "This variable represents the index for the lpFiLtFbAppleH tables."
::= { lpFiLtFbAppleHRowStatusEntry 10 }

lpFiLtFbAppleHTopTable OBJECT-TYPE
   SYNTAX     SEQUENCE OF LpFiLtFbAppleHTopEntry
   ACCESS     not-accessible
   STATUS     mandatory
   DESCRIPTION
     "This group contains the operational data for the LanTest component 
      and its subcomponents."
::= { lpFiLtFbAppleH 10 }

lpFiLtFbAppleHTopEntry OBJECT-TYPE
   SYNTAX     LpFiLtFbAppleHTopEntry
   ACCESS     not-accessible
   STATUS     mandatory
   DESCRIPTION
     "An entry in the lpFiLtFbAppleHTopTable."
   INDEX {
      lpIndex,
      lpFiIndex,
      lpFiLtIndex,
      lpFiLtFbIndex,
      lpFiLtFbAppleHIndex }
::= { lpFiLtFbAppleHTopTable 1 }

LpFiLtFbAppleHTopEntry ::= SEQUENCE {
   lpFiLtFbAppleHTData
      AsciiString }

lpFiLtFbAppleHTData OBJECT-TYPE
   SYNTAX     AsciiString (SIZE (0..255))
   ACCESS     read-write
   STATUS     mandatory
   DESCRIPTION
     "This attribute is used to display and set attributes."
::= { lpFiLtFbAppleHTopEntry 1 }


-- This component adds an IPX header to a frame or packet.

lpFiLtFbIpxH OBJECT IDENTIFIER ::= { lpFiLtFb 10 }



lpFiLtFbIpxHRowStatusTable OBJECT-TYPE
   SYNTAX     SEQUENCE OF LpFiLtFbIpxHRowStatusEntry
   ACCESS     not-accessible
   STATUS     mandatory
   DESCRIPTION
     "This entry controls the addition and deletion of 
      lpFiLtFbIpxH components."
::= { lpFiLtFbIpxH 1 }

lpFiLtFbIpxHRowStatusEntry OBJECT-TYPE
   SYNTAX     LpFiLtFbIpxHRowStatusEntry
   ACCESS     not-accessible
   STATUS     mandatory
   DESCRIPTION
     "A single entry in the table represents a single 
      lpFiLtFbIpxH component."
   INDEX {
      lpIndex,
      lpFiIndex,
      lpFiLtIndex,
      lpFiLtFbIndex,
      lpFiLtFbIpxHIndex }
::= { lpFiLtFbIpxHRowStatusTable 1 }

LpFiLtFbIpxHRowStatusEntry ::= SEQUENCE {
   lpFiLtFbIpxHRowStatus
      RowStatus,
   lpFiLtFbIpxHComponentName
      DisplayString,
   lpFiLtFbIpxHStorageType
      StorageType,
   lpFiLtFbIpxHIndex
      NonReplicated }

lpFiLtFbIpxHRowStatus OBJECT-TYPE
   SYNTAX     RowStatus 
   ACCESS     read-only
   STATUS     mandatory
   DESCRIPTION
     "This variable is used as the basis for SNMP naming of
      lpFiLtFbIpxH components.
      These components cannot be added nor deleted."
::= { lpFiLtFbIpxHRowStatusEntry 1 }

lpFiLtFbIpxHComponentName OBJECT-TYPE
   SYNTAX     DisplayString 
   ACCESS     read-only
   STATUS     mandatory
   DESCRIPTION
     "This variable provides the component's string name for
      use with the ASCII Console Interface"
::= { lpFiLtFbIpxHRowStatusEntry 2 }

lpFiLtFbIpxHStorageType OBJECT-TYPE
   SYNTAX     StorageType 
   ACCESS     read-only
   STATUS     mandatory
   DESCRIPTION
     "This variable represents the storage type value for the
      lpFiLtFbIpxH tables."
::= { lpFiLtFbIpxHRowStatusEntry 4 }

lpFiLtFbIpxHIndex OBJECT-TYPE
   SYNTAX     NonReplicated 
   ACCESS     not-accessible
   STATUS     mandatory
   DESCRIPTION
     "This variable represents the index for the lpFiLtFbIpxH tables."
::= { lpFiLtFbIpxHRowStatusEntry 10 }

lpFiLtFbIpxHTopTable OBJECT-TYPE
   SYNTAX     SEQUENCE OF LpFiLtFbIpxHTopEntry
   ACCESS     not-accessible
   STATUS     mandatory
   DESCRIPTION
     "This group contains the operational data for the LanTest component 
      and its subcomponents."
::= { lpFiLtFbIpxH 10 }

lpFiLtFbIpxHTopEntry OBJECT-TYPE
   SYNTAX     LpFiLtFbIpxHTopEntry
   ACCESS     not-accessible
   STATUS     mandatory
   DESCRIPTION
     "An entry in the lpFiLtFbIpxHTopTable."
   INDEX {
      lpIndex,
      lpFiIndex,
      lpFiLtIndex,
      lpFiLtFbIndex,
      lpFiLtFbIpxHIndex }
::= { lpFiLtFbIpxHTopTable 1 }

LpFiLtFbIpxHTopEntry ::= SEQUENCE {
   lpFiLtFbIpxHTData
      AsciiString }

lpFiLtFbIpxHTData OBJECT-TYPE
   SYNTAX     AsciiString (SIZE (0..255))
   ACCESS     read-write
   STATUS     mandatory
   DESCRIPTION
     "This attribute is used to display and set attributes."
::= { lpFiLtFbIpxHTopEntry 1 }


-- LanTest Control
-- This component controls the overall testing by telling the 
-- FrameBuild component to start and check the FrameCompare 
-- component to see if the test is complete.

lpFiLtCntl OBJECT IDENTIFIER ::= { lpFiLt 6 }



lpFiLtCntlRowStatusTable OBJECT-TYPE
   SYNTAX     SEQUENCE OF LpFiLtCntlRowStatusEntry
   ACCESS     not-accessible
   STATUS     mandatory
   DESCRIPTION
     "This entry controls the addition and deletion of 
      lpFiLtCntl components."
::= { lpFiLtCntl 1 }

lpFiLtCntlRowStatusEntry OBJECT-TYPE
   SYNTAX     LpFiLtCntlRowStatusEntry
   ACCESS     not-accessible
   STATUS     mandatory
   DESCRIPTION
     "A single entry in the table represents a single 
      lpFiLtCntl component."
   INDEX {
      lpIndex,
      lpFiIndex,
      lpFiLtIndex,
      lpFiLtCntlIndex }
::= { lpFiLtCntlRowStatusTable 1 }

LpFiLtCntlRowStatusEntry ::= SEQUENCE {
   lpFiLtCntlRowStatus
      RowStatus,
   lpFiLtCntlComponentName
      DisplayString,
   lpFiLtCntlStorageType
      StorageType,
   lpFiLtCntlIndex
      NonReplicated }

lpFiLtCntlRowStatus OBJECT-TYPE
   SYNTAX     RowStatus 
   ACCESS     read-only
   STATUS     mandatory
   DESCRIPTION
     "This variable is used as the basis for SNMP naming of
      lpFiLtCntl components.
      These components cannot be added nor deleted."
::= { lpFiLtCntlRowStatusEntry 1 }

lpFiLtCntlComponentName OBJECT-TYPE
   SYNTAX     DisplayString 
   ACCESS     read-only
   STATUS     mandatory
   DESCRIPTION
     "This variable provides the component's string name for
      use with the ASCII Console Interface"
::= { lpFiLtCntlRowStatusEntry 2 }

lpFiLtCntlStorageType OBJECT-TYPE
   SYNTAX     StorageType 
   ACCESS     read-only
   STATUS     mandatory
   DESCRIPTION
     "This variable represents the storage type value for the
      lpFiLtCntl tables."
::= { lpFiLtCntlRowStatusEntry 4 }

lpFiLtCntlIndex OBJECT-TYPE
   SYNTAX     NonReplicated 
   ACCESS     not-accessible
   STATUS     mandatory
   DESCRIPTION
     "This variable represents the index for the lpFiLtCntl tables."
::= { lpFiLtCntlRowStatusEntry 10 }

lpFiLtCntlTopTable OBJECT-TYPE
   SYNTAX     SEQUENCE OF LpFiLtCntlTopEntry
   ACCESS     not-accessible
   STATUS     mandatory
   DESCRIPTION
     "This group contains the operational data for the LanTest component 
      and its subcomponents."
::= { lpFiLtCntl 10 }

lpFiLtCntlTopEntry OBJECT-TYPE
   SYNTAX     LpFiLtCntlTopEntry
   ACCESS     not-accessible
   STATUS     mandatory
   DESCRIPTION
     "An entry in the lpFiLtCntlTopTable."
   INDEX {
      lpIndex,
      lpFiIndex,
      lpFiLtIndex,
      lpFiLtCntlIndex }
::= { lpFiLtCntlTopTable 1 }

LpFiLtCntlTopEntry ::= SEQUENCE {
   lpFiLtCntlTData
      AsciiString }

lpFiLtCntlTData OBJECT-TYPE
   SYNTAX     AsciiString (SIZE (0..255))
   ACCESS     read-write
   STATUS     mandatory
   DESCRIPTION
     "This attribute is used to display and set attributes."
::= { lpFiLtCntlTopEntry 1 }


-- Lp/n Fddi/n Phy/x
-- This component defines an instance of a FDDI port attached to a ring. 
-- Two instances of this component must be provisioned for each hardware 
-- port. Each port must be provisioned prior to inserting into the ring.

lpFiPhy OBJECT IDENTIFIER ::= { lpFi 3 }



lpFiPhyRowStatusTable OBJECT-TYPE
   SYNTAX     SEQUENCE OF LpFiPhyRowStatusEntry
   ACCESS     not-accessible
   STATUS     mandatory
   DESCRIPTION
     "This entry controls the addition and deletion of 
      lpFiPhy components."
::= { lpFiPhy 1 }

lpFiPhyRowStatusEntry OBJECT-TYPE
   SYNTAX     LpFiPhyRowStatusEntry
   ACCESS     not-accessible
   STATUS     mandatory
   DESCRIPTION
     "A single entry in the table represents a single 
      lpFiPhy component."
   INDEX {
      lpIndex,
      lpFiIndex,
      lpFiPhyFddiPhyTypeIndex }
::= { lpFiPhyRowStatusTable 1 }

LpFiPhyRowStatusEntry ::= SEQUENCE {
   lpFiPhyRowStatus
      RowStatus,
   lpFiPhyComponentName
      DisplayString,
   lpFiPhyStorageType
      StorageType,
   lpFiPhyFddiPhyTypeIndex
      INTEGER }

lpFiPhyRowStatus OBJECT-TYPE
   SYNTAX     RowStatus 
   ACCESS     read-write
   STATUS     mandatory
   DESCRIPTION
     "This variable is used as the basis for SNMP naming of
      lpFiPhy components.
      These components can be added."
::= { lpFiPhyRowStatusEntry 1 }

lpFiPhyComponentName OBJECT-TYPE
   SYNTAX     DisplayString 
   ACCESS     read-only
   STATUS     mandatory
   DESCRIPTION
     "This variable provides the component's string name for
      use with the ASCII Console Interface"
::= { lpFiPhyRowStatusEntry 2 }

lpFiPhyStorageType OBJECT-TYPE
   SYNTAX     StorageType 
   ACCESS     read-only
   STATUS     mandatory
   DESCRIPTION
     "This variable represents the storage type value for the
      lpFiPhy tables."
::= { lpFiPhyRowStatusEntry 4 }

lpFiPhyFddiPhyTypeIndex OBJECT-TYPE
   SYNTAX     INTEGER  {
                 a(0),
                 b(1) }
   ACCESS     not-accessible
   STATUS     mandatory
   DESCRIPTION
     "This variable represents the index for the lpFiPhy tables."
::= { lpFiPhyRowStatusEntry 10 }

lpFiPhyProvTable OBJECT-TYPE
   SYNTAX     SEQUENCE OF LpFiPhyProvEntry
   ACCESS     not-accessible
   STATUS     mandatory
   DESCRIPTION
     "This group contains the provisionable attributes of the Fddi Phy 
      component."
::= { lpFiPhy 10 }

lpFiPhyProvEntry OBJECT-TYPE
   SYNTAX     LpFiPhyProvEntry
   ACCESS     not-accessible
   STATUS     mandatory
   DESCRIPTION
     "An entry in the lpFiPhyProvTable."
   INDEX {
      lpIndex,
      lpFiIndex,
      lpFiPhyFddiPhyTypeIndex }
::= { lpFiPhyProvTable 1 }

LpFiPhyProvEntry ::= SEQUENCE {
   lpFiPhyLerCutoff
      Unsigned32,
   lpFiPhyLerAlarm
      Unsigned32,
   lpFiPhyLinkErrorMonitor
      INTEGER }

lpFiPhyLerCutoff OBJECT-TYPE
   SYNTAX     Unsigned32 (4..15)
   ACCESS     read-write
   STATUS     mandatory
   DESCRIPTION
     "The lerCutoff attribute contains the link error rate estimate at which a 
      link connection will be broken. The values will range from 10**-4 to 
      10**-15. Only the absolute value of the base 10 log is reported."
   DEFVAL     { 7 }
::= { lpFiPhyProvEntry 1 }

lpFiPhyLerAlarm OBJECT-TYPE
   SYNTAX     Unsigned32 (4..15)
   ACCESS     read-write
   STATUS     mandatory
   DESCRIPTION
     "The lerAlarm attribute contains the link error rate estimate at which a 
      link connection will generate an alarm. The values will range from 
      10**-4 to 10**-15. Only the absolute value of the base 10 log is 
      reported"
   DEFVAL     { 8 }
::= { lpFiPhyProvEntry 2 }

lpFiPhyLinkErrorMonitor OBJECT-TYPE
   SYNTAX     INTEGER  {
                 enabled(1),
                 disabled(2) }
   ACCESS     read-write
   STATUS     mandatory
   DESCRIPTION
     "The linkErrorMonitor attribute is used to select the state of the link error 
      monitor for the associated Phy component. If enabled, the link error 
      monitor will send the correct test status to the neighboring station. If 
      disabled, the link error monitor will always send a test passed status to 
      the neighboring station."
   DEFVAL     { enabled }
::= { lpFiPhyProvEntry 3 }

lpFiPhyOperTable OBJECT-TYPE
   SYNTAX     SEQUENCE OF LpFiPhyOperEntry
   ACCESS     not-accessible
   STATUS     mandatory
   DESCRIPTION
     "This group contains the operational attributes of the Fddi Phy 
      component."
::= { lpFiPhy 11 }

lpFiPhyOperEntry OBJECT-TYPE
   SYNTAX     LpFiPhyOperEntry
   ACCESS     not-accessible
   STATUS     mandatory
   DESCRIPTION
     "An entry in the lpFiPhyOperTable."
   INDEX {
      lpIndex,
      lpFiIndex,
      lpFiPhyFddiPhyTypeIndex }
::= { lpFiPhyOperTable 1 }

LpFiPhyOperEntry ::= SEQUENCE {
   lpFiPhyNeighborType
      INTEGER,
   lpFiPhyLctFailCounts
      Counter32,
   lpFiPhyLerEstimate
      Unsigned32,
   lpFiPhyLemRejectCounts
      Counter32,
   lpFiPhyLemCounts
      Counter32,
   lpFiPhyPcmState
      INTEGER,
   lpFiPhyLerFlag
      INTEGER,
   lpFiPhySignalState
      INTEGER,
   lpFiPhySignalBitsRcvd
      OCTET STRING,
   lpFiPhySignalBitsTxmt
      OCTET STRING }

lpFiPhyNeighborType OBJECT-TYPE
   SYNTAX     INTEGER  {
                 a(1),
                 b(2),
                 s(3),
                 m(4),
                 none(5) }
   ACCESS     read-only
   STATUS     mandatory
   DESCRIPTION
     "This attribute indicates the neighbor type of the neighbor physical layer."
::= { lpFiPhyOperEntry 4 }

lpFiPhyLctFailCounts OBJECT-TYPE
   SYNTAX     Counter32 
   ACCESS     read-only
   STATUS     mandatory
   DESCRIPTION
     "The lctFailCounts attribute contains the number of consecutive times the 
      Link Confidence Test (LCT) has failed. This counter will wrap around 
      after it reaches its maximum value."
::= { lpFiPhyOperEntry 13 }

lpFiPhyLerEstimate OBJECT-TYPE
   SYNTAX     Unsigned32 (4..15)
   ACCESS     read-only
   STATUS     mandatory
   DESCRIPTION
     "The lerEstimate attribute contains a long term average link error rate. 
      The values will range from 10**-4 to 10**-15. Only the absolute value 
      of the base 10 log is reported"
::= { lpFiPhyOperEntry 14 }

lpFiPhyLemRejectCounts OBJECT-TYPE
   SYNTAX     Counter32 
   ACCESS     read-only
   STATUS     mandatory
   DESCRIPTION
     "The lemRejectCounts attribute contains the number of times that a link 
      has been rejected. This counter will wrap around after it reaches its 
      maximum value."
::= { lpFiPhyOperEntry 15 }

lpFiPhyLemCounts OBJECT-TYPE
   SYNTAX     Counter32 
   ACCESS     read-only
   STATUS     mandatory
   DESCRIPTION
     "The lemCounts attribute contains the aggregate link error monitor error 
      count. This counter is set to zero only on station initialization. This 
      counter will wrap around after it reaches its maximum value."
::= { lpFiPhyOperEntry 16 }

lpFiPhyPcmState OBJECT-TYPE
   SYNTAX     INTEGER  {
                 off(1),
                 break(2),
                 trace(3),
                 connect(4),
                 next(5),
                 signal(6),
                 join(7),
                 verify(8),
                 active(9),
                 maint(10) }
   ACCESS     read-only
   STATUS     mandatory
   DESCRIPTION
     "The pcmState, physical connection manager (PCM), state indicates the 
      current state of the PCM state machine."
::= { lpFiPhyOperEntry 18 }

lpFiPhyLerFlag OBJECT-TYPE
   SYNTAX     INTEGER  {
                 true(1),
                 false(2) }
   ACCESS     read-only
   STATUS     mandatory
   DESCRIPTION
     "The lerFlag attribute indicates when the link error rate estimate is less 
      than or equal to the link error rate alarm. If true, the value of the link 
      error rate estimate is less than or equal to the link error rate alarm. If 
      false, the value of the link error rate estimate is greater than the link 
      error rate alarm."
::= { lpFiPhyOperEntry 20 }

lpFiPhySignalState OBJECT-TYPE
   SYNTAX     INTEGER  {
                 escape(0),
                 phyTypeL(1),
                 phyTypeH(2),
                 accept(3),
                 lctLengthL(4),
                 lctLengthH(5),
                 macAvail(6),
                 lctResult(7),
                 macLoop(8),
                 macOnPhy(9),
                 signalingDone(10) }
   ACCESS     read-only
   STATUS     mandatory
   DESCRIPTION
     "The signalState attribute contains the current physical connection 
      manager (PCM) signal bit being transmitted, or was transmitted, during 
      the PCM signal state."
::= { lpFiPhyOperEntry 23 }

lpFiPhySignalBitsRcvd OBJECT-TYPE
   SYNTAX     OCTET STRING (SIZE (2))
   ACCESS     read-only
   STATUS     mandatory
   DESCRIPTION
     "The signalBitsRcvd attribute contains the current physical connection 
      manager (PCM) signal bits received.

      Description of bits:
      escape(0)
      phyTypeL(1)
      phyTypeH(2)
      accept(3)
      lctLengthL(4)
      lctLengthH(5)
      macAvail(6)
      lctResult(7)
      macLoop(8)
      macOnPhy(9)"
::= { lpFiPhyOperEntry 24 }

lpFiPhySignalBitsTxmt OBJECT-TYPE
   SYNTAX     OCTET STRING (SIZE (2))
   ACCESS     read-only
   STATUS     mandatory
   DESCRIPTION
     "The signalBitsTxmt attribute contains the current physical connection 
      manager (PCM) signal bits transmitted.

      Description of bits:
      escape(0)
      phyTypeL(1)
      phyTypeH(2)
      accept(3)
      lctLengthL(4)
      lctLengthH(5)
      macAvail(6)
      lctResult(7)
      macLoop(8)
      macOnPhy(9)"
::= { lpFiPhyOperEntry 25 }


-- Lp/n Fddi/n Test, or
-- Lp/n Ethernet/n Test, or
-- Lp/n TokenRing/n Test, or
-- Lp/n IlsForwarder/n Test
-- The Test component is used to do StartUp port test for LAN cards.

lpFiTest OBJECT IDENTIFIER ::= { lpFi 5 }



lpFiTestRowStatusTable OBJECT-TYPE
   SYNTAX     SEQUENCE OF LpFiTestRowStatusEntry
   ACCESS     not-accessible
   STATUS     mandatory
   DESCRIPTION
     "This entry controls the addition and deletion of 
      lpFiTest components."
::= { lpFiTest 1 }

lpFiTestRowStatusEntry OBJECT-TYPE
   SYNTAX     LpFiTestRowStatusEntry
   ACCESS     not-accessible
   STATUS     mandatory
   DESCRIPTION
     "A single entry in the table represents a single 
      lpFiTest component."
   INDEX {
      lpIndex,
      lpFiIndex,
      lpFiTestIndex }
::= { lpFiTestRowStatusTable 1 }

LpFiTestRowStatusEntry ::= SEQUENCE {
   lpFiTestRowStatus
      RowStatus,
   lpFiTestComponentName
      DisplayString,
   lpFiTestStorageType
      StorageType,
   lpFiTestIndex
      NonReplicated }

lpFiTestRowStatus OBJECT-TYPE
   SYNTAX     RowStatus 
   ACCESS     read-only
   STATUS     mandatory
   DESCRIPTION
     "This variable is used as the basis for SNMP naming of
      lpFiTest components.
      These components cannot be added nor deleted."
::= { lpFiTestRowStatusEntry 1 }

lpFiTestComponentName OBJECT-TYPE
   SYNTAX     DisplayString 
   ACCESS     read-only
   STATUS     mandatory
   DESCRIPTION
     "This variable provides the component's string name for
      use with the ASCII Console Interface"
::= { lpFiTestRowStatusEntry 2 }

lpFiTestStorageType OBJECT-TYPE
   SYNTAX     StorageType 
   ACCESS     read-only
   STATUS     mandatory
   DESCRIPTION
     "This variable represents the storage type value for the
      lpFiTest tables."
::= { lpFiTestRowStatusEntry 4 }

lpFiTestIndex OBJECT-TYPE
   SYNTAX     NonReplicated 
   ACCESS     not-accessible
   STATUS     mandatory
   DESCRIPTION
     "This variable represents the index for the lpFiTest tables."
::= { lpFiTestRowStatusEntry 10 }

lpFiTestPTOTable OBJECT-TYPE
   SYNTAX     SEQUENCE OF LpFiTestPTOEntry
   ACCESS     not-accessible
   STATUS     mandatory
   DESCRIPTION
     "This group contains the operational data for the LanPortTest 
      component."
::= { lpFiTest 10 }

lpFiTestPTOEntry OBJECT-TYPE
   SYNTAX     LpFiTestPTOEntry
   ACCESS     not-accessible
   STATUS     mandatory
   DESCRIPTION
     "An entry in the lpFiTestPTOTable."
   INDEX {
      lpIndex,
      lpFiIndex,
      lpFiTestIndex }
::= { lpFiTestPTOTable 1 }

LpFiTestPTOEntry ::= SEQUENCE {
   lpFiTestType
      INTEGER,
   lpFiTestFrmSize
      Unsigned32,
   lpFiTestDuration
      Unsigned32 }

lpFiTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { lpFiTestPTOEntry 1 }

lpFiTestFrmSize OBJECT-TYPE
   SYNTAX     Unsigned32 (4..4096)
   ACCESS     read-write
   STATUS     mandatory
   DESCRIPTION
     "This attribute defines the size of the test data frames in number of 
      bytes."
   DEFVAL     { 1024 }
::= { lpFiTestPTOEntry 2 }

lpFiTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpFiTestPTOEntry 3 }

lpFiTestResultsTable OBJECT-TYPE
   SYNTAX     SEQUENCE OF LpFiTestResultsEntry
   ACCESS     not-accessible
   STATUS     mandatory
   DESCRIPTION
     "This group contains all the statistics related attributes of the Test 
      component."
::= { lpFiTest 11 }

lpFiTestResultsEntry OBJECT-TYPE
   SYNTAX     LpFiTestResultsEntry
   ACCESS     not-accessible
   STATUS     mandatory
   DESCRIPTION
     "An entry in the lpFiTestResultsTable."
   INDEX {
      lpIndex,
      lpFiIndex,
      lpFiTestIndex }
::= { lpFiTestResultsTable 1 }

LpFiTestResultsEntry ::= SEQUENCE {
   lpFiTestElapsedTime
      Counter32,
   lpFiTestTimeRemaining
      Unsigned32,
   lpFiTestCauseOfTermination
      INTEGER,
   lpFiTestFrmTx
      PassportCounter64,
   lpFiTestBitsTx
      PassportCounter64,
   lpFiTestFrmRx
      PassportCounter64,
   lpFiTestBitsRx
      PassportCounter64,
   lpFiTestErroredFrmRx
      PassportCounter64 }

lpFiTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpFiTestResultsEntry 4 }

lpFiTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpFiTestResultsEntry 5 }

lpFiTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { lpFiTestResultsEntry 6 }

lpFiTestFrmTx OBJECT-TYPE
   SYNTAX     PassportCounter64 
   ACCESS     read-only
   STATUS     mandatory
   DESCRIPTION
     "This attribute is the total number of frames sent during the test 
      period. This counter is not expected to reach its maximum value."
::= { lpFiTestResultsEntry 7 }

lpFiTestBitsTx OBJECT-TYPE
   SYNTAX     PassportCounter64 
   ACCESS     read-only
   STATUS     mandatory
   DESCRIPTION
     "This attribute is the total number of bits sent during the test period. 
      This counter is not expected to reach its maximum value."
::= { lpFiTestResultsEntry 8 }

lpFiTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpFiTestResultsEntry 9 }

lpFiTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { lpFiTestResultsEntry 10 }

lpFiTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { lpFiTestResultsEntry 11 }


-- Lp/n TokenRing/n
-- This component defines an instance of a Token Ring interface 
-- attached to a ring. One instance of this component must be created 
-- for each hardware interface. Each interface must be provisioned 
-- prior to inserting into the ring.

lpTr OBJECT IDENTIFIER ::= { lp 13 }



lpTrRowStatusTable OBJECT-TYPE
   SYNTAX     SEQUENCE OF LpTrRowStatusEntry
   ACCESS     not-accessible
   STATUS     mandatory
   DESCRIPTION
     "This entry controls the addition and deletion of 
      lpTr components."
::= { lpTr 1 }

lpTrRowStatusEntry OBJECT-TYPE
   SYNTAX     LpTrRowStatusEntry
   ACCESS     not-accessible
   STATUS     mandatory
   DESCRIPTION
     "A single entry in the table represents a single 
      lpTr component."
   INDEX {
      lpIndex,
      lpTrIndex }
::= { lpTrRowStatusTable 1 }

LpTrRowStatusEntry ::= SEQUENCE {
   lpTrRowStatus
      RowStatus,
   lpTrComponentName
      DisplayString,
   lpTrStorageType
      StorageType,
   lpTrIndex
      Integer32 }

lpTrRowStatus OBJECT-TYPE
   SYNTAX     RowStatus 
   ACCESS     read-write
   STATUS     mandatory
   DESCRIPTION
     "This variable is used as the basis for SNMP naming of
      lpTr components.
      These components can be added and deleted."
::= { lpTrRowStatusEntry 1 }

lpTrComponentName OBJECT-TYPE
   SYNTAX     DisplayString 
   ACCESS     read-only
   STATUS     mandatory
   DESCRIPTION
     "This variable provides the component's string name for
      use with the ASCII Console Interface"
::= { lpTrRowStatusEntry 2 }

lpTrStorageType OBJECT-TYPE
   SYNTAX     StorageType 
   ACCESS     read-only
   STATUS     mandatory
   DESCRIPTION
     "This variable represents the storage type value for the
      lpTr tables."
::= { lpTrRowStatusEntry 4 }

lpTrIndex OBJECT-TYPE
   SYNTAX     Integer32 (0..5)
   ACCESS     not-accessible
   STATUS     mandatory
   DESCRIPTION
     "This variable represents the index for the lpTr tables."
::= { lpTrRowStatusEntry 10 }

lpTrCidDataTable OBJECT-TYPE
   SYNTAX     SEQUENCE OF LpTrCidDataEntry
   ACCESS     not-accessible
   STATUS     mandatory
   DESCRIPTION
     "This group contains the attribute for a component's Customer 
      Identifier (CID). Refer to the attribute description for a detailed 
      explanation of CIDs."
::= { lpTr 10 }

lpTrCidDataEntry OBJECT-TYPE
   SYNTAX     LpTrCidDataEntry
   ACCESS     not-accessible
   STATUS     mandatory
   DESCRIPTION
     "An entry in the lpTrCidDataTable."
   INDEX {
      lpIndex,
      lpTrIndex }
::= { lpTrCidDataTable 1 }

LpTrCidDataEntry ::= SEQUENCE {
   lpTrCustomerIdentifier
      Unsigned32 }

lpTrCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpTrCidDataEntry 1 }

lpTrIfEntryTable OBJECT-TYPE
   SYNTAX     SEQUENCE OF LpTrIfEntryEntry
   ACCESS     not-accessible
   STATUS     mandatory
   DESCRIPTION
     "This group contains the provisionable attributes for the ifEntry."
::= { lpTr 11 }

lpTrIfEntryEntry OBJECT-TYPE
   SYNTAX     LpTrIfEntryEntry
   ACCESS     not-accessible
   STATUS     mandatory
   DESCRIPTION
     "An entry in the lpTrIfEntryTable."
   INDEX {
      lpIndex,
      lpTrIndex }
::= { lpTrIfEntryTable 1 }

LpTrIfEntryEntry ::= SEQUENCE {
   lpTrIfAdminStatus
      INTEGER,
   lpTrIfIndex
      InterfaceIndex }

lpTrIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpTrIfEntryEntry 1 }

lpTrIfIndex OBJECT-TYPE
   SYNTAX     InterfaceIndex (1..65535)
   ACCESS     read-only
   STATUS     mandatory
   DESCRIPTION
     "This is the index for the IfEntry. Its value is automatically initialized 
      during the provisioning process."
::= { lpTrIfEntryEntry 2 }

lpTrProvTable OBJECT-TYPE
   SYNTAX     SEQUENCE OF LpTrProvEntry
   ACCESS     not-accessible
   STATUS     mandatory
   DESCRIPTION
     "This group contains the provisionable attributes of the Token Ring 
      port."
::= { lpTr 12 }

lpTrProvEntry OBJECT-TYPE
   SYNTAX     LpTrProvEntry
   ACCESS     not-accessible
   STATUS     mandatory
   DESCRIPTION
     "An entry in the lpTrProvTable."
   INDEX {
      lpIndex,
      lpTrIndex }
::= { lpTrProvTable 1 }

LpTrProvEntry ::= SEQUENCE {
   lpTrRingSpeed
      INTEGER,
   lpTrMonitorParticipate
      INTEGER,
   lpTrFunctionalAddress
      MacAddress,
   lpTrNodeAddress
      MacAddress,
   lpTrGroupAddress
      MacAddress,
   lpTrProductId
      AsciiString,
   lpTrApplicationFramerName
      Link }

lpTrRingSpeed OBJECT-TYPE
   SYNTAX     INTEGER  {
                 fourMegabit(3),
                 sixteenMegabit(4) }
   ACCESS     read-write
   STATUS     mandatory
   DESCRIPTION
     "This attribute indicates the ring speed at the next insertion into the 
      ring. Note that all the interfaces on a ring must operate at the same 
      speed."
   DEFVAL     { sixteenMegabit }
::= { lpTrProvEntry 1 }

lpTrMonitorParticipate OBJECT-TYPE
   SYNTAX     INTEGER  {
                 true(1),
                 false(2) }
   ACCESS     read-write
   STATUS     mandatory
   DESCRIPTION
     "This attribute determines whether the interface will participate in 
      the active monitor selection process."
   DEFVAL     { false }
::= { lpTrProvEntry 2 }

lpTrFunctionalAddress OBJECT-TYPE
   SYNTAX     MacAddress (SIZE (6))
   ACCESS     read-write
   STATUS     mandatory
   DESCRIPTION
     "This attribute contains a bit mask of all token ring functional 
      addresses for which this interface will accept frames. The address is 
      displayed in canonical form."
   DEFVAL     { '0300feff8f01'H }
::= { lpTrProvEntry 3 }

lpTrNodeAddress OBJECT-TYPE
   SYNTAX     MacAddress (SIZE (6))
   ACCESS     read-write
   STATUS     mandatory
   DESCRIPTION
     "This attribute identifies the primary, node specific address 
      recognized by this interface. If an operator does not provision a 
      MAC address, the 			interface will use a predefined, permanently			
      assigned address.
      A valid node address must not be any of the following: a broadcast 
      address, a group address, a functional address or a null address. A 
      node address should be entered in the canonical form."
   DEFVAL     { '000000000000'H }
::= { lpTrProvEntry 4 }

lpTrGroupAddress OBJECT-TYPE
   SYNTAX     MacAddress (SIZE (6))
   ACCESS     read-write
   STATUS     mandatory
   DESCRIPTION
     "This attribute identifies the group address for 			which this interface 
      will accept frames. The address is displayed in canonical form. For 
      a valid group address, the least significant bit of the first octet 
      should be set to 1. Currently, only one group address can be 
      provisioned for one interface."
   DEFVAL     { '030001000000'H }
::= { lpTrProvEntry 5 }

lpTrProductId OBJECT-TYPE
   SYNTAX     AsciiString (SIZE (0..18))
   ACCESS     read-write
   STATUS     mandatory
   DESCRIPTION
     "This attribute is used to identify the host system attached to 			this 
      interface. This information is transmitted in response			 to Request 
      Station Attachment MAC frames."
   DEFVAL     { '4c414e20546f6b656e2052696e67'H }  -- "LAN Token Ring"
::= { lpTrProvEntry 6 }

lpTrApplicationFramerName OBJECT-TYPE
   SYNTAX     Link 
   ACCESS     read-write
   STATUS     mandatory
   DESCRIPTION
     "This attribute contains the component name of a Framer which is 
      associated with the Tr component."
::= { lpTrProvEntry 7 }

lpTrAdminInfoTable OBJECT-TYPE
   SYNTAX     SEQUENCE OF LpTrAdminInfoEntry
   ACCESS     not-accessible
   STATUS     mandatory
   DESCRIPTION
     "This group contains the attributes pertaining to the vendor of the 
      equipment."
::= { lpTr 13 }

lpTrAdminInfoEntry OBJECT-TYPE
   SYNTAX     LpTrAdminInfoEntry
   ACCESS     not-accessible
   STATUS     mandatory
   DESCRIPTION
     "An entry in the lpTrAdminInfoTable."
   INDEX {
      lpIndex,
      lpTrIndex }
::= { lpTrAdminInfoTable 1 }

LpTrAdminInfoEntry ::= SEQUENCE {
   lpTrVendor
      AsciiString,
   lpTrCommentText
      AsciiString }

lpTrVendor OBJECT-TYPE
   SYNTAX     AsciiString (SIZE (0..20))
   ACCESS     read-write
   STATUS     mandatory
   DESCRIPTION
     "This is the name of the vendor supplying the facility."
::= { lpTrAdminInfoEntry 1 }

lpTrCommentText OBJECT-TYPE
   SYNTAX     AsciiString (SIZE (0..60))
   ACCESS     read-write
   STATUS     mandatory
   DESCRIPTION
     "Any miscellaneous text about the facility."
::= { lpTrAdminInfoEntry 2 }

lpTrStateTable OBJECT-TYPE
   SYNTAX     SEQUENCE OF LpTrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpTr 15 }

lpTrStateEntry OBJECT-TYPE
   SYNTAX     LpTrStateEntry
   ACCESS     not-accessible
   STATUS     mandatory
   DESCRIPTION
     "An entry in the lpTrStateTable."
   INDEX {
      lpIndex,
      lpTrIndex }
::= { lpTrStateTable 1 }

LpTrStateEntry ::= SEQUENCE {
   lpTrAdminState
      INTEGER,
   lpTrOperationalState
      INTEGER,
   lpTrUsageState
      INTEGER }

lpTrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpTrStateEntry 1 }

lpTrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpTrStateEntry 2 }

lpTrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpTrStateEntry 3 }

lpTrOperStatusTable OBJECT-TYPE
   SYNTAX     SEQUENCE OF LpTrOperStatusEntry
   ACCESS     not-accessible
   STATUS     mandatory
   DESCRIPTION
     "This group includes the Operational Status attribute. This attribute 
      defines the current operational state of this component."
::= { lpTr 16 }

lpTrOperStatusEntry OBJECT-TYPE
   SYNTAX     LpTrOperStatusEntry
   ACCESS     not-accessible
   STATUS     mandatory
   DESCRIPTION
     "An entry in the lpTrOperStatusTable."
   INDEX {
      lpIndex,
      lpTrIndex }
::= { lpTrOperStatusTable 1 }

LpTrOperStatusEntry ::= SEQUENCE {
   lpTrSnmpOperStatus
      INTEGER }

lpTrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpTrOperStatusEntry 1 }

lpTrOperTable OBJECT-TYPE
   SYNTAX     SEQUENCE OF LpTrOperEntry
   ACCESS     not-accessible
   STATUS     mandatory
   DESCRIPTION
     "This group contains the operational attributes of the Token 		Ring 
      component."
::= { lpTr 17 }

lpTrOperEntry OBJECT-TYPE
   SYNTAX     LpTrOperEntry
   ACCESS     not-accessible
   STATUS     mandatory
   DESCRIPTION
     "An entry in the lpTrOperTable."
   INDEX {
      lpIndex,
      lpTrIndex }
::= { lpTrOperTable 1 }

LpTrOperEntry ::= SEQUENCE {
   lpTrMacAddress
      MacAddress,
   lpTrRingState
      INTEGER,
   lpTrRingStatus
      OCTET STRING,
   lpTrRingOpenStatus
      INTEGER,
   lpTrUpStream
      MacAddress,
   lpTrChipSet
      INTEGER,
   lpTrLastTimeBeaconSent
      EnterpriseDateAndTime }

lpTrMacAddress OBJECT-TYPE
   SYNTAX     MacAddress (SIZE (6))
   ACCESS     read-only
   STATUS     mandatory
   DESCRIPTION
     "This attribute contains the actual MAC address. The value is 
      assigned by the system if nodeAddress is not provisioned. This 
      address is displayed in canonical form. The non-canonical version 
      of this address is indicated in ncMacAddress."
   DEFVAL     { '000000000000'H }
::= { lpTrOperEntry 2 }

lpTrRingState OBJECT-TYPE
   SYNTAX     INTEGER  {
                 opened(1),
                 closed(2),
                 opening(3),
                 closing(4),
                 openFailure(5),
                 ringFailure(6) }
   ACCESS     read-only
   STATUS     mandatory
   DESCRIPTION
     "This attribute contains the value of the current interface state with 
      respect to entering or leaving the ring."
   DEFVAL     { ringFailure }
::= { lpTrOperEntry 4 }

lpTrRingStatus OBJECT-TYPE
   SYNTAX     OCTET STRING (SIZE (3))
   ACCESS     read-only
   STATUS     mandatory
   DESCRIPTION
     "This attribute contains the value of the current interface status after 
      the station has entered the ring. The value is a sum of values, one 
      for each currently applicable condition. Before the station attempts 
      an open this attribute has the value of noStatus.
      noProblems = 0,
      ringRecovery = 32,
      singleStation = 64,
      removeReceived = 256,
      reserved = 512,
      autoRemovalError = 1024,
      lobeWireFault = 2048,
      transmitBeacon = 4096,
      softError = 8192,
      hardError = 16384,
      signalLoss = 32768,
      noStatus = 131072

      Description of bits:
      noProblems(0)
      notused1(1)
      notused2(2)
      notused3(3)
      notused4(4)
      ringRecovery(5)
      singleStation(6)
      notused7(7)
      removeReceived(8)
      reserved(9)
      autoRemovalError(10)
      lobeWireFault(11)
      transmitBeacon(12)
      softError(13)
      hardError(14)
      signalLoss(15)
      notused16(16)
      noStatus(17)"
   DEFVAL     { '000040'H }
::= { lpTrOperEntry 5 }

lpTrRingOpenStatus OBJECT-TYPE
   SYNTAX     INTEGER  {
                 noOpen(1),
                 badParam(2),
                 lobeFailed(3),
                 signalLoss(4),
                 insertionTimeout(5),
                 ringFailed(6),
                 beaconing(7),
                 duplicateMac(8),
                 requestFailed(9),
                 removeReceived(10),
                 open(11) }
   ACCESS     read-only
   STATUS     mandatory
   DESCRIPTION
     "This attribute indicates what happened the last time the station 
      attempted to enter into the ring."
   DEFVAL     { noOpen }
::= { lpTrOperEntry 6 }

lpTrUpStream OBJECT-TYPE
   SYNTAX     MacAddress (SIZE (6))
   ACCESS     read-only
   STATUS     mandatory
   DESCRIPTION
     "This attribute is the MAC address of the station's up-stream 
      neighbor. This address is displayed in canonical form. The non-
      canonical version of this address is indicated in ncUpStream."
   DEFVAL     { '000000000000'H }
::= { lpTrOperEntry 7 }

lpTrChipSet OBJECT-TYPE
   SYNTAX     INTEGER  {
                 ibm16(1),
                 titms380(2),
                 titms380c16(3),
                 titms380c26(4) }
   ACCESS     read-only
   STATUS     mandatory
   DESCRIPTION
     "This attribute identifies the hardware chip set in use by an interface."
   DEFVAL     { titms380c16 }
::= { lpTrOperEntry 9 }

lpTrLastTimeBeaconSent OBJECT-TYPE
   SYNTAX     EnterpriseDateAndTime (SIZE (0 | 19))
   ACCESS     read-only
   STATUS     mandatory
   DESCRIPTION
     "This attribute indicates the time at which a Beacon frame was last 
      transmitted on this interface."
::= { lpTrOperEntry 10 }

lpTrStatsTable OBJECT-TYPE
   SYNTAX     SEQUENCE OF LpTrStatsEntry
   ACCESS     not-accessible
   STATUS     mandatory
   DESCRIPTION
     "This group contains statistical information for the Token 		Ring port."
::= { lpTr 18 }

lpTrStatsEntry OBJECT-TYPE
   SYNTAX     LpTrStatsEntry
   ACCESS     not-accessible
   STATUS     mandatory
   DESCRIPTION
     "An entry in the lpTrStatsTable."
   INDEX {
      lpIndex,
      lpTrIndex }
::= { lpTrStatsTable 1 }

LpTrStatsEntry ::= SEQUENCE {
   lpTrLineErrors
      Counter32,
   lpTrBurstErrors
      Counter32,
   lpTrAcErrors
      Counter32,
   lpTrAbortTransErrors
      Counter32,
   lpTrInternalErrors
      Counter32,
   lpTrLostFrameErrors
      Counter32,
   lpTrReceiveCongestions
      Counter32,
   lpTrFrameCopiedErrors
      Counter32,
   lpTrTokenErrors
      Counter32,
   lpTrSoftErrors
      Counter32,
   lpTrHardErrors
      Counter32,
   lpTrSignalLoss
      Counter32,
   lpTrTransmitBeacons
      Counter32,
   lpTrRingRecoverys
      Counter32,
   lpTrLobeWires
      Counter32,
   lpTrRemoveRings
      Counter32,
   lpTrSingleStation
      Counter32,
   lpTrFreqErrors
      Counter32 }

lpTrLineErrors OBJECT-TYPE
   SYNTAX     Counter32 
   ACCESS     read-only
   STATUS     mandatory
   DESCRIPTION
     "This attribute contains the number of frames or tokens copied or 
      repeated by a station where there is a non-data bit or a FCS error. 
      This counter wraps around when the maximum value is reached."
::= { lpTrStatsEntry 2 }

lpTrBurstErrors OBJECT-TYPE
   SYNTAX     Counter32 
   ACCESS     read-only
   STATUS     mandatory
   DESCRIPTION
     "This attribute contains the number of times the station detects the 
      absence of transitions for five consecutive half-bit times. This 
      counter wraps around when the maximum value is reached."
::= { lpTrStatsEntry 3 }

lpTrAcErrors OBJECT-TYPE
   SYNTAX     Counter32 
   ACCESS     read-only
   STATUS     mandatory
   DESCRIPTION
     "This attribute contains the number of times that a station can not set 
      the AC bits properly. This counter wraps around when the 
      maximum value is reached."
::= { lpTrStatsEntry 4 }

lpTrAbortTransErrors OBJECT-TYPE
   SYNTAX     Counter32 
   ACCESS     read-only
   STATUS     mandatory
   DESCRIPTION
     "This attribute contains the number of aborted frames. This counter 
      wraps around when the maximum value is reached."
::= { lpTrStatsEntry 5 }

lpTrInternalErrors OBJECT-TYPE
   SYNTAX     Counter32 
   ACCESS     read-only
   STATUS     mandatory
   DESCRIPTION
     "This attribute contains the number of internal errors. When the 
      value of the counter soars up quickly, it indicates a potential 
      hardware problem. This counter wraps around when the maximum 
      value is reached."
::= { lpTrStatsEntry 6 }

lpTrLostFrameErrors OBJECT-TYPE
   SYNTAX     Counter32 
   ACCESS     read-only
   STATUS     mandatory
   DESCRIPTION
     "This attribute contains the number of times a station is transmitting 
      and its TRR timer expires. This counter wraps around when the 
      maximum value is reached."
::= { lpTrStatsEntry 7 }

lpTrReceiveCongestions OBJECT-TYPE
   SYNTAX     Counter32 
   ACCESS     read-only
   STATUS     mandatory
   DESCRIPTION
     "This attribute contains the number of times a station is supposed to 
      receive a frame but cannot due to lack of buffer space. This counter 
      wraps around when the maximum value is reached."
::= { lpTrStatsEntry 8 }

lpTrFrameCopiedErrors OBJECT-TYPE
   SYNTAX     Counter32 
   ACCESS     read-only
   STATUS     mandatory
   DESCRIPTION
     "This attribute contains the number of times a station receives a 
      frame addressed to its specific address and detects that the A bit is 
      set. This counter wraps around when the maximum value is 
      reached."
::= { lpTrStatsEntry 9 }

lpTrTokenErrors OBJECT-TYPE
   SYNTAX     Counter32 
   ACCESS     read-only
   STATUS     mandatory
   DESCRIPTION
     "This attribute contains the number of times a station acting as the 
      active monitor recognizes an error condition that needs a token 
      transmission. This counter wraps around when the maximum value 
      is reached."
::= { lpTrStatsEntry 10 }

lpTrSoftErrors OBJECT-TYPE
   SYNTAX     Counter32 
   ACCESS     read-only
   STATUS     mandatory
   DESCRIPTION
     "This attribute contains the number of soft errors or the number of 
      Report Error Mac frames the station has transmitted. This counter 
      wraps around when the maximum value is reached."
::= { lpTrStatsEntry 11 }

lpTrHardErrors OBJECT-TYPE
   SYNTAX     Counter32 
   ACCESS     read-only
   STATUS     mandatory
   DESCRIPTION
     "This attribute contains the number of times this interface has 
      detected an immediately recoverable fatal error. This counter wraps 
      around when the maximum value is reached."
::= { lpTrStatsEntry 12 }

lpTrSignalLoss OBJECT-TYPE
   SYNTAX     Counter32 
   ACCESS     read-only
   STATUS     mandatory
   DESCRIPTION
     "This attribute contains the number of times signal condition has 
      been lost. This counter wraps around when the maximum value is 
      reached."
::= { lpTrStatsEntry 13 }

lpTrTransmitBeacons OBJECT-TYPE
   SYNTAX     Counter32 
   ACCESS     read-only
   STATUS     mandatory
   DESCRIPTION
     "This attribute contains the number of beacon frames transmitted. 
      This counter wraps around when the maximum value is reached."
::= { lpTrStatsEntry 14 }

lpTrRingRecoverys OBJECT-TYPE
   SYNTAX     Counter32 
   ACCESS     read-only
   STATUS     mandatory
   DESCRIPTION
     "This attribute contains the number of times the ring has been 
      purged. This counter wraps around when the maximum value is 
      reached."
::= { lpTrStatsEntry 15 }

lpTrLobeWires OBJECT-TYPE
   SYNTAX     Counter32 
   ACCESS     read-only
   STATUS     mandatory
   DESCRIPTION
     "This attribute contains the number of times the interface has 
      detected a short circuit in the lobe data path. This counter wraps 
      around when the maximum value is reached."
::= { lpTrStatsEntry 16 }

lpTrRemoveRings OBJECT-TYPE
   SYNTAX     Counter32 
   ACCESS     read-only
   STATUS     mandatory
   DESCRIPTION
     "This attribute contains the number of Remove Ring Station Mac 
      frames received. This counter wraps around when the maximum 
      value is reached."
::= { lpTrStatsEntry 17 }

lpTrSingleStation OBJECT-TYPE
   SYNTAX     Counter32 
   ACCESS     read-only
   STATUS     mandatory
   DESCRIPTION
     "This attribute contains the number of times the station has 
      determined it is the only one on the ring. This is not necessarily an 
      error. This counter wraps around when the maximum value is 
      reached."
::= { lpTrStatsEntry 18 }

lpTrFreqErrors OBJECT-TYPE
   SYNTAX     Counter32 
   ACCESS     read-only
   STATUS     mandatory
   DESCRIPTION
     "This attribute contains the number of signal frequency errors 
      detected. This counter wraps around when the maximum value is 
      reached."
::= { lpTrStatsEntry 19 }

lpTrNcMacOperTable OBJECT-TYPE
   SYNTAX     SEQUENCE OF LpTrNcMacOperEntry
   ACCESS     not-accessible
   STATUS     mandatory
   DESCRIPTION
     "This group contains the operational attributes of the TokenRing port 
      component related to non-canonical MAC addresses."
::= { lpTr 20 }

lpTrNcMacOperEntry OBJECT-TYPE
   SYNTAX     LpTrNcMacOperEntry
   ACCESS     not-accessible
   STATUS     mandatory
   DESCRIPTION
     "An entry in the lpTrNcMacOperTable."
   INDEX {
      lpIndex,
      lpTrIndex }
::= { lpTrNcMacOperTable 1 }

LpTrNcMacOperEntry ::= SEQUENCE {
   lpTrNcMacAddress
      MacAddress,
   lpTrNcUpStream
      MacAddress }

lpTrNcMacAddress OBJECT-TYPE
   SYNTAX     MacAddress (SIZE (6))
   ACCESS     read-only
   STATUS     mandatory
   DESCRIPTION
     "This attribute contains the actual MAC address. The value is 
      assigned by the system if nodeAddress is not provisioned. This 
      address is displayed in non-canonical form. The canonical version 
      of this address is indicated in macAddress."
::= { lpTrNcMacOperEntry 1 }

lpTrNcUpStream OBJECT-TYPE
   SYNTAX     MacAddress (SIZE (6))
   ACCESS     read-only
   STATUS     mandatory
   DESCRIPTION
     "This attribute is the MAC address of the station's up-stream 
      neighbor. This address is displayed in non-canonical form. The 
      canonical version of this address is indicated in upStream."
::= { lpTrNcMacOperEntry 2 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

lpTrLt OBJECT IDENTIFIER ::= { lpTr 2 }



lpTrLtRowStatusTable OBJECT-TYPE
   SYNTAX     SEQUENCE OF LpTrLtRowStatusEntry
   ACCESS     not-accessible
   STATUS     mandatory
   DESCRIPTION
     "This entry controls the addition and deletion of 
      lpTrLt components."
::= { lpTrLt 1 }

lpTrLtRowStatusEntry OBJECT-TYPE
   SYNTAX     LpTrLtRowStatusEntry
   ACCESS     not-accessible
   STATUS     mandatory
   DESCRIPTION
     "A single entry in the table represents a single 
      lpTrLt component."
   INDEX {
      lpIndex,
      lpTrIndex,
      lpTrLtIndex }
::= { lpTrLtRowStatusTable 1 }

LpTrLtRowStatusEntry ::= SEQUENCE {
   lpTrLtRowStatus
      RowStatus,
   lpTrLtComponentName
      DisplayString,
   lpTrLtStorageType
      StorageType,
   lpTrLtIndex
      NonReplicated }

lpTrLtRowStatus OBJECT-TYPE
   SYNTAX     RowStatus 
   ACCESS     read-only
   STATUS     mandatory
   DESCRIPTION
     "This variable is used as the basis for SNMP naming of
      lpTrLt components.
      These components cannot be added nor deleted."
::= { lpTrLtRowStatusEntry 1 }

lpTrLtComponentName OBJECT-TYPE
   SYNTAX     DisplayString 
   ACCESS     read-only
   STATUS     mandatory
   DESCRIPTION
     "This variable provides the component's string name for
      use with the ASCII Console Interface"
::= { lpTrLtRowStatusEntry 2 }

lpTrLtStorageType OBJECT-TYPE
   SYNTAX     StorageType 
   ACCESS     read-only
   STATUS     mandatory
   DESCRIPTION
     "This variable represents the storage type value for the
      lpTrLt tables."
::= { lpTrLtRowStatusEntry 4 }

lpTrLtIndex OBJECT-TYPE
   SYNTAX     NonReplicated 
   ACCESS     not-accessible
   STATUS     mandatory
   DESCRIPTION
     "This variable represents the index for the lpTrLt tables."
::= { lpTrLtRowStatusEntry 10 }

lpTrLtTopTable OBJECT-TYPE
   SYNTAX     SEQUENCE OF LpTrLtTopEntry
   ACCESS     not-accessible
   STATUS     mandatory
   DESCRIPTION
     "This group contains the operational data for the LanTest component 
      and its subcomponents."
::= { lpTrLt 20 }

lpTrLtTopEntry OBJECT-TYPE
   SYNTAX     LpTrLtTopEntry
   ACCESS     not-accessible
   STATUS     mandatory
   DESCRIPTION
     "An entry in the lpTrLtTopTable."
   INDEX {
      lpIndex,
      lpTrIndex,
      lpTrLtIndex }
::= { lpTrLtTopTable 1 }

LpTrLtTopEntry ::= SEQUENCE {
   lpTrLtTData
      AsciiString }

lpTrLtTData OBJECT-TYPE
   SYNTAX     AsciiString (SIZE (0..255))
   ACCESS     read-write
   STATUS     mandatory
   DESCRIPTION
     "This attribute is used to display and set attributes."
::= { lpTrLtTopEntry 1 }


-- This component compares frames received from the hardware and 
-- emulator during testing.

lpTrLtFrmCmp OBJECT IDENTIFIER ::= { lpTrLt 2 }



lpTrLtFrmCmpRowStatusTable OBJECT-TYPE
   SYNTAX     SEQUENCE OF LpTrLtFrmCmpRowStatusEntry
   ACCESS     not-accessible
   STATUS     mandatory
   DESCRIPTION
     "This entry controls the addition and deletion of 
      lpTrLtFrmCmp components."
::= { lpTrLtFrmCmp 1 }

lpTrLtFrmCmpRowStatusEntry OBJECT-TYPE
   SYNTAX     LpTrLtFrmCmpRowStatusEntry
   ACCESS     not-accessible
   STATUS     mandatory
   DESCRIPTION
     "A single entry in the table represents a single 
      lpTrLtFrmCmp component."
   INDEX {
      lpIndex,
      lpTrIndex,
      lpTrLtIndex,
      lpTrLtFrmCmpIndex }
::= { lpTrLtFrmCmpRowStatusTable 1 }

LpTrLtFrmCmpRowStatusEntry ::= SEQUENCE {
   lpTrLtFrmCmpRowStatus
      RowStatus,
   lpTrLtFrmCmpComponentName
      DisplayString,
   lpTrLtFrmCmpStorageType
      StorageType,
   lpTrLtFrmCmpIndex
      NonReplicated }

lpTrLtFrmCmpRowStatus OBJECT-TYPE
   SYNTAX     RowStatus 
   ACCESS     read-only
   STATUS     mandatory
   DESCRIPTION
     "This variable is used as the basis for SNMP naming of
      lpTrLtFrmCmp components.
      These components cannot be added nor deleted."
::= { lpTrLtFrmCmpRowStatusEntry 1 }

lpTrLtFrmCmpComponentName OBJECT-TYPE
   SYNTAX     DisplayString 
   ACCESS     read-only
   STATUS     mandatory
   DESCRIPTION
     "This variable provides the component's string name for
      use with the ASCII Console Interface"
::= { lpTrLtFrmCmpRowStatusEntry 2 }

lpTrLtFrmCmpStorageType OBJECT-TYPE
   SYNTAX     StorageType 
   ACCESS     read-only
   STATUS     mandatory
   DESCRIPTION
     "This variable represents the storage type value for the
      lpTrLtFrmCmp tables."
::= { lpTrLtFrmCmpRowStatusEntry 4 }

lpTrLtFrmCmpIndex OBJECT-TYPE
   SYNTAX     NonReplicated 
   ACCESS     not-accessible
   STATUS     mandatory
   DESCRIPTION
     "This variable represents the index for the lpTrLtFrmCmp tables."
::= { lpTrLtFrmCmpRowStatusEntry 10 }

lpTrLtFrmCmpTopTable OBJECT-TYPE
   SYNTAX     SEQUENCE OF LpTrLtFrmCmpTopEntry
   ACCESS     not-accessible
   STATUS     mandatory
   DESCRIPTION
     "This group contains the operational data for the LanTest component 
      and its subcomponents."
::= { lpTrLtFrmCmp 10 }

lpTrLtFrmCmpTopEntry OBJECT-TYPE
   SYNTAX     LpTrLtFrmCmpTopEntry
   ACCESS     not-accessible
   STATUS     mandatory
   DESCRIPTION
     "An entry in the lpTrLtFrmCmpTopTable."
   INDEX {
      lpIndex,
      lpTrIndex,
      lpTrLtIndex,
      lpTrLtFrmCmpIndex }
::= { lpTrLtFrmCmpTopTable 1 }

LpTrLtFrmCmpTopEntry ::= SEQUENCE {
   lpTrLtFrmCmpTData
      AsciiString }

lpTrLtFrmCmpTData OBJECT-TYPE
   SYNTAX     AsciiString (SIZE (0..255))
   ACCESS     read-write
   STATUS     mandatory
   DESCRIPTION
     "This attribute is used to display and set attributes."
::= { lpTrLtFrmCmpTopEntry 1 }


-- This component receives its input from FrameBuild and places it 
-- upon the hardware which sends it to the appropriate emulator.

lpTrLtFrmCpy OBJECT IDENTIFIER ::= { lpTrLt 3 }



lpTrLtFrmCpyRowStatusTable OBJECT-TYPE
   SYNTAX     SEQUENCE OF LpTrLtFrmCpyRowStatusEntry
   ACCESS     not-accessible
   STATUS     mandatory
   DESCRIPTION
     "This entry controls the addition and deletion of 
      lpTrLtFrmCpy components."
::= { lpTrLtFrmCpy 1 }

lpTrLtFrmCpyRowStatusEntry OBJECT-TYPE
   SYNTAX     LpTrLtFrmCpyRowStatusEntry
   ACCESS     not-accessible
   STATUS     mandatory
   DESCRIPTION
     "A single entry in the table represents a single 
      lpTrLtFrmCpy component."
   INDEX {
      lpIndex,
      lpTrIndex,
      lpTrLtIndex,
      lpTrLtFrmCpyIndex }
::= { lpTrLtFrmCpyRowStatusTable 1 }

LpTrLtFrmCpyRowStatusEntry ::= SEQUENCE {
   lpTrLtFrmCpyRowStatus
      RowStatus,
   lpTrLtFrmCpyComponentName
      DisplayString,
   lpTrLtFrmCpyStorageType
      StorageType,
   lpTrLtFrmCpyIndex
      NonReplicated }

lpTrLtFrmCpyRowStatus OBJECT-TYPE
   SYNTAX     RowStatus 
   ACCESS     read-only
   STATUS     mandatory
   DESCRIPTION
     "This variable is used as the basis for SNMP naming of
      lpTrLtFrmCpy components.
      These components cannot be added nor deleted."
::= { lpTrLtFrmCpyRowStatusEntry 1 }

lpTrLtFrmCpyComponentName OBJECT-TYPE
   SYNTAX     DisplayString 
   ACCESS     read-only
   STATUS     mandatory
   DESCRIPTION
     "This variable provides the component's string name for
      use with the ASCII Console Interface"
::= { lpTrLtFrmCpyRowStatusEntry 2 }

lpTrLtFrmCpyStorageType OBJECT-TYPE
   SYNTAX     StorageType 
   ACCESS     read-only
   STATUS     mandatory
   DESCRIPTION
     "This variable represents the storage type value for the
      lpTrLtFrmCpy tables."
::= { lpTrLtFrmCpyRowStatusEntry 4 }

lpTrLtFrmCpyIndex OBJECT-TYPE
   SYNTAX     NonReplicated 
   ACCESS     not-accessible
   STATUS     mandatory
   DESCRIPTION
     "This variable represents the index for the lpTrLtFrmCpy tables."
::= { lpTrLtFrmCpyRowStatusEntry 10 }

lpTrLtFrmCpyTopTable OBJECT-TYPE
   SYNTAX     SEQUENCE OF LpTrLtFrmCpyTopEntry
   ACCESS     not-accessible
   STATUS     mandatory
   DESCRIPTION
     "This group contains the operational data for the LanTest component 
      and its subcomponents."
::= { lpTrLtFrmCpy 10 }

lpTrLtFrmCpyTopEntry OBJECT-TYPE
   SYNTAX     LpTrLtFrmCpyTopEntry
   ACCESS     not-accessible
   STATUS     mandatory
   DESCRIPTION
     "An entry in the lpTrLtFrmCpyTopTable."
   INDEX {
      lpIndex,
      lpTrIndex,
      lpTrLtIndex,
      lpTrLtFrmCpyIndex }
::= { lpTrLtFrmCpyTopTable 1 }

LpTrLtFrmCpyTopEntry ::= SEQUENCE {
   lpTrLtFrmCpyTData
      AsciiString }

lpTrLtFrmCpyTData OBJECT-TYPE
   SYNTAX     AsciiString (SIZE (0..255))
   ACCESS     read-write
   STATUS     mandatory
   DESCRIPTION
     "This attribute is used to display and set attributes."
::= { lpTrLtFrmCpyTopEntry 1 }


-- This component controls the emulator and hardware to ensure 
-- frames output from each will match in FrameCompare.

lpTrLtPrtCfg OBJECT IDENTIFIER ::= { lpTrLt 4 }



lpTrLtPrtCfgRowStatusTable OBJECT-TYPE
   SYNTAX     SEQUENCE OF LpTrLtPrtCfgRowStatusEntry
   ACCESS     not-accessible
   STATUS     mandatory
   DESCRIPTION
     "This entry controls the addition and deletion of 
      lpTrLtPrtCfg components."
::= { lpTrLtPrtCfg 1 }

lpTrLtPrtCfgRowStatusEntry OBJECT-TYPE
   SYNTAX     LpTrLtPrtCfgRowStatusEntry
   ACCESS     not-accessible
   STATUS     mandatory
   DESCRIPTION
     "A single entry in the table represents a single 
      lpTrLtPrtCfg component."
   INDEX {
      lpIndex,
      lpTrIndex,
      lpTrLtIndex,
      lpTrLtPrtCfgIndex }
::= { lpTrLtPrtCfgRowStatusTable 1 }

LpTrLtPrtCfgRowStatusEntry ::= SEQUENCE {
   lpTrLtPrtCfgRowStatus
      RowStatus,
   lpTrLtPrtCfgComponentName
      DisplayString,
   lpTrLtPrtCfgStorageType
      StorageType,
   lpTrLtPrtCfgIndex
      NonReplicated }

lpTrLtPrtCfgRowStatus OBJECT-TYPE
   SYNTAX     RowStatus 
   ACCESS     read-only
   STATUS     mandatory
   DESCRIPTION
     "This variable is used as the basis for SNMP naming of
      lpTrLtPrtCfg components.
      These components cannot be added nor deleted."
::= { lpTrLtPrtCfgRowStatusEntry 1 }

lpTrLtPrtCfgComponentName OBJECT-TYPE
   SYNTAX     DisplayString 
   ACCESS     read-only
   STATUS     mandatory
   DESCRIPTION
     "This variable provides the component's string name for
      use with the ASCII Console Interface"
::= { lpTrLtPrtCfgRowStatusEntry 2 }

lpTrLtPrtCfgStorageType OBJECT-TYPE
   SYNTAX     StorageType 
   ACCESS     read-only
   STATUS     mandatory
   DESCRIPTION
     "This variable represents the storage type value for the
      lpTrLtPrtCfg tables."
::= { lpTrLtPrtCfgRowStatusEntry 4 }

lpTrLtPrtCfgIndex OBJECT-TYPE
   SYNTAX     NonReplicated 
   ACCESS     not-accessible
   STATUS     mandatory
   DESCRIPTION
     "This variable represents the index for the lpTrLtPrtCfg tables."
::= { lpTrLtPrtCfgRowStatusEntry 10 }

lpTrLtPrtCfgTopTable OBJECT-TYPE
   SYNTAX     SEQUENCE OF LpTrLtPrtCfgTopEntry
   ACCESS     not-accessible
   STATUS     mandatory
   DESCRIPTION
     "This group contains the operational data for the LanTest component 
      and its subcomponents."
::= { lpTrLtPrtCfg 10 }

lpTrLtPrtCfgTopEntry OBJECT-TYPE
   SYNTAX     LpTrLtPrtCfgTopEntry
   ACCESS     not-accessible
   STATUS     mandatory
   DESCRIPTION
     "An entry in the lpTrLtPrtCfgTopTable."
   INDEX {
      lpIndex,
      lpTrIndex,
      lpTrLtIndex,
      lpTrLtPrtCfgIndex }
::= { lpTrLtPrtCfgTopTable 1 }

LpTrLtPrtCfgTopEntry ::= SEQUENCE {
   lpTrLtPrtCfgTData
      AsciiString }

lpTrLtPrtCfgTData OBJECT-TYPE
   SYNTAX     AsciiString (SIZE (0..255))
   ACCESS     read-write
   STATUS     mandatory
   DESCRIPTION
     "This attribute is used to display and set attributes."
::= { lpTrLtPrtCfgTopEntry 1 }


-- LanTest Framebuild
-- This component controls the building of all frames built and sent by 
-- the LanTest component. Each component under FrameBuild builds 
-- a portion of a packet or frame.

lpTrLtFb OBJECT IDENTIFIER ::= { lpTrLt 5 }



lpTrLtFbRowStatusTable OBJECT-TYPE
   SYNTAX     SEQUENCE OF LpTrLtFbRowStatusEntry
   ACCESS     not-accessible
   STATUS     mandatory
   DESCRIPTION
     "This entry controls the addition and deletion of 
      lpTrLtFb components."
::= { lpTrLtFb 1 }

lpTrLtFbRowStatusEntry OBJECT-TYPE
   SYNTAX     LpTrLtFbRowStatusEntry
   ACCESS     not-accessible
   STATUS     mandatory
   DESCRIPTION
     "A single entry in the table represents a single 
      lpTrLtFb component."
   INDEX {
      lpIndex,
      lpTrIndex,
      lpTrLtIndex,
      lpTrLtFbIndex }
::= { lpTrLtFbRowStatusTable 1 }

LpTrLtFbRowStatusEntry ::= SEQUENCE {
   lpTrLtFbRowStatus
      RowStatus,
   lpTrLtFbComponentName
      DisplayString,
   lpTrLtFbStorageType
      StorageType,
   lpTrLtFbIndex
      NonReplicated }

lpTrLtFbRowStatus OBJECT-TYPE
   SYNTAX     RowStatus 
   ACCESS     read-only
   STATUS     mandatory
   DESCRIPTION
     "This variable is used as the basis for SNMP naming of
      lpTrLtFb components.
      These components cannot be added nor deleted."
::= { lpTrLtFbRowStatusEntry 1 }

lpTrLtFbComponentName OBJECT-TYPE
   SYNTAX     DisplayString 
   ACCESS     read-only
   STATUS     mandatory
   DESCRIPTION
     "This variable provides the component's string name for
      use with the ASCII Console Interface"
::= { lpTrLtFbRowStatusEntry 2 }

lpTrLtFbStorageType OBJECT-TYPE
   SYNTAX     StorageType 
   ACCESS     read-only
   STATUS     mandatory
   DESCRIPTION
     "This variable represents the storage type value for the
      lpTrLtFb tables."
::= { lpTrLtFbRowStatusEntry 4 }

lpTrLtFbIndex OBJECT-TYPE
   SYNTAX     NonReplicated 
   ACCESS     not-accessible
   STATUS     mandatory
   DESCRIPTION
     "This variable represents the index for the lpTrLtFb tables."
::= { lpTrLtFbRowStatusEntry 10 }

lpTrLtFbTopTable OBJECT-TYPE
   SYNTAX     SEQUENCE OF LpTrLtFbTopEntry
   ACCESS     not-accessible
   STATUS     mandatory
   DESCRIPTION
     "This group contains the operational data for the LanTest component 
      and its subcomponents."
::= { lpTrLtFb 20 }

lpTrLtFbTopEntry OBJECT-TYPE
   SYNTAX     LpTrLtFbTopEntry
   ACCESS     not-accessible
   STATUS     mandatory
   DESCRIPTION
     "An entry in the lpTrLtFbTopTable."
   INDEX {
      lpIndex,
      lpTrIndex,
      lpTrLtIndex,
      lpTrLtFbIndex }
::= { lpTrLtFbTopTable 1 }

LpTrLtFbTopEntry ::= SEQUENCE {
   lpTrLtFbTData
      AsciiString }

lpTrLtFbTData OBJECT-TYPE
   SYNTAX     AsciiString (SIZE (0..255))
   ACCESS     read-write
   STATUS     mandatory
   DESCRIPTION
     "This attribute is used to display and set attributes."
::= { lpTrLtFbTopEntry 1 }


-- LanTest TransmitInfo
-- This component builds a transmit header which is attached to all 
-- frames transmitted on LAN interfaces.

lpTrLtFbTxInfo OBJECT IDENTIFIER ::= { lpTrLtFb 2 }



lpTrLtFbTxInfoRowStatusTable OBJECT-TYPE
   SYNTAX     SEQUENCE OF LpTrLtFbTxInfoRowStatusEntry
   ACCESS     not-accessible
   STATUS     mandatory
   DESCRIPTION
     "This entry controls the addition and deletion of 
      lpTrLtFbTxInfo components."
::= { lpTrLtFbTxInfo 1 }

lpTrLtFbTxInfoRowStatusEntry OBJECT-TYPE
   SYNTAX     LpTrLtFbTxInfoRowStatusEntry
   ACCESS     not-accessible
   STATUS     mandatory
   DESCRIPTION
     "A single entry in the table represents a single 
      lpTrLtFbTxInfo component."
   INDEX {
      lpIndex,
      lpTrIndex,
      lpTrLtIndex,
      lpTrLtFbIndex,
      lpTrLtFbTxInfoIndex }
::= { lpTrLtFbTxInfoRowStatusTable 1 }

LpTrLtFbTxInfoRowStatusEntry ::= SEQUENCE {
   lpTrLtFbTxInfoRowStatus
      RowStatus,
   lpTrLtFbTxInfoComponentName
      DisplayString,
   lpTrLtFbTxInfoStorageType
      StorageType,
   lpTrLtFbTxInfoIndex
      NonReplicated }

lpTrLtFbTxInfoRowStatus OBJECT-TYPE
   SYNTAX     RowStatus 
   ACCESS     read-only
   STATUS     mandatory
   DESCRIPTION
     "This variable is used as the basis for SNMP naming of
      lpTrLtFbTxInfo components.
      These components cannot be added nor deleted."
::= { lpTrLtFbTxInfoRowStatusEntry 1 }

lpTrLtFbTxInfoComponentName OBJECT-TYPE
   SYNTAX     DisplayString 
   ACCESS     read-only
   STATUS     mandatory
   DESCRIPTION
     "This variable provides the component's string name for
      use with the ASCII Console Interface"
::= { lpTrLtFbTxInfoRowStatusEntry 2 }

lpTrLtFbTxInfoStorageType OBJECT-TYPE
   SYNTAX     StorageType 
   ACCESS     read-only
   STATUS     mandatory
   DESCRIPTION
     "This variable represents the storage type value for the
      lpTrLtFbTxInfo tables."
::= { lpTrLtFbTxInfoRowStatusEntry 4 }

lpTrLtFbTxInfoIndex OBJECT-TYPE
   SYNTAX     NonReplicated 
   ACCESS     not-accessible
   STATUS     mandatory
   DESCRIPTION
     "This variable represents the index for the lpTrLtFbTxInfo tables."
::= { lpTrLtFbTxInfoRowStatusEntry 10 }

lpTrLtFbTxInfoTopTable OBJECT-TYPE
   SYNTAX     SEQUENCE OF LpTrLtFbTxInfoTopEntry
   ACCESS     not-accessible
   STATUS     mandatory
   DESCRIPTION
     "This group contains the operational data for the LanTest component 
      and its subcomponents."
::= { lpTrLtFbTxInfo 10 }

lpTrLtFbTxInfoTopEntry OBJECT-TYPE
   SYNTAX     LpTrLtFbTxInfoTopEntry
   ACCESS     not-accessible
   STATUS     mandatory
   DESCRIPTION
     "An entry in the lpTrLtFbTxInfoTopTable."
   INDEX {
      lpIndex,
      lpTrIndex,
      lpTrLtIndex,
      lpTrLtFbIndex,
      lpTrLtFbTxInfoIndex }
::= { lpTrLtFbTxInfoTopTable 1 }

LpTrLtFbTxInfoTopEntry ::= SEQUENCE {
   lpTrLtFbTxInfoTData
      AsciiString }

lpTrLtFbTxInfoTData OBJECT-TYPE
   SYNTAX     AsciiString (SIZE (0..255))
   ACCESS     read-write
   STATUS     mandatory
   DESCRIPTION
     "This attribute is used to display and set attributes."
::= { lpTrLtFbTxInfoTopEntry 1 }


-- LanTest FddiMac
-- This component builds an FDDI MAC header which is attached to 
-- all FDDI frames.

lpTrLtFbFddiMac OBJECT IDENTIFIER ::= { lpTrLtFb 3 }



lpTrLtFbFddiMacRowStatusTable OBJECT-TYPE
   SYNTAX     SEQUENCE OF LpTrLtFbFddiMacRowStatusEntry
   ACCESS     not-accessible
   STATUS     mandatory
   DESCRIPTION
     "This entry controls the addition and deletion of 
      lpTrLtFbFddiMac components."
::= { lpTrLtFbFddiMac 1 }

lpTrLtFbFddiMacRowStatusEntry OBJECT-TYPE
   SYNTAX     LpTrLtFbFddiMacRowStatusEntry
   ACCESS     not-accessible
   STATUS     mandatory
   DESCRIPTION
     "A single entry in the table represents a single 
      lpTrLtFbFddiMac component."
   INDEX {
      lpIndex,
      lpTrIndex,
      lpTrLtIndex,
      lpTrLtFbIndex,
      lpTrLtFbFddiMacIndex }
::= { lpTrLtFbFddiMacRowStatusTable 1 }

LpTrLtFbFddiMacRowStatusEntry ::= SEQUENCE {
   lpTrLtFbFddiMacRowStatus
      RowStatus,
   lpTrLtFbFddiMacComponentName
      DisplayString,
   lpTrLtFbFddiMacStorageType
      StorageType,
   lpTrLtFbFddiMacIndex
      NonReplicated }

lpTrLtFbFddiMacRowStatus OBJECT-TYPE
   SYNTAX     RowStatus 
   ACCESS     read-only
   STATUS     mandatory
   DESCRIPTION
     "This variable is used as the basis for SNMP naming of
      lpTrLtFbFddiMac components.
      These components cannot be added nor deleted."
::= { lpTrLtFbFddiMacRowStatusEntry 1 }

lpTrLtFbFddiMacComponentName OBJECT-TYPE
   SYNTAX     DisplayString 
   ACCESS     read-only
   STATUS     mandatory
   DESCRIPTION
     "This variable provides the component's string name for
      use with the ASCII Console Interface"
::= { lpTrLtFbFddiMacRowStatusEntry 2 }

lpTrLtFbFddiMacStorageType OBJECT-TYPE
   SYNTAX     StorageType 
   ACCESS     read-only
   STATUS     mandatory
   DESCRIPTION
     "This variable represents the storage type value for the
      lpTrLtFbFddiMac tables."
::= { lpTrLtFbFddiMacRowStatusEntry 4 }

lpTrLtFbFddiMacIndex OBJECT-TYPE
   SYNTAX     NonReplicated 
   ACCESS     not-accessible
   STATUS     mandatory
   DESCRIPTION
     "This variable represents the index for the lpTrLtFbFddiMac tables."
::= { lpTrLtFbFddiMacRowStatusEntry 10 }

lpTrLtFbFddiMacTopTable OBJECT-TYPE
   SYNTAX     SEQUENCE OF LpTrLtFbFddiMacTopEntry
   ACCESS     not-accessible
   STATUS     mandatory
   DESCRIPTION
     "This group contains the operational data for the LanTest component 
      and its subcomponents."
::= { lpTrLtFbFddiMac 10 }

lpTrLtFbFddiMacTopEntry OBJECT-TYPE
   SYNTAX     LpTrLtFbFddiMacTopEntry
   ACCESS     not-accessible
   STATUS     mandatory
   DESCRIPTION
     "An entry in the lpTrLtFbFddiMacTopTable."
   INDEX {
      lpIndex,
      lpTrIndex,
      lpTrLtIndex,
      lpTrLtFbIndex,
      lpTrLtFbFddiMacIndex }
::= { lpTrLtFbFddiMacTopTable 1 }

LpTrLtFbFddiMacTopEntry ::= SEQUENCE {
   lpTrLtFbFddiMacTData
      AsciiString }

lpTrLtFbFddiMacTData OBJECT-TYPE
   SYNTAX     AsciiString (SIZE (0..255))
   ACCESS     read-write
   STATUS     mandatory
   DESCRIPTION
     "This attribute is used to display and set attributes."
::= { lpTrLtFbFddiMacTopEntry 1 }


-- LanTest EthernetMac
-- This component builds an Ethernet MAC header which is attached 
-- to all Ethernet frames.

lpTrLtFbMacEnet OBJECT IDENTIFIER ::= { lpTrLtFb 4 }



lpTrLtFbMacEnetRowStatusTable OBJECT-TYPE
   SYNTAX     SEQUENCE OF LpTrLtFbMacEnetRowStatusEntry
   ACCESS     not-accessible
   STATUS     mandatory
   DESCRIPTION
     "This entry controls the addition and deletion of 
      lpTrLtFbMacEnet components."
::= { lpTrLtFbMacEnet 1 }

lpTrLtFbMacEnetRowStatusEntry OBJECT-TYPE
   SYNTAX     LpTrLtFbMacEnetRowStatusEntry
   ACCESS     not-accessible
   STATUS     mandatory
   DESCRIPTION
     "A single entry in the table represents a single 
      lpTrLtFbMacEnet component."
   INDEX {
      lpIndex,
      lpTrIndex,
      lpTrLtIndex,
      lpTrLtFbIndex,
      lpTrLtFbMacEnetIndex }
::= { lpTrLtFbMacEnetRowStatusTable 1 }

LpTrLtFbMacEnetRowStatusEntry ::= SEQUENCE {
   lpTrLtFbMacEnetRowStatus
      RowStatus,
   lpTrLtFbMacEnetComponentName
      DisplayString,
   lpTrLtFbMacEnetStorageType
      StorageType,
   lpTrLtFbMacEnetIndex
      NonReplicated }

lpTrLtFbMacEnetRowStatus OBJECT-TYPE
   SYNTAX     RowStatus 
   ACCESS     read-only
   STATUS     mandatory
   DESCRIPTION
     "This variable is used as the basis for SNMP naming of
      lpTrLtFbMacEnet components.
      These components cannot be added nor deleted."
::= { lpTrLtFbMacEnetRowStatusEntry 1 }

lpTrLtFbMacEnetComponentName OBJECT-TYPE
   SYNTAX     DisplayString 
   ACCESS     read-only
   STATUS     mandatory
   DESCRIPTION
     "This variable provides the component's string name for
      use with the ASCII Console Interface"
::= { lpTrLtFbMacEnetRowStatusEntry 2 }

lpTrLtFbMacEnetStorageType OBJECT-TYPE
   SYNTAX     StorageType 
   ACCESS     read-only
   STATUS     mandatory
   DESCRIPTION
     "This variable represents the storage type value for the
      lpTrLtFbMacEnet tables."
::= { lpTrLtFbMacEnetRowStatusEntry 4 }

lpTrLtFbMacEnetIndex OBJECT-TYPE
   SYNTAX     NonReplicated 
   ACCESS     not-accessible
   STATUS     mandatory
   DESCRIPTION
     "This variable represents the index for the lpTrLtFbMacEnet tables."
::= { lpTrLtFbMacEnetRowStatusEntry 10 }

lpTrLtFbMacEnetTopTable OBJECT-TYPE
   SYNTAX     SEQUENCE OF LpTrLtFbMacEnetTopEntry
   ACCESS     not-accessible
   STATUS     mandatory
   DESCRIPTION
     "This group contains the operational data for the LanTest component 
      and its subcomponents."
::= { lpTrLtFbMacEnet 10 }

lpTrLtFbMacEnetTopEntry OBJECT-TYPE
   SYNTAX     LpTrLtFbMacEnetTopEntry
   ACCESS     not-accessible
   STATUS     mandatory
   DESCRIPTION
     "An entry in the lpTrLtFbMacEnetTopTable."
   INDEX {
      lpIndex,
      lpTrIndex,
      lpTrLtIndex,
      lpTrLtFbIndex,
      lpTrLtFbMacEnetIndex }
::= { lpTrLtFbMacEnetTopTable 1 }

LpTrLtFbMacEnetTopEntry ::= SEQUENCE {
   lpTrLtFbMacEnetTData
      AsciiString }

lpTrLtFbMacEnetTData OBJECT-TYPE
   SYNTAX     AsciiString (SIZE (0..255))
   ACCESS     read-write
   STATUS     mandatory
   DESCRIPTION
     "This attribute is used to display and set attributes."
::= { lpTrLtFbMacEnetTopEntry 1 }


-- LanTest TokenRingMac
-- This component builds a Token Ring MAC header which is attached 
-- to all Token Ring frames.

lpTrLtFbMacTr OBJECT IDENTIFIER ::= { lpTrLtFb 5 }



lpTrLtFbMacTrRowStatusTable OBJECT-TYPE
   SYNTAX     SEQUENCE OF LpTrLtFbMacTrRowStatusEntry
   ACCESS     not-accessible
   STATUS     mandatory
   DESCRIPTION
     "This entry controls the addition and deletion of 
      lpTrLtFbMacTr components."
::= { lpTrLtFbMacTr 1 }

lpTrLtFbMacTrRowStatusEntry OBJECT-TYPE
   SYNTAX     LpTrLtFbMacTrRowStatusEntry
   ACCESS     not-accessible
   STATUS     mandatory
   DESCRIPTION
     "A single entry in the table represents a single 
      lpTrLtFbMacTr component."
   INDEX {
      lpIndex,
      lpTrIndex,
      lpTrLtIndex,
      lpTrLtFbIndex,
      lpTrLtFbMacTrIndex }
::= { lpTrLtFbMacTrRowStatusTable 1 }

LpTrLtFbMacTrRowStatusEntry ::= SEQUENCE {
   lpTrLtFbMacTrRowStatus
      RowStatus,
   lpTrLtFbMacTrComponentName
      DisplayString,
   lpTrLtFbMacTrStorageType
      StorageType,
   lpTrLtFbMacTrIndex
      NonReplicated }

lpTrLtFbMacTrRowStatus OBJECT-TYPE
   SYNTAX     RowStatus 
   ACCESS     read-only
   STATUS     mandatory
   DESCRIPTION
     "This variable is used as the basis for SNMP naming of
      lpTrLtFbMacTr components.
      These components cannot be added nor deleted."
::= { lpTrLtFbMacTrRowStatusEntry 1 }

lpTrLtFbMacTrComponentName OBJECT-TYPE
   SYNTAX     DisplayString 
   ACCESS     read-only
   STATUS     mandatory
   DESCRIPTION
     "This variable provides the component's string name for
      use with the ASCII Console Interface"
::= { lpTrLtFbMacTrRowStatusEntry 2 }

lpTrLtFbMacTrStorageType OBJECT-TYPE
   SYNTAX     StorageType 
   ACCESS     read-only
   STATUS     mandatory
   DESCRIPTION
     "This variable represents the storage type value for the
      lpTrLtFbMacTr tables."
::= { lpTrLtFbMacTrRowStatusEntry 4 }

lpTrLtFbMacTrIndex OBJECT-TYPE
   SYNTAX     NonReplicated 
   ACCESS     not-accessible
   STATUS     mandatory
   DESCRIPTION
     "This variable represents the index for the lpTrLtFbMacTr tables."
::= { lpTrLtFbMacTrRowStatusEntry 10 }

lpTrLtFbMacTrTopTable OBJECT-TYPE
   SYNTAX     SEQUENCE OF LpTrLtFbMacTrTopEntry
   ACCESS     not-accessible
   STATUS     mandatory
   DESCRIPTION
     "This group contains the operational data for the LanTest component 
      and its subcomponents."
::= { lpTrLtFbMacTr 10 }

lpTrLtFbMacTrTopEntry OBJECT-TYPE
   SYNTAX     LpTrLtFbMacTrTopEntry
   ACCESS     not-accessible
   STATUS     mandatory
   DESCRIPTION
     "An entry in the lpTrLtFbMacTrTopTable."
   INDEX {
      lpIndex,
      lpTrIndex,
      lpTrLtIndex,
      lpTrLtFbIndex,
      lpTrLtFbMacTrIndex }
::= { lpTrLtFbMacTrTopTable 1 }

LpTrLtFbMacTrTopEntry ::= SEQUENCE {
   lpTrLtFbMacTrTData
      AsciiString }

lpTrLtFbMacTrTData OBJECT-TYPE
   SYNTAX     AsciiString (SIZE (0..255))
   ACCESS     read-write
   STATUS     mandatory
   DESCRIPTION
     "This attribute is used to display and set attributes."
::= { lpTrLtFbMacTrTopEntry 1 }


-- This component adds a data field to frame.

lpTrLtFbData OBJECT IDENTIFIER ::= { lpTrLtFb 6 }



lpTrLtFbDataRowStatusTable OBJECT-TYPE
   SYNTAX     SEQUENCE OF LpTrLtFbDataRowStatusEntry
   ACCESS     not-accessible
   STATUS     mandatory
   DESCRIPTION
     "This entry controls the addition and deletion of 
      lpTrLtFbData components."
::= { lpTrLtFbData 1 }

lpTrLtFbDataRowStatusEntry OBJECT-TYPE
   SYNTAX     LpTrLtFbDataRowStatusEntry
   ACCESS     not-accessible
   STATUS     mandatory
   DESCRIPTION
     "A single entry in the table represents a single 
      lpTrLtFbData component."
   INDEX {
      lpIndex,
      lpTrIndex,
      lpTrLtIndex,
      lpTrLtFbIndex,
      lpTrLtFbDataIndex }
::= { lpTrLtFbDataRowStatusTable 1 }

LpTrLtFbDataRowStatusEntry ::= SEQUENCE {
   lpTrLtFbDataRowStatus
      RowStatus,
   lpTrLtFbDataComponentName
      DisplayString,
   lpTrLtFbDataStorageType
      StorageType,
   lpTrLtFbDataIndex
      NonReplicated }

lpTrLtFbDataRowStatus OBJECT-TYPE
   SYNTAX     RowStatus 
   ACCESS     read-only
   STATUS     mandatory
   DESCRIPTION
     "This variable is used as the basis for SNMP naming of
      lpTrLtFbData components.
      These components cannot be added nor deleted."
::= { lpTrLtFbDataRowStatusEntry 1 }

lpTrLtFbDataComponentName OBJECT-TYPE
   SYNTAX     DisplayString 
   ACCESS     read-only
   STATUS     mandatory
   DESCRIPTION
     "This variable provides the component's string name for
      use with the ASCII Console Interface"
::= { lpTrLtFbDataRowStatusEntry 2 }

lpTrLtFbDataStorageType OBJECT-TYPE
   SYNTAX     StorageType 
   ACCESS     read-only
   STATUS     mandatory
   DESCRIPTION
     "This variable represents the storage type value for the
      lpTrLtFbData tables."
::= { lpTrLtFbDataRowStatusEntry 4 }

lpTrLtFbDataIndex OBJECT-TYPE
   SYNTAX     NonReplicated 
   ACCESS     not-accessible
   STATUS     mandatory
   DESCRIPTION
     "This variable represents the index for the lpTrLtFbData tables."
::= { lpTrLtFbDataRowStatusEntry 10 }

lpTrLtFbDataTopTable OBJECT-TYPE
   SYNTAX     SEQUENCE OF LpTrLtFbDataTopEntry
   ACCESS     not-accessible
   STATUS     mandatory
   DESCRIPTION
     "This group contains the operational data for the LanTest component 
      and its subcomponents."
::= { lpTrLtFbData 10 }

lpTrLtFbDataTopEntry OBJECT-TYPE
   SYNTAX     LpTrLtFbDataTopEntry
   ACCESS     not-accessible
   STATUS     mandatory
   DESCRIPTION
     "An entry in the lpTrLtFbDataTopTable."
   INDEX {
      lpIndex,
      lpTrIndex,
      lpTrLtIndex,
      lpTrLtFbIndex,
      lpTrLtFbDataIndex }
::= { lpTrLtFbDataTopTable 1 }

LpTrLtFbDataTopEntry ::= SEQUENCE {
   lpTrLtFbDataTData
      AsciiString }

lpTrLtFbDataTData OBJECT-TYPE
   SYNTAX     AsciiString (SIZE (0..255))
   ACCESS     read-write
   STATUS     mandatory
   DESCRIPTION
     "This attribute is used to display and set attributes."
::= { lpTrLtFbDataTopEntry 1 }


-- LanTest IpHeader
-- This component adds an IP header to a frame or packet.

lpTrLtFbIpH OBJECT IDENTIFIER ::= { lpTrLtFb 7 }



lpTrLtFbIpHRowStatusTable OBJECT-TYPE
   SYNTAX     SEQUENCE OF LpTrLtFbIpHRowStatusEntry
   ACCESS     not-accessible
   STATUS     mandatory
   DESCRIPTION
     "This entry controls the addition and deletion of 
      lpTrLtFbIpH components."
::= { lpTrLtFbIpH 1 }

lpTrLtFbIpHRowStatusEntry OBJECT-TYPE
   SYNTAX     LpTrLtFbIpHRowStatusEntry
   ACCESS     not-accessible
   STATUS     mandatory
   DESCRIPTION
     "A single entry in the table represents a single 
      lpTrLtFbIpH component."
   INDEX {
      lpIndex,
      lpTrIndex,
      lpTrLtIndex,
      lpTrLtFbIndex,
      lpTrLtFbIpHIndex }
::= { lpTrLtFbIpHRowStatusTable 1 }

LpTrLtFbIpHRowStatusEntry ::= SEQUENCE {
   lpTrLtFbIpHRowStatus
      RowStatus,
   lpTrLtFbIpHComponentName
      DisplayString,
   lpTrLtFbIpHStorageType
      StorageType,
   lpTrLtFbIpHIndex
      NonReplicated }

lpTrLtFbIpHRowStatus OBJECT-TYPE
   SYNTAX     RowStatus 
   ACCESS     read-only
   STATUS     mandatory
   DESCRIPTION
     "This variable is used as the basis for SNMP naming of
      lpTrLtFbIpH components.
      These components cannot be added nor deleted."
::= { lpTrLtFbIpHRowStatusEntry 1 }

lpTrLtFbIpHComponentName OBJECT-TYPE
   SYNTAX     DisplayString 
   ACCESS     read-only
   STATUS     mandatory
   DESCRIPTION
     "This variable provides the component's string name for
      use with the ASCII Console Interface"
::= { lpTrLtFbIpHRowStatusEntry 2 }

lpTrLtFbIpHStorageType OBJECT-TYPE
   SYNTAX     StorageType 
   ACCESS     read-only
   STATUS     mandatory
   DESCRIPTION
     "This variable represents the storage type value for the
      lpTrLtFbIpH tables."
::= { lpTrLtFbIpHRowStatusEntry 4 }

lpTrLtFbIpHIndex OBJECT-TYPE
   SYNTAX     NonReplicated 
   ACCESS     not-accessible
   STATUS     mandatory
   DESCRIPTION
     "This variable represents the index for the lpTrLtFbIpH tables."
::= { lpTrLtFbIpHRowStatusEntry 10 }

lpTrLtFbIpHTopTable OBJECT-TYPE
   SYNTAX     SEQUENCE OF LpTrLtFbIpHTopEntry
   ACCESS     not-accessible
   STATUS     mandatory
   DESCRIPTION
     "This group contains the operational data for the LanTest component 
      and its subcomponents."
::= { lpTrLtFbIpH 10 }

lpTrLtFbIpHTopEntry OBJECT-TYPE
   SYNTAX     LpTrLtFbIpHTopEntry
   ACCESS     not-accessible
   STATUS     mandatory
   DESCRIPTION
     "An entry in the lpTrLtFbIpHTopTable."
   INDEX {
      lpIndex,
      lpTrIndex,
      lpTrLtIndex,
      lpTrLtFbIndex,
      lpTrLtFbIpHIndex }
::= { lpTrLtFbIpHTopTable 1 }

LpTrLtFbIpHTopEntry ::= SEQUENCE {
   lpTrLtFbIpHTData
      AsciiString }

lpTrLtFbIpHTData OBJECT-TYPE
   SYNTAX     AsciiString (SIZE (0..255))
   ACCESS     read-write
   STATUS     mandatory
   DESCRIPTION
     "This attribute is used to display and set attributes."
::= { lpTrLtFbIpHTopEntry 1 }


-- LanTest LlcHeader
-- This component adds an LLC 802.2 or Ethernet header to a frame 
-- or packet.

lpTrLtFbLlch OBJECT IDENTIFIER ::= { lpTrLtFb 8 }



lpTrLtFbLlchRowStatusTable OBJECT-TYPE
   SYNTAX     SEQUENCE OF LpTrLtFbLlchRowStatusEntry
   ACCESS     not-accessible
   STATUS     mandatory
   DESCRIPTION
     "This entry controls the addition and deletion of 
      lpTrLtFbLlch components."
::= { lpTrLtFbLlch 1 }

lpTrLtFbLlchRowStatusEntry OBJECT-TYPE
   SYNTAX     LpTrLtFbLlchRowStatusEntry
   ACCESS     not-accessible
   STATUS     mandatory
   DESCRIPTION
     "A single entry in the table represents a single 
      lpTrLtFbLlch component."
   INDEX {
      lpIndex,
      lpTrIndex,
      lpTrLtIndex,
      lpTrLtFbIndex,
      lpTrLtFbLlchIndex }
::= { lpTrLtFbLlchRowStatusTable 1 }

LpTrLtFbLlchRowStatusEntry ::= SEQUENCE {
   lpTrLtFbLlchRowStatus
      RowStatus,
   lpTrLtFbLlchComponentName
      DisplayString,
   lpTrLtFbLlchStorageType
      StorageType,
   lpTrLtFbLlchIndex
      NonReplicated }

lpTrLtFbLlchRowStatus OBJECT-TYPE
   SYNTAX     RowStatus 
   ACCESS     read-only
   STATUS     mandatory
   DESCRIPTION
     "This variable is used as the basis for SNMP naming of
      lpTrLtFbLlch components.
      These components cannot be added nor deleted."
::= { lpTrLtFbLlchRowStatusEntry 1 }

lpTrLtFbLlchComponentName OBJECT-TYPE
   SYNTAX     DisplayString 
   ACCESS     read-only
   STATUS     mandatory
   DESCRIPTION
     "This variable provides the component's string name for
      use with the ASCII Console Interface"
::= { lpTrLtFbLlchRowStatusEntry 2 }

lpTrLtFbLlchStorageType OBJECT-TYPE
   SYNTAX     StorageType 
   ACCESS     read-only
   STATUS     mandatory
   DESCRIPTION
     "This variable represents the storage type value for the
      lpTrLtFbLlch tables."
::= { lpTrLtFbLlchRowStatusEntry 4 }

lpTrLtFbLlchIndex OBJECT-TYPE
   SYNTAX     NonReplicated 
   ACCESS     not-accessible
   STATUS     mandatory
   DESCRIPTION
     "This variable represents the index for the lpTrLtFbLlch tables."
::= { lpTrLtFbLlchRowStatusEntry 10 }

lpTrLtFbLlchTopTable OBJECT-TYPE
   SYNTAX     SEQUENCE OF LpTrLtFbLlchTopEntry
   ACCESS     not-accessible
   STATUS     mandatory
   DESCRIPTION
     "This group contains the operational data for the LanTest component 
      and its subcomponents."
::= { lpTrLtFbLlch 10 }

lpTrLtFbLlchTopEntry OBJECT-TYPE
   SYNTAX     LpTrLtFbLlchTopEntry
   ACCESS     not-accessible
   STATUS     mandatory
   DESCRIPTION
     "An entry in the lpTrLtFbLlchTopTable."
   INDEX {
      lpIndex,
      lpTrIndex,
      lpTrLtIndex,
      lpTrLtFbIndex,
      lpTrLtFbLlchIndex }
::= { lpTrLtFbLlchTopTable 1 }

LpTrLtFbLlchTopEntry ::= SEQUENCE {
   lpTrLtFbLlchTData
      AsciiString }

lpTrLtFbLlchTData OBJECT-TYPE
   SYNTAX     AsciiString (SIZE (0..255))
   ACCESS     read-write
   STATUS     mandatory
   DESCRIPTION
     "This attribute is used to display and set attributes."
::= { lpTrLtFbLlchTopEntry 1 }


-- This component adds an AppleTalk header to a frame or packet.

lpTrLtFbAppleH OBJECT IDENTIFIER ::= { lpTrLtFb 9 }



lpTrLtFbAppleHRowStatusTable OBJECT-TYPE
   SYNTAX     SEQUENCE OF LpTrLtFbAppleHRowStatusEntry
   ACCESS     not-accessible
   STATUS     mandatory
   DESCRIPTION
     "This entry controls the addition and deletion of 
      lpTrLtFbAppleH components."
::= { lpTrLtFbAppleH 1 }

lpTrLtFbAppleHRowStatusEntry OBJECT-TYPE
   SYNTAX     LpTrLtFbAppleHRowStatusEntry
   ACCESS     not-accessible
   STATUS     mandatory
   DESCRIPTION
     "A single entry in the table represents a single 
      lpTrLtFbAppleH component."
   INDEX {
      lpIndex,
      lpTrIndex,
      lpTrLtIndex,
      lpTrLtFbIndex,
      lpTrLtFbAppleHIndex }
::= { lpTrLtFbAppleHRowStatusTable 1 }

LpTrLtFbAppleHRowStatusEntry ::= SEQUENCE {
   lpTrLtFbAppleHRowStatus
      RowStatus,
   lpTrLtFbAppleHComponentName
      DisplayString,
   lpTrLtFbAppleHStorageType
      StorageType,
   lpTrLtFbAppleHIndex
      NonReplicated }

lpTrLtFbAppleHRowStatus OBJECT-TYPE
   SYNTAX     RowStatus 
   ACCESS     read-only
   STATUS     mandatory
   DESCRIPTION
     "This variable is used as the basis for SNMP naming of
      lpTrLtFbAppleH components.
      These components cannot be added nor deleted."
::= { lpTrLtFbAppleHRowStatusEntry 1 }

lpTrLtFbAppleHComponentName OBJECT-TYPE
   SYNTAX     DisplayString 
   ACCESS     read-only
   STATUS     mandatory
   DESCRIPTION
     "This variable provides the component's string name for
      use with the ASCII Console Interface"
::= { lpTrLtFbAppleHRowStatusEntry 2 }

lpTrLtFbAppleHStorageType OBJECT-TYPE
   SYNTAX     StorageType 
   ACCESS     read-only
   STATUS     mandatory
   DESCRIPTION
     "This variable represents the storage type value for the
      lpTrLtFbAppleH tables."
::= { lpTrLtFbAppleHRowStatusEntry 4 }

lpTrLtFbAppleHIndex OBJECT-TYPE
   SYNTAX     NonReplicated 
   ACCESS     not-accessible
   STATUS     mandatory
   DESCRIPTION
     "This variable represents the index for the lpTrLtFbAppleH tables."
::= { lpTrLtFbAppleHRowStatusEntry 10 }

lpTrLtFbAppleHTopTable OBJECT-TYPE
   SYNTAX     SEQUENCE OF LpTrLtFbAppleHTopEntry
   ACCESS     not-accessible
   STATUS     mandatory
   DESCRIPTION
     "This group contains the operational data for the LanTest component 
      and its subcomponents."
::= { lpTrLtFbAppleH 10 }

lpTrLtFbAppleHTopEntry OBJECT-TYPE
   SYNTAX     LpTrLtFbAppleHTopEntry
   ACCESS     not-accessible
   STATUS     mandatory
   DESCRIPTION
     "An entry in the lpTrLtFbAppleHTopTable."
   INDEX {
      lpIndex,
      lpTrIndex,
      lpTrLtIndex,
      lpTrLtFbIndex,
      lpTrLtFbAppleHIndex }
::= { lpTrLtFbAppleHTopTable 1 }

LpTrLtFbAppleHTopEntry ::= SEQUENCE {
   lpTrLtFbAppleHTData
      AsciiString }

lpTrLtFbAppleHTData OBJECT-TYPE
   SYNTAX     AsciiString (SIZE (0..255))
   ACCESS     read-write
   STATUS     mandatory
   DESCRIPTION
     "This attribute is used to display and set attributes."
::= { lpTrLtFbAppleHTopEntry 1 }


-- This component adds an IPX header to a frame or packet.

lpTrLtFbIpxH OBJECT IDENTIFIER ::= { lpTrLtFb 10 }



lpTrLtFbIpxHRowStatusTable OBJECT-TYPE
   SYNTAX     SEQUENCE OF LpTrLtFbIpxHRowStatusEntry
   ACCESS     not-accessible
   STATUS     mandatory
   DESCRIPTION
     "This entry controls the addition and deletion of 
      lpTrLtFbIpxH components."
::= { lpTrLtFbIpxH 1 }

lpTrLtFbIpxHRowStatusEntry OBJECT-TYPE
   SYNTAX     LpTrLtFbIpxHRowStatusEntry
   ACCESS     not-accessible
   STATUS     mandatory
   DESCRIPTION
     "A single entry in the table represents a single 
      lpTrLtFbIpxH component."
   INDEX {
      lpIndex,
      lpTrIndex,
      lpTrLtIndex,
      lpTrLtFbIndex,
      lpTrLtFbIpxHIndex }
::= { lpTrLtFbIpxHRowStatusTable 1 }

LpTrLtFbIpxHRowStatusEntry ::= SEQUENCE {
   lpTrLtFbIpxHRowStatus
      RowStatus,
   lpTrLtFbIpxHComponentName
      DisplayString,
   lpTrLtFbIpxHStorageType
      StorageType,
   lpTrLtFbIpxHIndex
      NonReplicated }

lpTrLtFbIpxHRowStatus OBJECT-TYPE
   SYNTAX     RowStatus 
   ACCESS     read-only
   STATUS     mandatory
   DESCRIPTION
     "This variable is used as the basis for SNMP naming of
      lpTrLtFbIpxH components.
      These components cannot be added nor deleted."
::= { lpTrLtFbIpxHRowStatusEntry 1 }

lpTrLtFbIpxHComponentName OBJECT-TYPE
   SYNTAX     DisplayString 
   ACCESS     read-only
   STATUS     mandatory
   DESCRIPTION
     "This variable provides the component's string name for
      use with the ASCII Console Interface"
::= { lpTrLtFbIpxHRowStatusEntry 2 }

lpTrLtFbIpxHStorageType OBJECT-TYPE
   SYNTAX     StorageType 
   ACCESS     read-only
   STATUS     mandatory
   DESCRIPTION
     "This variable represents the storage type value for the
      lpTrLtFbIpxH tables."
::= { lpTrLtFbIpxHRowStatusEntry 4 }

lpTrLtFbIpxHIndex OBJECT-TYPE
   SYNTAX     NonReplicated 
   ACCESS     not-accessible
   STATUS     mandatory
   DESCRIPTION
     "This variable represents the index for the lpTrLtFbIpxH tables."
::= { lpTrLtFbIpxHRowStatusEntry 10 }

lpTrLtFbIpxHTopTable OBJECT-TYPE
   SYNTAX     SEQUENCE OF LpTrLtFbIpxHTopEntry
   ACCESS     not-accessible
   STATUS     mandatory
   DESCRIPTION
     "This group contains the operational data for the LanTest component 
      and its subcomponents."
::= { lpTrLtFbIpxH 10 }

lpTrLtFbIpxHTopEntry OBJECT-TYPE
   SYNTAX     LpTrLtFbIpxHTopEntry
   ACCESS     not-accessible
   STATUS     mandatory
   DESCRIPTION
     "An entry in the lpTrLtFbIpxHTopTable."
   INDEX {
      lpIndex,
      lpTrIndex,
      lpTrLtIndex,
      lpTrLtFbIndex,
      lpTrLtFbIpxHIndex }
::= { lpTrLtFbIpxHTopTable 1 }

LpTrLtFbIpxHTopEntry ::= SEQUENCE {
   lpTrLtFbIpxHTData
      AsciiString }

lpTrLtFbIpxHTData OBJECT-TYPE
   SYNTAX     AsciiString (SIZE (0..255))
   ACCESS     read-write
   STATUS     mandatory
   DESCRIPTION
     "This attribute is used to display and set attributes."
::= { lpTrLtFbIpxHTopEntry 1 }


-- LanTest Control
-- This component controls the overall testing by telling the 
-- FrameBuild component to start and check the FrameCompare 
-- component to see if the test is complete.

lpTrLtCntl OBJECT IDENTIFIER ::= { lpTrLt 6 }



lpTrLtCntlRowStatusTable OBJECT-TYPE
   SYNTAX     SEQUENCE OF LpTrLtCntlRowStatusEntry
   ACCESS     not-accessible
   STATUS     mandatory
   DESCRIPTION
     "This entry controls the addition and deletion of 
      lpTrLtCntl components."
::= { lpTrLtCntl 1 }

lpTrLtCntlRowStatusEntry OBJECT-TYPE
   SYNTAX     LpTrLtCntlRowStatusEntry
   ACCESS     not-accessible
   STATUS     mandatory
   DESCRIPTION
     "A single entry in the table represents a single 
      lpTrLtCntl component."
   INDEX {
      lpIndex,
      lpTrIndex,
      lpTrLtIndex,
      lpTrLtCntlIndex }
::= { lpTrLtCntlRowStatusTable 1 }

LpTrLtCntlRowStatusEntry ::= SEQUENCE {
   lpTrLtCntlRowStatus
      RowStatus,
   lpTrLtCntlComponentName
      DisplayString,
   lpTrLtCntlStorageType
      StorageType,
   lpTrLtCntlIndex
      NonReplicated }

lpTrLtCntlRowStatus OBJECT-TYPE
   SYNTAX     RowStatus 
   ACCESS     read-only
   STATUS     mandatory
   DESCRIPTION
     "This variable is used as the basis for SNMP naming of
      lpTrLtCntl components.
      These components cannot be added nor deleted."
::= { lpTrLtCntlRowStatusEntry 1 }

lpTrLtCntlComponentName OBJECT-TYPE
   SYNTAX     DisplayString 
   ACCESS     read-only
   STATUS     mandatory
   DESCRIPTION
     "This variable provides the component's string name for
      use with the ASCII Console Interface"
::= { lpTrLtCntlRowStatusEntry 2 }

lpTrLtCntlStorageType OBJECT-TYPE
   SYNTAX     StorageType 
   ACCESS     read-only
   STATUS     mandatory
   DESCRIPTION
     "This variable represents the storage type value for the
      lpTrLtCntl tables."
::= { lpTrLtCntlRowStatusEntry 4 }

lpTrLtCntlIndex OBJECT-TYPE
   SYNTAX     NonReplicated 
   ACCESS     not-accessible
   STATUS     mandatory
   DESCRIPTION
     "This variable represents the index for the lpTrLtCntl tables."
::= { lpTrLtCntlRowStatusEntry 10 }

lpTrLtCntlTopTable OBJECT-TYPE
   SYNTAX     SEQUENCE OF LpTrLtCntlTopEntry
   ACCESS     not-accessible
   STATUS     mandatory
   DESCRIPTION
     "This group contains the operational data for the LanTest component 
      and its subcomponents."
::= { lpTrLtCntl 10 }

lpTrLtCntlTopEntry OBJECT-TYPE
   SYNTAX     LpTrLtCntlTopEntry
   ACCESS     not-accessible
   STATUS     mandatory
   DESCRIPTION
     "An entry in the lpTrLtCntlTopTable."
   INDEX {
      lpIndex,
      lpTrIndex,
      lpTrLtIndex,
      lpTrLtCntlIndex }
::= { lpTrLtCntlTopTable 1 }

LpTrLtCntlTopEntry ::= SEQUENCE {
   lpTrLtCntlTData
      AsciiString }

lpTrLtCntlTData OBJECT-TYPE
   SYNTAX     AsciiString (SIZE (0..255))
   ACCESS     read-write
   STATUS     mandatory
   DESCRIPTION
     "This attribute is used to display and set attributes."
::= { lpTrLtCntlTopEntry 1 }


-- Lp/n Fddi/n Test, or
-- Lp/n Ethernet/n Test, or
-- Lp/n TokenRing/n Test, or
-- Lp/n IlsForwarder/n Test
-- The Test component is used to do StartUp port test for LAN cards.

lpTrTest OBJECT IDENTIFIER ::= { lpTr 5 }



lpTrTestRowStatusTable OBJECT-TYPE
   SYNTAX     SEQUENCE OF LpTrTestRowStatusEntry
   ACCESS     not-accessible
   STATUS     mandatory
   DESCRIPTION
     "This entry controls the addition and deletion of 
      lpTrTest components."
::= { lpTrTest 1 }

lpTrTestRowStatusEntry OBJECT-TYPE
   SYNTAX     LpTrTestRowStatusEntry
   ACCESS     not-accessible
   STATUS     mandatory
   DESCRIPTION
     "A single entry in the table represents a single 
      lpTrTest component."
   INDEX {
      lpIndex,
      lpTrIndex,
      lpTrTestIndex }
::= { lpTrTestRowStatusTable 1 }

LpTrTestRowStatusEntry ::= SEQUENCE {
   lpTrTestRowStatus
      RowStatus,
   lpTrTestComponentName
      DisplayString,
   lpTrTestStorageType
      StorageType,
   lpTrTestIndex
      NonReplicated }

lpTrTestRowStatus OBJECT-TYPE
   SYNTAX     RowStatus 
   ACCESS     read-only
   STATUS     mandatory
   DESCRIPTION
     "This variable is used as the basis for SNMP naming of
      lpTrTest components.
      These components cannot be added nor deleted."
::= { lpTrTestRowStatusEntry 1 }

lpTrTestComponentName OBJECT-TYPE
   SYNTAX     DisplayString 
   ACCESS     read-only
   STATUS     mandatory
   DESCRIPTION
     "This variable provides the component's string name for
      use with the ASCII Console Interface"
::= { lpTrTestRowStatusEntry 2 }

lpTrTestStorageType OBJECT-TYPE
   SYNTAX     StorageType 
   ACCESS     read-only
   STATUS     mandatory
   DESCRIPTION
     "This variable represents the storage type value for the
      lpTrTest tables."
::= { lpTrTestRowStatusEntry 4 }

lpTrTestIndex OBJECT-TYPE
   SYNTAX     NonReplicated 
   ACCESS     not-accessible
   STATUS     mandatory
   DESCRIPTION
     "This variable represents the index for the lpTrTest tables."
::= { lpTrTestRowStatusEntry 10 }

lpTrTestPTOTable OBJECT-TYPE
   SYNTAX     SEQUENCE OF LpTrTestPTOEntry
   ACCESS     not-accessible
   STATUS     mandatory
   DESCRIPTION
     "This group contains the operational data for the LanPortTest 
      component."
::= { lpTrTest 10 }

lpTrTestPTOEntry OBJECT-TYPE
   SYNTAX     LpTrTestPTOEntry
   ACCESS     not-accessible
   STATUS     mandatory
   DESCRIPTION
     "An entry in the lpTrTestPTOTable."
   INDEX {
      lpIndex,
      lpTrIndex,
      lpTrTestIndex }
::= { lpTrTestPTOTable 1 }

LpTrTestPTOEntry ::= SEQUENCE {
   lpTrTestType
      INTEGER,
   lpTrTestFrmSize
      Unsigned32,
   lpTrTestDuration
      Unsigned32 }

lpTrTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { lpTrTestPTOEntry 1 }

lpTrTestFrmSize OBJECT-TYPE
   SYNTAX     Unsigned32 (4..4096)
   ACCESS     read-write
   STATUS     mandatory
   DESCRIPTION
     "This attribute defines the size of the test data frames in number of 
      bytes."
   DEFVAL     { 1024 }
::= { lpTrTestPTOEntry 2 }

lpTrTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpTrTestPTOEntry 3 }

lpTrTestResultsTable OBJECT-TYPE
   SYNTAX     SEQUENCE OF LpTrTestResultsEntry
   ACCESS     not-accessible
   STATUS     mandatory
   DESCRIPTION
     "This group contains all the statistics related attributes of the Test 
      component."
::= { lpTrTest 11 }

lpTrTestResultsEntry OBJECT-TYPE
   SYNTAX     LpTrTestResultsEntry
   ACCESS     not-accessible
   STATUS     mandatory
   DESCRIPTION
     "An entry in the lpTrTestResultsTable."
   INDEX {
      lpIndex,
      lpTrIndex,
      lpTrTestIndex }
::= { lpTrTestResultsTable 1 }

LpTrTestResultsEntry ::= SEQUENCE {
   lpTrTestElapsedTime
      Counter32,
   lpTrTestTimeRemaining
      Unsigned32,
   lpTrTestCauseOfTermination
      INTEGER,
   lpTrTestFrmTx
      PassportCounter64,
   lpTrTestBitsTx
      PassportCounter64,
   lpTrTestFrmRx
      PassportCounter64,
   lpTrTestBitsRx
      PassportCounter64,
   lpTrTestErroredFrmRx
      PassportCounter64 }

lpTrTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpTrTestResultsEntry 4 }

lpTrTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpTrTestResultsEntry 5 }

lpTrTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { lpTrTestResultsEntry 6 }

lpTrTestFrmTx OBJECT-TYPE
   SYNTAX     PassportCounter64 
   ACCESS     read-only
   STATUS     mandatory
   DESCRIPTION
     "This attribute is the total number of frames sent during the test 
      period. This counter is not expected to reach its maximum value."
::= { lpTrTestResultsEntry 7 }

lpTrTestBitsTx OBJECT-TYPE
   SYNTAX     PassportCounter64 
   ACCESS     read-only
   STATUS     mandatory
   DESCRIPTION
     "This attribute is the total number of bits sent during the test period. 
      This counter is not expected to reach its maximum value."
::= { lpTrTestResultsEntry 8 }

lpTrTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpTrTestResultsEntry 9 }

lpTrTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { lpTrTestResultsEntry 10 }

lpTrTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { lpTrTestResultsEntry 11 }


-- Lp/n IlsForwarder/0
-- This component defines an instance of a IlsForwarder. At least one 
-- instance of this component must be provisioned if there is any AtmMpe 
-- component provisioned.

lpIlsFwdr OBJECT IDENTIFIER ::= { lp 21 }



lpIlsFwdrRowStatusTable OBJECT-TYPE
   SYNTAX     SEQUENCE OF LpIlsFwdrRowStatusEntry
   ACCESS     not-accessible
   STATUS     mandatory
   DESCRIPTION
     "This entry controls the addition and deletion of 
      lpIlsFwdr components."
::= { lpIlsFwdr 1 }

lpIlsFwdrRowStatusEntry OBJECT-TYPE
   SYNTAX     LpIlsFwdrRowStatusEntry
   ACCESS     not-accessible
   STATUS     mandatory
   DESCRIPTION
     "A single entry in the table represents a single 
      lpIlsFwdr component."
   INDEX {
      lpIndex,
      lpIlsFwdrIndex }
::= { lpIlsFwdrRowStatusTable 1 }

LpIlsFwdrRowStatusEntry ::= SEQUENCE {
   lpIlsFwdrRowStatus
      RowStatus,
   lpIlsFwdrComponentName
      DisplayString,
   lpIlsFwdrStorageType
      StorageType,
   lpIlsFwdrIndex
      Integer32 }

lpIlsFwdrRowStatus OBJECT-TYPE
   SYNTAX     RowStatus 
   ACCESS     read-write
   STATUS     mandatory
   DESCRIPTION
     "This variable is used as the basis for SNMP naming of
      lpIlsFwdr components.
      These components can be added and deleted."
::= { lpIlsFwdrRowStatusEntry 1 }

lpIlsFwdrComponentName OBJECT-TYPE
   SYNTAX     DisplayString 
   ACCESS     read-only
   STATUS     mandatory
   DESCRIPTION
     "This variable provides the component's string name for
      use with the ASCII Console Interface"
::= { lpIlsFwdrRowStatusEntry 2 }

lpIlsFwdrStorageType OBJECT-TYPE
   SYNTAX     StorageType 
   ACCESS     read-only
   STATUS     mandatory
   DESCRIPTION
     "This variable represents the storage type value for the
      lpIlsFwdr tables."
::= { lpIlsFwdrRowStatusEntry 4 }

lpIlsFwdrIndex OBJECT-TYPE
   SYNTAX     Integer32 (0)
   ACCESS     not-accessible
   STATUS     mandatory
   DESCRIPTION
     "This variable represents the index for the lpIlsFwdr tables."
::= { lpIlsFwdrRowStatusEntry 10 }

lpIlsFwdrIfEntryTable OBJECT-TYPE
   SYNTAX     SEQUENCE OF LpIlsFwdrIfEntryEntry
   ACCESS     not-accessible
   STATUS     mandatory
   DESCRIPTION
     "This group contains the provisionable attributes for the ifEntry."
::= { lpIlsFwdr 11 }

lpIlsFwdrIfEntryEntry OBJECT-TYPE
   SYNTAX     LpIlsFwdrIfEntryEntry
   ACCESS     not-accessible
   STATUS     mandatory
   DESCRIPTION
     "An entry in the lpIlsFwdrIfEntryTable."
   INDEX {
      lpIndex,
      lpIlsFwdrIndex }
::= { lpIlsFwdrIfEntryTable 1 }

LpIlsFwdrIfEntryEntry ::= SEQUENCE {
   lpIlsFwdrIfAdminStatus
      INTEGER,
   lpIlsFwdrIfIndex
      InterfaceIndex }

lpIlsFwdrIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpIlsFwdrIfEntryEntry 1 }

lpIlsFwdrIfIndex OBJECT-TYPE
   SYNTAX     InterfaceIndex (1..65535)
   ACCESS     read-only
   STATUS     mandatory
   DESCRIPTION
     "This is the index for the IfEntry. Its value is automatically initialized 
      during the provisioning process."
::= { lpIlsFwdrIfEntryEntry 2 }

lpIlsFwdrStateTable OBJECT-TYPE
   SYNTAX     SEQUENCE OF LpIlsFwdrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpIlsFwdr 12 }

lpIlsFwdrStateEntry OBJECT-TYPE
   SYNTAX     LpIlsFwdrStateEntry
   ACCESS     not-accessible
   STATUS     mandatory
   DESCRIPTION
     "An entry in the lpIlsFwdrStateTable."
   INDEX {
      lpIndex,
      lpIlsFwdrIndex }
::= { lpIlsFwdrStateTable 1 }

LpIlsFwdrStateEntry ::= SEQUENCE {
   lpIlsFwdrAdminState
      INTEGER,
   lpIlsFwdrOperationalState
      INTEGER,
   lpIlsFwdrUsageState
      INTEGER }

lpIlsFwdrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpIlsFwdrStateEntry 1 }

lpIlsFwdrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpIlsFwdrStateEntry 2 }

lpIlsFwdrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpIlsFwdrStateEntry 3 }

lpIlsFwdrOperStatusTable OBJECT-TYPE
   SYNTAX     SEQUENCE OF LpIlsFwdrOperStatusEntry
   ACCESS     not-accessible
   STATUS     mandatory
   DESCRIPTION
     "This group includes the Operational Status attribute. This attribute 
      defines the current operational state of this component."
::= { lpIlsFwdr 13 }

lpIlsFwdrOperStatusEntry OBJECT-TYPE
   SYNTAX     LpIlsFwdrOperStatusEntry
   ACCESS     not-accessible
   STATUS     mandatory
   DESCRIPTION
     "An entry in the lpIlsFwdrOperStatusTable."
   INDEX {
      lpIndex,
      lpIlsFwdrIndex }
::= { lpIlsFwdrOperStatusTable 1 }

LpIlsFwdrOperStatusEntry ::= SEQUENCE {
   lpIlsFwdrSnmpOperStatus
      INTEGER }

lpIlsFwdrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpIlsFwdrOperStatusEntry 1 }

lpIlsFwdrStatsTable OBJECT-TYPE
   SYNTAX     SEQUENCE OF LpIlsFwdrStatsEntry
   ACCESS     not-accessible
   STATUS     mandatory
   DESCRIPTION
     "This group contains the operational frame statistics related attributes of 
      the IlsForwarder component."
::= { lpIlsFwdr 14 }

lpIlsFwdrStatsEntry OBJECT-TYPE
   SYNTAX     LpIlsFwdrStatsEntry
   ACCESS     not-accessible
   STATUS     mandatory
   DESCRIPTION
     "An entry in the lpIlsFwdrStatsTable."
   INDEX {
      lpIndex,
      lpIlsFwdrIndex }
::= { lpIlsFwdrStatsTable 1 }

LpIlsFwdrStatsEntry ::= SEQUENCE {
   lpIlsFwdrFramesReceived
      PassportCounter64,
   lpIlsFwdrProcessedCount
      PassportCounter64,
   lpIlsFwdrErrorCount
      PassportCounter64,
   lpIlsFwdrFramesDiscarded
      PassportCounter64 }

lpIlsFwdrFramesReceived OBJECT-TYPE
   SYNTAX     PassportCounter64 
   ACCESS     read-only
   STATUS     mandatory
   DESCRIPTION
     "This attribute counts the total number of frames that have been received 
      by this card. This counter will wrap around after it reaches its maximum 
      value."
::= { lpIlsFwdrStatsEntry 1 }

lpIlsFwdrProcessedCount OBJECT-TYPE
   SYNTAX     PassportCounter64 
   ACCESS     read-only
   STATUS     mandatory
   DESCRIPTION
     "This attribute counts the number of frames successfully processed by 
      this card. This counter will wrap around after it reaches its maximum 
      value."
::= { lpIlsFwdrStatsEntry 2 }

lpIlsFwdrErrorCount OBJECT-TYPE
   SYNTAX     PassportCounter64 
   ACCESS     read-only
   STATUS     mandatory
   DESCRIPTION
     "This attribute counts the number of internal errors detected in 
      transferring frames from an ATM card to this card. A continuous 
      increment of this count indicates that the hardware may probably be 
      defective. This counter will wrap around after it reaches its maximum 
      value."
::= { lpIlsFwdrStatsEntry 3 }

lpIlsFwdrFramesDiscarded OBJECT-TYPE
   SYNTAX     PassportCounter64 
   ACCESS     read-only
   STATUS     mandatory
   DESCRIPTION
     "This attribute counts the number of frames which are discarded due to 
      local buffer congestion. This counter will wrap around after it reaches its 
      maximum value."
::= { lpIlsFwdrStatsEntry 4 }

lpIlsFwdrLinkToTrafficSourceTable OBJECT-TYPE
   SYNTAX     SEQUENCE OF LpIlsFwdrLinkToTrafficSourceEntry
   ACCESS     not-accessible
   STATUS     mandatory
   DESCRIPTION
     "This attribute contains a list of components that are using this 
      IlsForwarder."
::= { lpIlsFwdr 312 }

lpIlsFwdrLinkToTrafficSourceEntry OBJECT-TYPE
   SYNTAX     LpIlsFwdrLinkToTrafficSourceEntry
   ACCESS     not-accessible
   STATUS     mandatory
   DESCRIPTION
     "An entry in the lpIlsFwdrLinkToTrafficSourceTable."
   INDEX {
      lpIndex,
      lpIlsFwdrIndex,
      lpIlsFwdrLinkToTrafficSourceValue }
::= { lpIlsFwdrLinkToTrafficSourceTable 1 }

LpIlsFwdrLinkToTrafficSourceEntry ::= SEQUENCE {
   lpIlsFwdrLinkToTrafficSourceValue
      Link }

lpIlsFwdrLinkToTrafficSourceValue OBJECT-TYPE
   SYNTAX     Link 
   ACCESS     read-only
   STATUS     mandatory
   DESCRIPTION
     "This variable represents both the value and the index for the
      lpIlsFwdrLinkToTrafficSourceTable."
::= { lpIlsFwdrLinkToTrafficSourceEntry 1 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

lpIlsFwdrLt OBJECT IDENTIFIER ::= { lpIlsFwdr 2 }



lpIlsFwdrLtRowStatusTable OBJECT-TYPE
   SYNTAX     SEQUENCE OF LpIlsFwdrLtRowStatusEntry
   ACCESS     not-accessible
   STATUS     mandatory
   DESCRIPTION
     "This entry controls the addition and deletion of 
      lpIlsFwdrLt components."
::= { lpIlsFwdrLt 1 }

lpIlsFwdrLtRowStatusEntry OBJECT-TYPE
   SYNTAX     LpIlsFwdrLtRowStatusEntry
   ACCESS     not-accessible
   STATUS     mandatory
   DESCRIPTION
     "A single entry in the table represents a single 
      lpIlsFwdrLt component."
   INDEX {
      lpIndex,
      lpIlsFwdrIndex,
      lpIlsFwdrLtIndex }
::= { lpIlsFwdrLtRowStatusTable 1 }

LpIlsFwdrLtRowStatusEntry ::= SEQUENCE {
   lpIlsFwdrLtRowStatus
      RowStatus,
   lpIlsFwdrLtComponentName
      DisplayString,
   lpIlsFwdrLtStorageType
      StorageType,
   lpIlsFwdrLtIndex
      NonReplicated }

lpIlsFwdrLtRowStatus OBJECT-TYPE
   SYNTAX     RowStatus 
   ACCESS     read-only
   STATUS     mandatory
   DESCRIPTION
     "This variable is used as the basis for SNMP naming of
      lpIlsFwdrLt components.
      These components cannot be added nor deleted."
::= { lpIlsFwdrLtRowStatusEntry 1 }

lpIlsFwdrLtComponentName OBJECT-TYPE
   SYNTAX     DisplayString 
   ACCESS     read-only
   STATUS     mandatory
   DESCRIPTION
     "This variable provides the component's string name for
      use with the ASCII Console Interface"
::= { lpIlsFwdrLtRowStatusEntry 2 }

lpIlsFwdrLtStorageType OBJECT-TYPE
   SYNTAX     StorageType 
   ACCESS     read-only
   STATUS     mandatory
   DESCRIPTION
     "This variable represents the storage type value for the
      lpIlsFwdrLt tables."
::= { lpIlsFwdrLtRowStatusEntry 4 }

lpIlsFwdrLtIndex OBJECT-TYPE
   SYNTAX     NonReplicated 
   ACCESS     not-accessible
   STATUS     mandatory
   DESCRIPTION
     "This variable represents the index for the lpIlsFwdrLt tables."
::= { lpIlsFwdrLtRowStatusEntry 10 }

lpIlsFwdrLtTopTable OBJECT-TYPE
   SYNTAX     SEQUENCE OF LpIlsFwdrLtTopEntry
   ACCESS     not-accessible
   STATUS     mandatory
   DESCRIPTION
     "This group contains the operational data for the LanTest component 
      and its subcomponents."
::= { lpIlsFwdrLt 20 }

lpIlsFwdrLtTopEntry OBJECT-TYPE
   SYNTAX     LpIlsFwdrLtTopEntry
   ACCESS     not-accessible
   STATUS     mandatory
   DESCRIPTION
     "An entry in the lpIlsFwdrLtTopTable."
   INDEX {
      lpIndex,
      lpIlsFwdrIndex,
      lpIlsFwdrLtIndex }
::= { lpIlsFwdrLtTopTable 1 }

LpIlsFwdrLtTopEntry ::= SEQUENCE {
   lpIlsFwdrLtTData
      AsciiString }

lpIlsFwdrLtTData OBJECT-TYPE
   SYNTAX     AsciiString (SIZE (0..255))
   ACCESS     read-write
   STATUS     mandatory
   DESCRIPTION
     "This attribute is used to display and set attributes."
::= { lpIlsFwdrLtTopEntry 1 }


-- This component compares frames received from the hardware and 
-- emulator during testing.

lpIlsFwdrLtFrmCmp OBJECT IDENTIFIER ::= { lpIlsFwdrLt 2 }



lpIlsFwdrLtFrmCmpRowStatusTable OBJECT-TYPE
   SYNTAX     SEQUENCE OF LpIlsFwdrLtFrmCmpRowStatusEntry
   ACCESS     not-accessible
   STATUS     mandatory
   DESCRIPTION
     "This entry controls the addition and deletion of 
      lpIlsFwdrLtFrmCmp components."
::= { lpIlsFwdrLtFrmCmp 1 }

lpIlsFwdrLtFrmCmpRowStatusEntry OBJECT-TYPE
   SYNTAX     LpIlsFwdrLtFrmCmpRowStatusEntry
   ACCESS     not-accessible
   STATUS     mandatory
   DESCRIPTION
     "A single entry in the table represents a single 
      lpIlsFwdrLtFrmCmp component."
   INDEX {
      lpIndex,
      lpIlsFwdrIndex,
      lpIlsFwdrLtIndex,
      lpIlsFwdrLtFrmCmpIndex }
::= { lpIlsFwdrLtFrmCmpRowStatusTable 1 }

LpIlsFwdrLtFrmCmpRowStatusEntry ::= SEQUENCE {
   lpIlsFwdrLtFrmCmpRowStatus
      RowStatus,
   lpIlsFwdrLtFrmCmpComponentName
      DisplayString,
   lpIlsFwdrLtFrmCmpStorageType
      StorageType,
   lpIlsFwdrLtFrmCmpIndex
      NonReplicated }

lpIlsFwdrLtFrmCmpRowStatus OBJECT-TYPE
   SYNTAX     RowStatus 
   ACCESS     read-only
   STATUS     mandatory
   DESCRIPTION
     "This variable is used as the basis for SNMP naming of
      lpIlsFwdrLtFrmCmp components.
      These components cannot be added nor deleted."
::= { lpIlsFwdrLtFrmCmpRowStatusEntry 1 }

lpIlsFwdrLtFrmCmpComponentName OBJECT-TYPE
   SYNTAX     DisplayString 
   ACCESS     read-only
   STATUS     mandatory
   DESCRIPTION
     "This variable provides the component's string name for
      use with the ASCII Console Interface"
::= { lpIlsFwdrLtFrmCmpRowStatusEntry 2 }

lpIlsFwdrLtFrmCmpStorageType OBJECT-TYPE
   SYNTAX     StorageType 
   ACCESS     read-only
   STATUS     mandatory
   DESCRIPTION
     "This variable represents the storage type value for the
      lpIlsFwdrLtFrmCmp tables."
::= { lpIlsFwdrLtFrmCmpRowStatusEntry 4 }

lpIlsFwdrLtFrmCmpIndex OBJECT-TYPE
   SYNTAX     NonReplicated 
   ACCESS     not-accessible
   STATUS     mandatory
   DESCRIPTION
     "This variable represents the index for the lpIlsFwdrLtFrmCmp tables."
::= { lpIlsFwdrLtFrmCmpRowStatusEntry 10 }

lpIlsFwdrLtFrmCmpTopTable OBJECT-TYPE
   SYNTAX     SEQUENCE OF LpIlsFwdrLtFrmCmpTopEntry
   ACCESS     not-accessible
   STATUS     mandatory
   DESCRIPTION
     "This group contains the operational data for the LanTest component 
      and its subcomponents."
::= { lpIlsFwdrLtFrmCmp 10 }

lpIlsFwdrLtFrmCmpTopEntry OBJECT-TYPE
   SYNTAX     LpIlsFwdrLtFrmCmpTopEntry
   ACCESS     not-accessible
   STATUS     mandatory
   DESCRIPTION
     "An entry in the lpIlsFwdrLtFrmCmpTopTable."
   INDEX {
      lpIndex,
      lpIlsFwdrIndex,
      lpIlsFwdrLtIndex,
      lpIlsFwdrLtFrmCmpIndex }
::= { lpIlsFwdrLtFrmCmpTopTable 1 }

LpIlsFwdrLtFrmCmpTopEntry ::= SEQUENCE {
   lpIlsFwdrLtFrmCmpTData
      AsciiString }

lpIlsFwdrLtFrmCmpTData OBJECT-TYPE
   SYNTAX     AsciiString (SIZE (0..255))
   ACCESS     read-write
   STATUS     mandatory
   DESCRIPTION
     "This attribute is used to display and set attributes."
::= { lpIlsFwdrLtFrmCmpTopEntry 1 }


-- This component receives its input from FrameBuild and places it 
-- upon the hardware which sends it to the appropriate emulator.

lpIlsFwdrLtFrmCpy OBJECT IDENTIFIER ::= { lpIlsFwdrLt 3 }



lpIlsFwdrLtFrmCpyRowStatusTable OBJECT-TYPE
   SYNTAX     SEQUENCE OF LpIlsFwdrLtFrmCpyRowStatusEntry
   ACCESS     not-accessible
   STATUS     mandatory
   DESCRIPTION
     "This entry controls the addition and deletion of 
      lpIlsFwdrLtFrmCpy components."
::= { lpIlsFwdrLtFrmCpy 1 }

lpIlsFwdrLtFrmCpyRowStatusEntry OBJECT-TYPE
   SYNTAX     LpIlsFwdrLtFrmCpyRowStatusEntry
   ACCESS     not-accessible
   STATUS     mandatory
   DESCRIPTION
     "A single entry in the table represents a single 
      lpIlsFwdrLtFrmCpy component."
   INDEX {
      lpIndex,
      lpIlsFwdrIndex,
      lpIlsFwdrLtIndex,
      lpIlsFwdrLtFrmCpyIndex }
::= { lpIlsFwdrLtFrmCpyRowStatusTable 1 }

LpIlsFwdrLtFrmCpyRowStatusEntry ::= SEQUENCE {
   lpIlsFwdrLtFrmCpyRowStatus
      RowStatus,
   lpIlsFwdrLtFrmCpyComponentName
      DisplayString,
   lpIlsFwdrLtFrmCpyStorageType
      StorageType,
   lpIlsFwdrLtFrmCpyIndex
      NonReplicated }

lpIlsFwdrLtFrmCpyRowStatus OBJECT-TYPE
   SYNTAX     RowStatus 
   ACCESS     read-only
   STATUS     mandatory
   DESCRIPTION
     "This variable is used as the basis for SNMP naming of
      lpIlsFwdrLtFrmCpy components.
      These components cannot be added nor deleted."
::= { lpIlsFwdrLtFrmCpyRowStatusEntry 1 }

lpIlsFwdrLtFrmCpyComponentName OBJECT-TYPE
   SYNTAX     DisplayString 
   ACCESS     read-only
   STATUS     mandatory
   DESCRIPTION
     "This variable provides the component's string name for
      use with the ASCII Console Interface"
::= { lpIlsFwdrLtFrmCpyRowStatusEntry 2 }

lpIlsFwdrLtFrmCpyStorageType OBJECT-TYPE
   SYNTAX     StorageType 
   ACCESS     read-only
   STATUS     mandatory
   DESCRIPTION
     "This variable represents the storage type value for the
      lpIlsFwdrLtFrmCpy tables."
::= { lpIlsFwdrLtFrmCpyRowStatusEntry 4 }

lpIlsFwdrLtFrmCpyIndex OBJECT-TYPE
   SYNTAX     NonReplicated 
   ACCESS     not-accessible
   STATUS     mandatory
   DESCRIPTION
     "This variable represents the index for the lpIlsFwdrLtFrmCpy tables."
::= { lpIlsFwdrLtFrmCpyRowStatusEntry 10 }

lpIlsFwdrLtFrmCpyTopTable OBJECT-TYPE
   SYNTAX     SEQUENCE OF LpIlsFwdrLtFrmCpyTopEntry
   ACCESS     not-accessible
   STATUS     mandatory
   DESCRIPTION
     "This group contains the operational data for the LanTest component 
      and its subcomponents."
::= { lpIlsFwdrLtFrmCpy 10 }

lpIlsFwdrLtFrmCpyTopEntry OBJECT-TYPE
   SYNTAX     LpIlsFwdrLtFrmCpyTopEntry
   ACCESS     not-accessible
   STATUS     mandatory
   DESCRIPTION
     "An entry in the lpIlsFwdrLtFrmCpyTopTable."
   INDEX {
      lpIndex,
      lpIlsFwdrIndex,
      lpIlsFwdrLtIndex,
      lpIlsFwdrLtFrmCpyIndex }
::= { lpIlsFwdrLtFrmCpyTopTable 1 }

LpIlsFwdrLtFrmCpyTopEntry ::= SEQUENCE {
   lpIlsFwdrLtFrmCpyTData
      AsciiString }

lpIlsFwdrLtFrmCpyTData OBJECT-TYPE
   SYNTAX     AsciiString (SIZE (0..255))
   ACCESS     read-write
   STATUS     mandatory
   DESCRIPTION
     "This attribute is used to display and set attributes."
::= { lpIlsFwdrLtFrmCpyTopEntry 1 }


-- This component controls the emulator and hardware to ensure 
-- frames output from each will match in FrameCompare.

lpIlsFwdrLtPrtCfg OBJECT IDENTIFIER ::= { lpIlsFwdrLt 4 }



lpIlsFwdrLtPrtCfgRowStatusTable OBJECT-TYPE
   SYNTAX     SEQUENCE OF LpIlsFwdrLtPrtCfgRowStatusEntry
   ACCESS     not-accessible
   STATUS     mandatory
   DESCRIPTION
     "This entry controls the addition and deletion of 
      lpIlsFwdrLtPrtCfg components."
::= { lpIlsFwdrLtPrtCfg 1 }

lpIlsFwdrLtPrtCfgRowStatusEntry OBJECT-TYPE
   SYNTAX     LpIlsFwdrLtPrtCfgRowStatusEntry
   ACCESS     not-accessible
   STATUS     mandatory
   DESCRIPTION
     "A single entry in the table represents a single 
      lpIlsFwdrLtPrtCfg component."
   INDEX {
      lpIndex,
      lpIlsFwdrIndex,
      lpIlsFwdrLtIndex,
      lpIlsFwdrLtPrtCfgIndex }
::= { lpIlsFwdrLtPrtCfgRowStatusTable 1 }

LpIlsFwdrLtPrtCfgRowStatusEntry ::= SEQUENCE {
   lpIlsFwdrLtPrtCfgRowStatus
      RowStatus,
   lpIlsFwdrLtPrtCfgComponentName
      DisplayString,
   lpIlsFwdrLtPrtCfgStorageType
      StorageType,
   lpIlsFwdrLtPrtCfgIndex
      NonReplicated }

lpIlsFwdrLtPrtCfgRowStatus OBJECT-TYPE
   SYNTAX     RowStatus 
   ACCESS     read-only
   STATUS     mandatory
   DESCRIPTION
     "This variable is used as the basis for SNMP naming of
      lpIlsFwdrLtPrtCfg components.
      These components cannot be added nor deleted."
::= { lpIlsFwdrLtPrtCfgRowStatusEntry 1 }

lpIlsFwdrLtPrtCfgComponentName OBJECT-TYPE
   SYNTAX     DisplayString 
   ACCESS     read-only
   STATUS     mandatory
   DESCRIPTION
     "This variable provides the component's string name for
      use with the ASCII Console Interface"
::= { lpIlsFwdrLtPrtCfgRowStatusEntry 2 }

lpIlsFwdrLtPrtCfgStorageType OBJECT-TYPE
   SYNTAX     StorageType 
   ACCESS     read-only
   STATUS     mandatory
   DESCRIPTION
     "This variable represents the storage type value for the
      lpIlsFwdrLtPrtCfg tables."
::= { lpIlsFwdrLtPrtCfgRowStatusEntry 4 }

lpIlsFwdrLtPrtCfgIndex OBJECT-TYPE
   SYNTAX     NonReplicated 
   ACCESS     not-accessible
   STATUS     mandatory
   DESCRIPTION
     "This variable represents the index for the lpIlsFwdrLtPrtCfg tables."
::= { lpIlsFwdrLtPrtCfgRowStatusEntry 10 }

lpIlsFwdrLtPrtCfgTopTable OBJECT-TYPE
   SYNTAX     SEQUENCE OF LpIlsFwdrLtPrtCfgTopEntry
   ACCESS     not-accessible
   STATUS     mandatory
   DESCRIPTION
     "This group contains the operational data for the LanTest component 
      and its subcomponents."
::= { lpIlsFwdrLtPrtCfg 10 }

lpIlsFwdrLtPrtCfgTopEntry OBJECT-TYPE
   SYNTAX     LpIlsFwdrLtPrtCfgTopEntry
   ACCESS     not-accessible
   STATUS     mandatory
   DESCRIPTION
     "An entry in the lpIlsFwdrLtPrtCfgTopTable."
   INDEX {
      lpIndex,
      lpIlsFwdrIndex,
      lpIlsFwdrLtIndex,
      lpIlsFwdrLtPrtCfgIndex }
::= { lpIlsFwdrLtPrtCfgTopTable 1 }

LpIlsFwdrLtPrtCfgTopEntry ::= SEQUENCE {
   lpIlsFwdrLtPrtCfgTData
      AsciiString }

lpIlsFwdrLtPrtCfgTData OBJECT-TYPE
   SYNTAX     AsciiString (SIZE (0..255))
   ACCESS     read-write
   STATUS     mandatory
   DESCRIPTION
     "This attribute is used to display and set attributes."
::= { lpIlsFwdrLtPrtCfgTopEntry 1 }


-- LanTest Framebuild
-- This component controls the building of all frames built and sent by 
-- the LanTest component. Each component under FrameBuild builds 
-- a portion of a packet or frame.

lpIlsFwdrLtFb OBJECT IDENTIFIER ::= { lpIlsFwdrLt 5 }



lpIlsFwdrLtFbRowStatusTable OBJECT-TYPE
   SYNTAX     SEQUENCE OF LpIlsFwdrLtFbRowStatusEntry
   ACCESS     not-accessible
   STATUS     mandatory
   DESCRIPTION
     "This entry controls the addition and deletion of 
      lpIlsFwdrLtFb components."
::= { lpIlsFwdrLtFb 1 }

lpIlsFwdrLtFbRowStatusEntry OBJECT-TYPE
   SYNTAX     LpIlsFwdrLtFbRowStatusEntry
   ACCESS     not-accessible
   STATUS     mandatory
   DESCRIPTION
     "A single entry in the table represents a single 
      lpIlsFwdrLtFb component."
   INDEX {
      lpIndex,
      lpIlsFwdrIndex,
      lpIlsFwdrLtIndex,
      lpIlsFwdrLtFbIndex }
::= { lpIlsFwdrLtFbRowStatusTable 1 }

LpIlsFwdrLtFbRowStatusEntry ::= SEQUENCE {
   lpIlsFwdrLtFbRowStatus
      RowStatus,
   lpIlsFwdrLtFbComponentName
      DisplayString,
   lpIlsFwdrLtFbStorageType
      StorageType,
   lpIlsFwdrLtFbIndex
      NonReplicated }

lpIlsFwdrLtFbRowStatus OBJECT-TYPE
   SYNTAX     RowStatus 
   ACCESS     read-only
   STATUS     mandatory
   DESCRIPTION
     "This variable is used as the basis for SNMP naming of
      lpIlsFwdrLtFb components.
      These components cannot be added nor deleted."
::= { lpIlsFwdrLtFbRowStatusEntry 1 }

lpIlsFwdrLtFbComponentName OBJECT-TYPE
   SYNTAX     DisplayString 
   ACCESS     read-only
   STATUS     mandatory
   DESCRIPTION
     "This variable provides the component's string name for
      use with the ASCII Console Interface"
::= { lpIlsFwdrLtFbRowStatusEntry 2 }

lpIlsFwdrLtFbStorageType OBJECT-TYPE
   SYNTAX     StorageType 
   ACCESS     read-only
   STATUS     mandatory
   DESCRIPTION
     "This variable represents the storage type value for the
      lpIlsFwdrLtFb tables."
::= { lpIlsFwdrLtFbRowStatusEntry 4 }

lpIlsFwdrLtFbIndex OBJECT-TYPE
   SYNTAX     NonReplicated 
   ACCESS     not-accessible
   STATUS     mandatory
   DESCRIPTION
     "This variable represents the index for the lpIlsFwdrLtFb tables."
::= { lpIlsFwdrLtFbRowStatusEntry 10 }

lpIlsFwdrLtFbTopTable OBJECT-TYPE
   SYNTAX     SEQUENCE OF LpIlsFwdrLtFbTopEntry
   ACCESS     not-accessible
   STATUS     mandatory
   DESCRIPTION
     "This group contains the operational data for the LanTest component 
      and its subcomponents."
::= { lpIlsFwdrLtFb 20 }

lpIlsFwdrLtFbTopEntry OBJECT-TYPE
   SYNTAX     LpIlsFwdrLtFbTopEntry
   ACCESS     not-accessible
   STATUS     mandatory
   DESCRIPTION
     "An entry in the lpIlsFwdrLtFbTopTable."
   INDEX {
      lpIndex,
      lpIlsFwdrIndex,
      lpIlsFwdrLtIndex,
      lpIlsFwdrLtFbIndex }
::= { lpIlsFwdrLtFbTopTable 1 }

LpIlsFwdrLtFbTopEntry ::= SEQUENCE {
   lpIlsFwdrLtFbTData
      AsciiString }

lpIlsFwdrLtFbTData OBJECT-TYPE
   SYNTAX     AsciiString (SIZE (0..255))
   ACCESS     read-write
   STATUS     mandatory
   DESCRIPTION
     "This attribute is used to display and set attributes."
::= { lpIlsFwdrLtFbTopEntry 1 }


-- LanTest TransmitInfo
-- This component builds a transmit header which is attached to all 
-- frames transmitted on LAN interfaces.

lpIlsFwdrLtFbTxInfo OBJECT IDENTIFIER ::= { lpIlsFwdrLtFb 2 }



lpIlsFwdrLtFbTxInfoRowStatusTable OBJECT-TYPE
   SYNTAX     SEQUENCE OF LpIlsFwdrLtFbTxInfoRowStatusEntry
   ACCESS     not-accessible
   STATUS     mandatory
   DESCRIPTION
     "This entry controls the addition and deletion of 
      lpIlsFwdrLtFbTxInfo components."
::= { lpIlsFwdrLtFbTxInfo 1 }

lpIlsFwdrLtFbTxInfoRowStatusEntry OBJECT-TYPE
   SYNTAX     LpIlsFwdrLtFbTxInfoRowStatusEntry
   ACCESS     not-accessible
   STATUS     mandatory
   DESCRIPTION
     "A single entry in the table represents a single 
      lpIlsFwdrLtFbTxInfo component."
   INDEX {
      lpIndex,
      lpIlsFwdrIndex,
      lpIlsFwdrLtIndex,
      lpIlsFwdrLtFbIndex,
      lpIlsFwdrLtFbTxInfoIndex }
::= { lpIlsFwdrLtFbTxInfoRowStatusTable 1 }

LpIlsFwdrLtFbTxInfoRowStatusEntry ::= SEQUENCE {
   lpIlsFwdrLtFbTxInfoRowStatus
      RowStatus,
   lpIlsFwdrLtFbTxInfoComponentName
      DisplayString,
   lpIlsFwdrLtFbTxInfoStorageType
      StorageType,
   lpIlsFwdrLtFbTxInfoIndex
      NonReplicated }

lpIlsFwdrLtFbTxInfoRowStatus OBJECT-TYPE
   SYNTAX     RowStatus 
   ACCESS     read-only
   STATUS     mandatory
   DESCRIPTION
     "This variable is used as the basis for SNMP naming of
      lpIlsFwdrLtFbTxInfo components.
      These components cannot be added nor deleted."
::= { lpIlsFwdrLtFbTxInfoRowStatusEntry 1 }

lpIlsFwdrLtFbTxInfoComponentName OBJECT-TYPE
   SYNTAX     DisplayString 
   ACCESS     read-only
   STATUS     mandatory
   DESCRIPTION
     "This variable provides the component's string name for
      use with the ASCII Console Interface"
::= { lpIlsFwdrLtFbTxInfoRowStatusEntry 2 }

lpIlsFwdrLtFbTxInfoStorageType OBJECT-TYPE
   SYNTAX     StorageType 
   ACCESS     read-only
   STATUS     mandatory
   DESCRIPTION
     "This variable represents the storage type value for the
      lpIlsFwdrLtFbTxInfo tables."
::= { lpIlsFwdrLtFbTxInfoRowStatusEntry 4 }

lpIlsFwdrLtFbTxInfoIndex OBJECT-TYPE
   SYNTAX     NonReplicated 
   ACCESS     not-accessible
   STATUS     mandatory
   DESCRIPTION
     "This variable represents the index for the lpIlsFwdrLtFbTxInfo tables."
::= { lpIlsFwdrLtFbTxInfoRowStatusEntry 10 }

lpIlsFwdrLtFbTxInfoTopTable OBJECT-TYPE
   SYNTAX     SEQUENCE OF LpIlsFwdrLtFbTxInfoTopEntry
   ACCESS     not-accessible
   STATUS     mandatory
   DESCRIPTION
     "This group contains the operational data for the LanTest component 
      and its subcomponents."
::= { lpIlsFwdrLtFbTxInfo 10 }

lpIlsFwdrLtFbTxInfoTopEntry OBJECT-TYPE
   SYNTAX     LpIlsFwdrLtFbTxInfoTopEntry
   ACCESS     not-accessible
   STATUS     mandatory
   DESCRIPTION
     "An entry in the lpIlsFwdrLtFbTxInfoTopTable."
   INDEX {
      lpIndex,
      lpIlsFwdrIndex,
      lpIlsFwdrLtIndex,
      lpIlsFwdrLtFbIndex,
      lpIlsFwdrLtFbTxInfoIndex }
::= { lpIlsFwdrLtFbTxInfoTopTable 1 }

LpIlsFwdrLtFbTxInfoTopEntry ::= SEQUENCE {
   lpIlsFwdrLtFbTxInfoTData
      AsciiString }

lpIlsFwdrLtFbTxInfoTData OBJECT-TYPE
   SYNTAX     AsciiString (SIZE (0..255))
   ACCESS     read-write
   STATUS     mandatory
   DESCRIPTION
     "This attribute is used to display and set attributes."
::= { lpIlsFwdrLtFbTxInfoTopEntry 1 }


-- LanTest FddiMac
-- This component builds an FDDI MAC header which is attached to 
-- all FDDI frames.

lpIlsFwdrLtFbFddiMac OBJECT IDENTIFIER ::= { lpIlsFwdrLtFb 3 }



lpIlsFwdrLtFbFddiMacRowStatusTable OBJECT-TYPE
   SYNTAX     SEQUENCE OF LpIlsFwdrLtFbFddiMacRowStatusEntry
   ACCESS     not-accessible
   STATUS     mandatory
   DESCRIPTION
     "This entry controls the addition and deletion of 
      lpIlsFwdrLtFbFddiMac components."
::= { lpIlsFwdrLtFbFddiMac 1 }

lpIlsFwdrLtFbFddiMacRowStatusEntry OBJECT-TYPE
   SYNTAX     LpIlsFwdrLtFbFddiMacRowStatusEntry
   ACCESS     not-accessible
   STATUS     mandatory
   DESCRIPTION
     "A single entry in the table represents a single 
      lpIlsFwdrLtFbFddiMac component."
   INDEX {
      lpIndex,
      lpIlsFwdrIndex,
      lpIlsFwdrLtIndex,
      lpIlsFwdrLtFbIndex,
      lpIlsFwdrLtFbFddiMacIndex }
::= { lpIlsFwdrLtFbFddiMacRowStatusTable 1 }

LpIlsFwdrLtFbFddiMacRowStatusEntry ::= SEQUENCE {
   lpIlsFwdrLtFbFddiMacRowStatus
      RowStatus,
   lpIlsFwdrLtFbFddiMacComponentName
      DisplayString,
   lpIlsFwdrLtFbFddiMacStorageType
      StorageType,
   lpIlsFwdrLtFbFddiMacIndex
      NonReplicated }

lpIlsFwdrLtFbFddiMacRowStatus OBJECT-TYPE
   SYNTAX     RowStatus 
   ACCESS     read-only
   STATUS     mandatory
   DESCRIPTION
     "This variable is used as the basis for SNMP naming of
      lpIlsFwdrLtFbFddiMac components.
      These components cannot be added nor deleted."
::= { lpIlsFwdrLtFbFddiMacRowStatusEntry 1 }

lpIlsFwdrLtFbFddiMacComponentName OBJECT-TYPE
   SYNTAX     DisplayString 
   ACCESS     read-only
   STATUS     mandatory
   DESCRIPTION
     "This variable provides the component's string name for
      use with the ASCII Console Interface"
::= { lpIlsFwdrLtFbFddiMacRowStatusEntry 2 }

lpIlsFwdrLtFbFddiMacStorageType OBJECT-TYPE
   SYNTAX     StorageType 
   ACCESS     read-only
   STATUS     mandatory
   DESCRIPTION
     "This variable represents the storage type value for the
      lpIlsFwdrLtFbFddiMac tables."
::= { lpIlsFwdrLtFbFddiMacRowStatusEntry 4 }

lpIlsFwdrLtFbFddiMacIndex OBJECT-TYPE
   SYNTAX     NonReplicated 
   ACCESS     not-accessible
   STATUS     mandatory
   DESCRIPTION
     "This variable represents the index for the lpIlsFwdrLtFbFddiMac tables."
::= { lpIlsFwdrLtFbFddiMacRowStatusEntry 10 }

lpIlsFwdrLtFbFddiMacTopTable OBJECT-TYPE
   SYNTAX     SEQUENCE OF LpIlsFwdrLtFbFddiMacTopEntry
   ACCESS     not-accessible
   STATUS     mandatory
   DESCRIPTION
     "This group contains the operational data for the LanTest component 
      and its subcomponents."
::= { lpIlsFwdrLtFbFddiMac 10 }

lpIlsFwdrLtFbFddiMacTopEntry OBJECT-TYPE
   SYNTAX     LpIlsFwdrLtFbFddiMacTopEntry
   ACCESS     not-accessible
   STATUS     mandatory
   DESCRIPTION
     "An entry in the lpIlsFwdrLtFbFddiMacTopTable."
   INDEX {
      lpIndex,
      lpIlsFwdrIndex,
      lpIlsFwdrLtIndex,
      lpIlsFwdrLtFbIndex,
      lpIlsFwdrLtFbFddiMacIndex }
::= { lpIlsFwdrLtFbFddiMacTopTable 1 }

LpIlsFwdrLtFbFddiMacTopEntry ::= SEQUENCE {
   lpIlsFwdrLtFbFddiMacTData
      AsciiString }

lpIlsFwdrLtFbFddiMacTData OBJECT-TYPE
   SYNTAX     AsciiString (SIZE (0..255))
   ACCESS     read-write
   STATUS     mandatory
   DESCRIPTION
     "This attribute is used to display and set attributes."
::= { lpIlsFwdrLtFbFddiMacTopEntry 1 }


-- LanTest EthernetMac
-- This component builds an Ethernet MAC header which is attached 
-- to all Ethernet frames.

lpIlsFwdrLtFbMacEnet OBJECT IDENTIFIER ::= { lpIlsFwdrLtFb 4 }



lpIlsFwdrLtFbMacEnetRowStatusTable OBJECT-TYPE
   SYNTAX     SEQUENCE OF LpIlsFwdrLtFbMacEnetRowStatusEntry
   ACCESS     not-accessible
   STATUS     mandatory
   DESCRIPTION
     "This entry controls the addition and deletion of 
      lpIlsFwdrLtFbMacEnet components."
::= { lpIlsFwdrLtFbMacEnet 1 }

lpIlsFwdrLtFbMacEnetRowStatusEntry OBJECT-TYPE
   SYNTAX     LpIlsFwdrLtFbMacEnetRowStatusEntry
   ACCESS     not-accessible
   STATUS     mandatory
   DESCRIPTION
     "A single entry in the table represents a single 
      lpIlsFwdrLtFbMacEnet component."
   INDEX {
      lpIndex,
      lpIlsFwdrIndex,
      lpIlsFwdrLtIndex,
      lpIlsFwdrLtFbIndex,
      lpIlsFwdrLtFbMacEnetIndex }
::= { lpIlsFwdrLtFbMacEnetRowStatusTable 1 }

LpIlsFwdrLtFbMacEnetRowStatusEntry ::= SEQUENCE {
   lpIlsFwdrLtFbMacEnetRowStatus
      RowStatus,
   lpIlsFwdrLtFbMacEnetComponentName
      DisplayString,
   lpIlsFwdrLtFbMacEnetStorageType
      StorageType,
   lpIlsFwdrLtFbMacEnetIndex
      NonReplicated }

lpIlsFwdrLtFbMacEnetRowStatus OBJECT-TYPE
   SYNTAX     RowStatus 
   ACCESS     read-only
   STATUS     mandatory
   DESCRIPTION
     "This variable is used as the basis for SNMP naming of
      lpIlsFwdrLtFbMacEnet components.
      These components cannot be added nor deleted."
::= { lpIlsFwdrLtFbMacEnetRowStatusEntry 1 }

lpIlsFwdrLtFbMacEnetComponentName OBJECT-TYPE
   SYNTAX     DisplayString 
   ACCESS     read-only
   STATUS     mandatory
   DESCRIPTION
     "This variable provides the component's string name for
      use with the ASCII Console Interface"
::= { lpIlsFwdrLtFbMacEnetRowStatusEntry 2 }

lpIlsFwdrLtFbMacEnetStorageType OBJECT-TYPE
   SYNTAX     StorageType 
   ACCESS     read-only
   STATUS     mandatory
   DESCRIPTION
     "This variable represents the storage type value for the
      lpIlsFwdrLtFbMacEnet tables."
::= { lpIlsFwdrLtFbMacEnetRowStatusEntry 4 }

lpIlsFwdrLtFbMacEnetIndex OBJECT-TYPE
   SYNTAX     NonReplicated 
   ACCESS     not-accessible
   STATUS     mandatory
   DESCRIPTION
     "This variable represents the index for the lpIlsFwdrLtFbMacEnet tables."
::= { lpIlsFwdrLtFbMacEnetRowStatusEntry 10 }

lpIlsFwdrLtFbMacEnetTopTable OBJECT-TYPE
   SYNTAX     SEQUENCE OF LpIlsFwdrLtFbMacEnetTopEntry
   ACCESS     not-accessible
   STATUS     mandatory
   DESCRIPTION
     "This group contains the operational data for the LanTest component 
      and its subcomponents."
::= { lpIlsFwdrLtFbMacEnet 10 }

lpIlsFwdrLtFbMacEnetTopEntry OBJECT-TYPE
   SYNTAX     LpIlsFwdrLtFbMacEnetTopEntry
   ACCESS     not-accessible
   STATUS     mandatory
   DESCRIPTION
     "An entry in the lpIlsFwdrLtFbMacEnetTopTable."
   INDEX {
      lpIndex,
      lpIlsFwdrIndex,
      lpIlsFwdrLtIndex,
      lpIlsFwdrLtFbIndex,
      lpIlsFwdrLtFbMacEnetIndex }
::= { lpIlsFwdrLtFbMacEnetTopTable 1 }

LpIlsFwdrLtFbMacEnetTopEntry ::= SEQUENCE {
   lpIlsFwdrLtFbMacEnetTData
      AsciiString }

lpIlsFwdrLtFbMacEnetTData OBJECT-TYPE
   SYNTAX     AsciiString (SIZE (0..255))
   ACCESS     read-write
   STATUS     mandatory
   DESCRIPTION
     "This attribute is used to display and set attributes."
::= { lpIlsFwdrLtFbMacEnetTopEntry 1 }


-- LanTest TokenRingMac
-- This component builds a Token Ring MAC header which is attached 
-- to all Token Ring frames.

lpIlsFwdrLtFbMacTr OBJECT IDENTIFIER ::= { lpIlsFwdrLtFb 5 }



lpIlsFwdrLtFbMacTrRowStatusTable OBJECT-TYPE
   SYNTAX     SEQUENCE OF LpIlsFwdrLtFbMacTrRowStatusEntry
   ACCESS     not-accessible
   STATUS     mandatory
   DESCRIPTION
     "This entry controls the addition and deletion of 
      lpIlsFwdrLtFbMacTr components."
::= { lpIlsFwdrLtFbMacTr 1 }

lpIlsFwdrLtFbMacTrRowStatusEntry OBJECT-TYPE
   SYNTAX     LpIlsFwdrLtFbMacTrRowStatusEntry
   ACCESS     not-accessible
   STATUS     mandatory
   DESCRIPTION
     "A single entry in the table represents a single 
      lpIlsFwdrLtFbMacTr component."
   INDEX {
      lpIndex,
      lpIlsFwdrIndex,
      lpIlsFwdrLtIndex,
      lpIlsFwdrLtFbIndex,
      lpIlsFwdrLtFbMacTrIndex }
::= { lpIlsFwdrLtFbMacTrRowStatusTable 1 }

LpIlsFwdrLtFbMacTrRowStatusEntry ::= SEQUENCE {
   lpIlsFwdrLtFbMacTrRowStatus
      RowStatus,
   lpIlsFwdrLtFbMacTrComponentName
      DisplayString,
   lpIlsFwdrLtFbMacTrStorageType
      StorageType,
   lpIlsFwdrLtFbMacTrIndex
      NonReplicated }

lpIlsFwdrLtFbMacTrRowStatus OBJECT-TYPE
   SYNTAX     RowStatus 
   ACCESS     read-only
   STATUS     mandatory
   DESCRIPTION
     "This variable is used as the basis for SNMP naming of
      lpIlsFwdrLtFbMacTr components.
      These components cannot be added nor deleted."
::= { lpIlsFwdrLtFbMacTrRowStatusEntry 1 }

lpIlsFwdrLtFbMacTrComponentName OBJECT-TYPE
   SYNTAX     DisplayString 
   ACCESS     read-only
   STATUS     mandatory
   DESCRIPTION
     "This variable provides the component's string name for
      use with the ASCII Console Interface"
::= { lpIlsFwdrLtFbMacTrRowStatusEntry 2 }

lpIlsFwdrLtFbMacTrStorageType OBJECT-TYPE
   SYNTAX     StorageType 
   ACCESS     read-only
   STATUS     mandatory
   DESCRIPTION
     "This variable represents the storage type value for the
      lpIlsFwdrLtFbMacTr tables."
::= { lpIlsFwdrLtFbMacTrRowStatusEntry 4 }

lpIlsFwdrLtFbMacTrIndex OBJECT-TYPE
   SYNTAX     NonReplicated 
   ACCESS     not-accessible
   STATUS     mandatory
   DESCRIPTION
     "This variable represents the index for the lpIlsFwdrLtFbMacTr tables."
::= { lpIlsFwdrLtFbMacTrRowStatusEntry 10 }

lpIlsFwdrLtFbMacTrTopTable OBJECT-TYPE
   SYNTAX     SEQUENCE OF LpIlsFwdrLtFbMacTrTopEntry
   ACCESS     not-accessible
   STATUS     mandatory
   DESCRIPTION
     "This group contains the operational data for the LanTest component 
      and its subcomponents."
::= { lpIlsFwdrLtFbMacTr 10 }

lpIlsFwdrLtFbMacTrTopEntry OBJECT-TYPE
   SYNTAX     LpIlsFwdrLtFbMacTrTopEntry
   ACCESS     not-accessible
   STATUS     mandatory
   DESCRIPTION
     "An entry in the lpIlsFwdrLtFbMacTrTopTable."
   INDEX {
      lpIndex,
      lpIlsFwdrIndex,
      lpIlsFwdrLtIndex,
      lpIlsFwdrLtFbIndex,
      lpIlsFwdrLtFbMacTrIndex }
::= { lpIlsFwdrLtFbMacTrTopTable 1 }

LpIlsFwdrLtFbMacTrTopEntry ::= SEQUENCE {
   lpIlsFwdrLtFbMacTrTData
      AsciiString }

lpIlsFwdrLtFbMacTrTData OBJECT-TYPE
   SYNTAX     AsciiString (SIZE (0..255))
   ACCESS     read-write
   STATUS     mandatory
   DESCRIPTION
     "This attribute is used to display and set attributes."
::= { lpIlsFwdrLtFbMacTrTopEntry 1 }


-- This component adds a data field to frame.

lpIlsFwdrLtFbData OBJECT IDENTIFIER ::= { lpIlsFwdrLtFb 6 }



lpIlsFwdrLtFbDataRowStatusTable OBJECT-TYPE
   SYNTAX     SEQUENCE OF LpIlsFwdrLtFbDataRowStatusEntry
   ACCESS     not-accessible
   STATUS     mandatory
   DESCRIPTION
     "This entry controls the addition and deletion of 
      lpIlsFwdrLtFbData components."
::= { lpIlsFwdrLtFbData 1 }

lpIlsFwdrLtFbDataRowStatusEntry OBJECT-TYPE
   SYNTAX     LpIlsFwdrLtFbDataRowStatusEntry
   ACCESS     not-accessible
   STATUS     mandatory
   DESCRIPTION
     "A single entry in the table represents a single 
      lpIlsFwdrLtFbData component."
   INDEX {
      lpIndex,
      lpIlsFwdrIndex,
      lpIlsFwdrLtIndex,
      lpIlsFwdrLtFbIndex,
      lpIlsFwdrLtFbDataIndex }
::= { lpIlsFwdrLtFbDataRowStatusTable 1 }

LpIlsFwdrLtFbDataRowStatusEntry ::= SEQUENCE {
   lpIlsFwdrLtFbDataRowStatus
      RowStatus,
   lpIlsFwdrLtFbDataComponentName
      DisplayString,
   lpIlsFwdrLtFbDataStorageType
      StorageType,
   lpIlsFwdrLtFbDataIndex
      NonReplicated }

lpIlsFwdrLtFbDataRowStatus OBJECT-TYPE
   SYNTAX     RowStatus 
   ACCESS     read-only
   STATUS     mandatory
   DESCRIPTION
     "This variable is used as the basis for SNMP naming of
      lpIlsFwdrLtFbData components.
      These components cannot be added nor deleted."
::= { lpIlsFwdrLtFbDataRowStatusEntry 1 }

lpIlsFwdrLtFbDataComponentName OBJECT-TYPE
   SYNTAX     DisplayString 
   ACCESS     read-only
   STATUS     mandatory
   DESCRIPTION
     "This variable provides the component's string name for
      use with the ASCII Console Interface"
::= { lpIlsFwdrLtFbDataRowStatusEntry 2 }

lpIlsFwdrLtFbDataStorageType OBJECT-TYPE
   SYNTAX     StorageType 
   ACCESS     read-only
   STATUS     mandatory
   DESCRIPTION
     "This variable represents the storage type value for the
      lpIlsFwdrLtFbData tables."
::= { lpIlsFwdrLtFbDataRowStatusEntry 4 }

lpIlsFwdrLtFbDataIndex OBJECT-TYPE
   SYNTAX     NonReplicated 
   ACCESS     not-accessible
   STATUS     mandatory
   DESCRIPTION
     "This variable represents the index for the lpIlsFwdrLtFbData tables."
::= { lpIlsFwdrLtFbDataRowStatusEntry 10 }

lpIlsFwdrLtFbDataTopTable OBJECT-TYPE
   SYNTAX     SEQUENCE OF LpIlsFwdrLtFbDataTopEntry
   ACCESS     not-accessible
   STATUS     mandatory
   DESCRIPTION
     "This group contains the operational data for the LanTest component 
      and its subcomponents."
::= { lpIlsFwdrLtFbData 10 }

lpIlsFwdrLtFbDataTopEntry OBJECT-TYPE
   SYNTAX     LpIlsFwdrLtFbDataTopEntry
   ACCESS     not-accessible
   STATUS     mandatory
   DESCRIPTION
     "An entry in the lpIlsFwdrLtFbDataTopTable."
   INDEX {
      lpIndex,
      lpIlsFwdrIndex,
      lpIlsFwdrLtIndex,
      lpIlsFwdrLtFbIndex,
      lpIlsFwdrLtFbDataIndex }
::= { lpIlsFwdrLtFbDataTopTable 1 }

LpIlsFwdrLtFbDataTopEntry ::= SEQUENCE {
   lpIlsFwdrLtFbDataTData
      AsciiString }

lpIlsFwdrLtFbDataTData OBJECT-TYPE
   SYNTAX     AsciiString (SIZE (0..255))
   ACCESS     read-write
   STATUS     mandatory
   DESCRIPTION
     "This attribute is used to display and set attributes."
::= { lpIlsFwdrLtFbDataTopEntry 1 }


-- LanTest IpHeader
-- This component adds an IP header to a frame or packet.

lpIlsFwdrLtFbIpH OBJECT IDENTIFIER ::= { lpIlsFwdrLtFb 7 }



lpIlsFwdrLtFbIpHRowStatusTable OBJECT-TYPE
   SYNTAX     SEQUENCE OF LpIlsFwdrLtFbIpHRowStatusEntry
   ACCESS     not-accessible
   STATUS     mandatory
   DESCRIPTION
     "This entry controls the addition and deletion of 
      lpIlsFwdrLtFbIpH components."
::= { lpIlsFwdrLtFbIpH 1 }

lpIlsFwdrLtFbIpHRowStatusEntry OBJECT-TYPE
   SYNTAX     LpIlsFwdrLtFbIpHRowStatusEntry
   ACCESS     not-accessible
   STATUS     mandatory
   DESCRIPTION
     "A single entry in the table represents a single 
      lpIlsFwdrLtFbIpH component."
   INDEX {
      lpIndex,
      lpIlsFwdrIndex,
      lpIlsFwdrLtIndex,
      lpIlsFwdrLtFbIndex,
      lpIlsFwdrLtFbIpHIndex }
::= { lpIlsFwdrLtFbIpHRowStatusTable 1 }

LpIlsFwdrLtFbIpHRowStatusEntry ::= SEQUENCE {
   lpIlsFwdrLtFbIpHRowStatus
      RowStatus,
   lpIlsFwdrLtFbIpHComponentName
      DisplayString,
   lpIlsFwdrLtFbIpHStorageType
      StorageType,
   lpIlsFwdrLtFbIpHIndex
      NonReplicated }

lpIlsFwdrLtFbIpHRowStatus OBJECT-TYPE
   SYNTAX     RowStatus 
   ACCESS     read-only
   STATUS     mandatory
   DESCRIPTION
     "This variable is used as the basis for SNMP naming of
      lpIlsFwdrLtFbIpH components.
      These components cannot be added nor deleted."
::= { lpIlsFwdrLtFbIpHRowStatusEntry 1 }

lpIlsFwdrLtFbIpHComponentName OBJECT-TYPE
   SYNTAX     DisplayString 
   ACCESS     read-only
   STATUS     mandatory
   DESCRIPTION
     "This variable provides the component's string name for
      use with the ASCII Console Interface"
::= { lpIlsFwdrLtFbIpHRowStatusEntry 2 }

lpIlsFwdrLtFbIpHStorageType OBJECT-TYPE
   SYNTAX     StorageType 
   ACCESS     read-only
   STATUS     mandatory
   DESCRIPTION
     "This variable represents the storage type value for the
      lpIlsFwdrLtFbIpH tables."
::= { lpIlsFwdrLtFbIpHRowStatusEntry 4 }

lpIlsFwdrLtFbIpHIndex OBJECT-TYPE
   SYNTAX     NonReplicated 
   ACCESS     not-accessible
   STATUS     mandatory
   DESCRIPTION
     "This variable represents the index for the lpIlsFwdrLtFbIpH tables."
::= { lpIlsFwdrLtFbIpHRowStatusEntry 10 }

lpIlsFwdrLtFbIpHTopTable OBJECT-TYPE
   SYNTAX     SEQUENCE OF LpIlsFwdrLtFbIpHTopEntry
   ACCESS     not-accessible
   STATUS     mandatory
   DESCRIPTION
     "This group contains the operational data for the LanTest component 
      and its subcomponents."
::= { lpIlsFwdrLtFbIpH 10 }

lpIlsFwdrLtFbIpHTopEntry OBJECT-TYPE
   SYNTAX     LpIlsFwdrLtFbIpHTopEntry
   ACCESS     not-accessible
   STATUS     mandatory
   DESCRIPTION
     "An entry in the lpIlsFwdrLtFbIpHTopTable."
   INDEX {
      lpIndex,
      lpIlsFwdrIndex,
      lpIlsFwdrLtIndex,
      lpIlsFwdrLtFbIndex,
      lpIlsFwdrLtFbIpHIndex }
::= { lpIlsFwdrLtFbIpHTopTable 1 }

LpIlsFwdrLtFbIpHTopEntry ::= SEQUENCE {
   lpIlsFwdrLtFbIpHTData
      AsciiString }

lpIlsFwdrLtFbIpHTData OBJECT-TYPE
   SYNTAX     AsciiString (SIZE (0..255))
   ACCESS     read-write
   STATUS     mandatory
   DESCRIPTION
     "This attribute is used to display and set attributes."
::= { lpIlsFwdrLtFbIpHTopEntry 1 }


-- LanTest LlcHeader
-- This component adds an LLC 802.2 or Ethernet header to a frame 
-- or packet.

lpIlsFwdrLtFbLlch OBJECT IDENTIFIER ::= { lpIlsFwdrLtFb 8 }



lpIlsFwdrLtFbLlchRowStatusTable OBJECT-TYPE
   SYNTAX     SEQUENCE OF LpIlsFwdrLtFbLlchRowStatusEntry
   ACCESS     not-accessible
   STATUS     mandatory
   DESCRIPTION
     "This entry controls the addition and deletion of 
      lpIlsFwdrLtFbLlch components."
::= { lpIlsFwdrLtFbLlch 1 }

lpIlsFwdrLtFbLlchRowStatusEntry OBJECT-TYPE
   SYNTAX     LpIlsFwdrLtFbLlchRowStatusEntry
   ACCESS     not-accessible
   STATUS     mandatory
   DESCRIPTION
     "A single entry in the table represents a single 
      lpIlsFwdrLtFbLlch component."
   INDEX {
      lpIndex,
      lpIlsFwdrIndex,
      lpIlsFwdrLtIndex,
      lpIlsFwdrLtFbIndex,
      lpIlsFwdrLtFbLlchIndex }
::= { lpIlsFwdrLtFbLlchRowStatusTable 1 }

LpIlsFwdrLtFbLlchRowStatusEntry ::= SEQUENCE {
   lpIlsFwdrLtFbLlchRowStatus
      RowStatus,
   lpIlsFwdrLtFbLlchComponentName
      DisplayString,
   lpIlsFwdrLtFbLlchStorageType
      StorageType,
   lpIlsFwdrLtFbLlchIndex
      NonReplicated }

lpIlsFwdrLtFbLlchRowStatus OBJECT-TYPE
   SYNTAX     RowStatus 
   ACCESS     read-only
   STATUS     mandatory
   DESCRIPTION
     "This variable is used as the basis for SNMP naming of
      lpIlsFwdrLtFbLlch components.
      These components cannot be added nor deleted."
::= { lpIlsFwdrLtFbLlchRowStatusEntry 1 }

lpIlsFwdrLtFbLlchComponentName OBJECT-TYPE
   SYNTAX     DisplayString 
   ACCESS     read-only
   STATUS     mandatory
   DESCRIPTION
     "This variable provides the component's string name for
      use with the ASCII Console Interface"
::= { lpIlsFwdrLtFbLlchRowStatusEntry 2 }

lpIlsFwdrLtFbLlchStorageType OBJECT-TYPE
   SYNTAX     StorageType 
   ACCESS     read-only
   STATUS     mandatory
   DESCRIPTION
     "This variable represents the storage type value for the
      lpIlsFwdrLtFbLlch tables."
::= { lpIlsFwdrLtFbLlchRowStatusEntry 4 }

lpIlsFwdrLtFbLlchIndex OBJECT-TYPE
   SYNTAX     NonReplicated 
   ACCESS     not-accessible
   STATUS     mandatory
   DESCRIPTION
     "This variable represents the index for the lpIlsFwdrLtFbLlch tables."
::= { lpIlsFwdrLtFbLlchRowStatusEntry 10 }

lpIlsFwdrLtFbLlchTopTable OBJECT-TYPE
   SYNTAX     SEQUENCE OF LpIlsFwdrLtFbLlchTopEntry
   ACCESS     not-accessible
   STATUS     mandatory
   DESCRIPTION
     "This group contains the operational data for the LanTest component 
      and its subcomponents."
::= { lpIlsFwdrLtFbLlch 10 }

lpIlsFwdrLtFbLlchTopEntry OBJECT-TYPE
   SYNTAX     LpIlsFwdrLtFbLlchTopEntry
   ACCESS     not-accessible
   STATUS     mandatory
   DESCRIPTION
     "An entry in the lpIlsFwdrLtFbLlchTopTable."
   INDEX {
      lpIndex,
      lpIlsFwdrIndex,
      lpIlsFwdrLtIndex,
      lpIlsFwdrLtFbIndex,
      lpIlsFwdrLtFbLlchIndex }
::= { lpIlsFwdrLtFbLlchTopTable 1 }

LpIlsFwdrLtFbLlchTopEntry ::= SEQUENCE {
   lpIlsFwdrLtFbLlchTData
      AsciiString }

lpIlsFwdrLtFbLlchTData OBJECT-TYPE
   SYNTAX     AsciiString (SIZE (0..255))
   ACCESS     read-write
   STATUS     mandatory
   DESCRIPTION
     "This attribute is used to display and set attributes."
::= { lpIlsFwdrLtFbLlchTopEntry 1 }


-- This component adds an AppleTalk header to a frame or packet.

lpIlsFwdrLtFbAppleH OBJECT IDENTIFIER ::= { lpIlsFwdrLtFb 9 }



lpIlsFwdrLtFbAppleHRowStatusTable OBJECT-TYPE
   SYNTAX     SEQUENCE OF LpIlsFwdrLtFbAppleHRowStatusEntry
   ACCESS     not-accessible
   STATUS     mandatory
   DESCRIPTION
     "This entry controls the addition and deletion of 
      lpIlsFwdrLtFbAppleH components."
::= { lpIlsFwdrLtFbAppleH 1 }

lpIlsFwdrLtFbAppleHRowStatusEntry OBJECT-TYPE
   SYNTAX     LpIlsFwdrLtFbAppleHRowStatusEntry
   ACCESS     not-accessible
   STATUS     mandatory
   DESCRIPTION
     "A single entry in the table represents a single 
      lpIlsFwdrLtFbAppleH component."
   INDEX {
      lpIndex,
      lpIlsFwdrIndex,
      lpIlsFwdrLtIndex,
      lpIlsFwdrLtFbIndex,
      lpIlsFwdrLtFbAppleHIndex }
::= { lpIlsFwdrLtFbAppleHRowStatusTable 1 }

LpIlsFwdrLtFbAppleHRowStatusEntry ::= SEQUENCE {
   lpIlsFwdrLtFbAppleHRowStatus
      RowStatus,
   lpIlsFwdrLtFbAppleHComponentName
      DisplayString,
   lpIlsFwdrLtFbAppleHStorageType
      StorageType,
   lpIlsFwdrLtFbAppleHIndex
      NonReplicated }

lpIlsFwdrLtFbAppleHRowStatus OBJECT-TYPE
   SYNTAX     RowStatus 
   ACCESS     read-only
   STATUS     mandatory
   DESCRIPTION
     "This variable is used as the basis for SNMP naming of
      lpIlsFwdrLtFbAppleH components.
      These components cannot be added nor deleted."
::= { lpIlsFwdrLtFbAppleHRowStatusEntry 1 }

lpIlsFwdrLtFbAppleHComponentName OBJECT-TYPE
   SYNTAX     DisplayString 
   ACCESS     read-only
   STATUS     mandatory
   DESCRIPTION
     "This variable provides the component's string name for
      use with the ASCII Console Interface"
::= { lpIlsFwdrLtFbAppleHRowStatusEntry 2 }

lpIlsFwdrLtFbAppleHStorageType OBJECT-TYPE
   SYNTAX     StorageType 
   ACCESS     read-only
   STATUS     mandatory
   DESCRIPTION
     "This variable represents the storage type value for the
      lpIlsFwdrLtFbAppleH tables."
::= { lpIlsFwdrLtFbAppleHRowStatusEntry 4 }

lpIlsFwdrLtFbAppleHIndex OBJECT-TYPE
   SYNTAX     NonReplicated 
   ACCESS     not-accessible
   STATUS     mandatory
   DESCRIPTION
     "This variable represents the index for the lpIlsFwdrLtFbAppleH tables."
::= { lpIlsFwdrLtFbAppleHRowStatusEntry 10 }

lpIlsFwdrLtFbAppleHTopTable OBJECT-TYPE
   SYNTAX     SEQUENCE OF LpIlsFwdrLtFbAppleHTopEntry
   ACCESS     not-accessible
   STATUS     mandatory
   DESCRIPTION
     "This group contains the operational data for the LanTest component 
      and its subcomponents."
::= { lpIlsFwdrLtFbAppleH 10 }

lpIlsFwdrLtFbAppleHTopEntry OBJECT-TYPE
   SYNTAX     LpIlsFwdrLtFbAppleHTopEntry
   ACCESS     not-accessible
   STATUS     mandatory
   DESCRIPTION
     "An entry in the lpIlsFwdrLtFbAppleHTopTable."
   INDEX {
      lpIndex,
      lpIlsFwdrIndex,
      lpIlsFwdrLtIndex,
      lpIlsFwdrLtFbIndex,
      lpIlsFwdrLtFbAppleHIndex }
::= { lpIlsFwdrLtFbAppleHTopTable 1 }

LpIlsFwdrLtFbAppleHTopEntry ::= SEQUENCE {
   lpIlsFwdrLtFbAppleHTData
      AsciiString }

lpIlsFwdrLtFbAppleHTData OBJECT-TYPE
   SYNTAX     AsciiString (SIZE (0..255))
   ACCESS     read-write
   STATUS     mandatory
   DESCRIPTION
     "This attribute is used to display and set attributes."
::= { lpIlsFwdrLtFbAppleHTopEntry 1 }


-- This component adds an IPX header to a frame or packet.

lpIlsFwdrLtFbIpxH OBJECT IDENTIFIER ::= { lpIlsFwdrLtFb 10 }



lpIlsFwdrLtFbIpxHRowStatusTable OBJECT-TYPE
   SYNTAX     SEQUENCE OF LpIlsFwdrLtFbIpxHRowStatusEntry
   ACCESS     not-accessible
   STATUS     mandatory
   DESCRIPTION
     "This entry controls the addition and deletion of 
      lpIlsFwdrLtFbIpxH components."
::= { lpIlsFwdrLtFbIpxH 1 }

lpIlsFwdrLtFbIpxHRowStatusEntry OBJECT-TYPE
   SYNTAX     LpIlsFwdrLtFbIpxHRowStatusEntry
   ACCESS     not-accessible
   STATUS     mandatory
   DESCRIPTION
     "A single entry in the table represents a single 
      lpIlsFwdrLtFbIpxH component."
   INDEX {
      lpIndex,
      lpIlsFwdrIndex,
      lpIlsFwdrLtIndex,
      lpIlsFwdrLtFbIndex,
      lpIlsFwdrLtFbIpxHIndex }
::= { lpIlsFwdrLtFbIpxHRowStatusTable 1 }

LpIlsFwdrLtFbIpxHRowStatusEntry ::= SEQUENCE {
   lpIlsFwdrLtFbIpxHRowStatus
      RowStatus,
   lpIlsFwdrLtFbIpxHComponentName
      DisplayString,
   lpIlsFwdrLtFbIpxHStorageType
      StorageType,
   lpIlsFwdrLtFbIpxHIndex
      NonReplicated }

lpIlsFwdrLtFbIpxHRowStatus OBJECT-TYPE
   SYNTAX     RowStatus 
   ACCESS     read-only
   STATUS     mandatory
   DESCRIPTION
     "This variable is used as the basis for SNMP naming of
      lpIlsFwdrLtFbIpxH components.
      These components cannot be added nor deleted."
::= { lpIlsFwdrLtFbIpxHRowStatusEntry 1 }

lpIlsFwdrLtFbIpxHComponentName OBJECT-TYPE
   SYNTAX     DisplayString 
   ACCESS     read-only
   STATUS     mandatory
   DESCRIPTION
     "This variable provides the component's string name for
      use with the ASCII Console Interface"
::= { lpIlsFwdrLtFbIpxHRowStatusEntry 2 }

lpIlsFwdrLtFbIpxHStorageType OBJECT-TYPE
   SYNTAX     StorageType 
   ACCESS     read-only
   STATUS     mandatory
   DESCRIPTION
     "This variable represents the storage type value for the
      lpIlsFwdrLtFbIpxH tables."
::= { lpIlsFwdrLtFbIpxHRowStatusEntry 4 }

lpIlsFwdrLtFbIpxHIndex OBJECT-TYPE
   SYNTAX     NonReplicated 
   ACCESS     not-accessible
   STATUS     mandatory
   DESCRIPTION
     "This variable represents the index for the lpIlsFwdrLtFbIpxH tables."
::= { lpIlsFwdrLtFbIpxHRowStatusEntry 10 }

lpIlsFwdrLtFbIpxHTopTable OBJECT-TYPE
   SYNTAX     SEQUENCE OF LpIlsFwdrLtFbIpxHTopEntry
   ACCESS     not-accessible
   STATUS     mandatory
   DESCRIPTION
     "This group contains the operational data for the LanTest component 
      and its subcomponents."
::= { lpIlsFwdrLtFbIpxH 10 }

lpIlsFwdrLtFbIpxHTopEntry OBJECT-TYPE
   SYNTAX     LpIlsFwdrLtFbIpxHTopEntry
   ACCESS     not-accessible
   STATUS     mandatory
   DESCRIPTION
     "An entry in the lpIlsFwdrLtFbIpxHTopTable."
   INDEX {
      lpIndex,
      lpIlsFwdrIndex,
      lpIlsFwdrLtIndex,
      lpIlsFwdrLtFbIndex,
      lpIlsFwdrLtFbIpxHIndex }
::= { lpIlsFwdrLtFbIpxHTopTable 1 }

LpIlsFwdrLtFbIpxHTopEntry ::= SEQUENCE {
   lpIlsFwdrLtFbIpxHTData
      AsciiString }

lpIlsFwdrLtFbIpxHTData OBJECT-TYPE
   SYNTAX     AsciiString (SIZE (0..255))
   ACCESS     read-write
   STATUS     mandatory
   DESCRIPTION
     "This attribute is used to display and set attributes."
::= { lpIlsFwdrLtFbIpxHTopEntry 1 }


-- LanTest Control
-- This component controls the overall testing by telling the 
-- FrameBuild component to start and check the FrameCompare 
-- component to see if the test is complete.

lpIlsFwdrLtCntl OBJECT IDENTIFIER ::= { lpIlsFwdrLt 6 }



lpIlsFwdrLtCntlRowStatusTable OBJECT-TYPE
   SYNTAX     SEQUENCE OF LpIlsFwdrLtCntlRowStatusEntry
   ACCESS     not-accessible
   STATUS     mandatory
   DESCRIPTION
     "This entry controls the addition and deletion of 
      lpIlsFwdrLtCntl components."
::= { lpIlsFwdrLtCntl 1 }

lpIlsFwdrLtCntlRowStatusEntry OBJECT-TYPE
   SYNTAX     LpIlsFwdrLtCntlRowStatusEntry
   ACCESS     not-accessible
   STATUS     mandatory
   DESCRIPTION
     "A single entry in the table represents a single 
      lpIlsFwdrLtCntl component."
   INDEX {
      lpIndex,
      lpIlsFwdrIndex,
      lpIlsFwdrLtIndex,
      lpIlsFwdrLtCntlIndex }
::= { lpIlsFwdrLtCntlRowStatusTable 1 }

LpIlsFwdrLtCntlRowStatusEntry ::= SEQUENCE {
   lpIlsFwdrLtCntlRowStatus
      RowStatus,
   lpIlsFwdrLtCntlComponentName
      DisplayString,
   lpIlsFwdrLtCntlStorageType
      StorageType,
   lpIlsFwdrLtCntlIndex
      NonReplicated }

lpIlsFwdrLtCntlRowStatus OBJECT-TYPE
   SYNTAX     RowStatus 
   ACCESS     read-only
   STATUS     mandatory
   DESCRIPTION
     "This variable is used as the basis for SNMP naming of
      lpIlsFwdrLtCntl components.
      These components cannot be added nor deleted."
::= { lpIlsFwdrLtCntlRowStatusEntry 1 }

lpIlsFwdrLtCntlComponentName OBJECT-TYPE
   SYNTAX     DisplayString 
   ACCESS     read-only
   STATUS     mandatory
   DESCRIPTION
     "This variable provides the component's string name for
      use with the ASCII Console Interface"
::= { lpIlsFwdrLtCntlRowStatusEntry 2 }

lpIlsFwdrLtCntlStorageType OBJECT-TYPE
   SYNTAX     StorageType 
   ACCESS     read-only
   STATUS     mandatory
   DESCRIPTION
     "This variable represents the storage type value for the
      lpIlsFwdrLtCntl tables."
::= { lpIlsFwdrLtCntlRowStatusEntry 4 }

lpIlsFwdrLtCntlIndex OBJECT-TYPE
   SYNTAX     NonReplicated 
   ACCESS     not-accessible
   STATUS     mandatory
   DESCRIPTION
     "This variable represents the index for the lpIlsFwdrLtCntl tables."
::= { lpIlsFwdrLtCntlRowStatusEntry 10 }

lpIlsFwdrLtCntlTopTable OBJECT-TYPE
   SYNTAX     SEQUENCE OF LpIlsFwdrLtCntlTopEntry
   ACCESS     not-accessible
   STATUS     mandatory
   DESCRIPTION
     "This group contains the operational data for the LanTest component 
      and its subcomponents."
::= { lpIlsFwdrLtCntl 10 }

lpIlsFwdrLtCntlTopEntry OBJECT-TYPE
   SYNTAX     LpIlsFwdrLtCntlTopEntry
   ACCESS     not-accessible
   STATUS     mandatory
   DESCRIPTION
     "An entry in the lpIlsFwdrLtCntlTopTable."
   INDEX {
      lpIndex,
      lpIlsFwdrIndex,
      lpIlsFwdrLtIndex,
      lpIlsFwdrLtCntlIndex }
::= { lpIlsFwdrLtCntlTopTable 1 }

LpIlsFwdrLtCntlTopEntry ::= SEQUENCE {
   lpIlsFwdrLtCntlTData
      AsciiString }

lpIlsFwdrLtCntlTData OBJECT-TYPE
   SYNTAX     AsciiString (SIZE (0..255))
   ACCESS     read-write
   STATUS     mandatory
   DESCRIPTION
     "This attribute is used to display and set attributes."
::= { lpIlsFwdrLtCntlTopEntry 1 }


-- Lp/n Fddi/n Test, or
-- Lp/n Ethernet/n Test, or
-- Lp/n TokenRing/n Test, or
-- Lp/n IlsForwarder/n Test
-- The Test component is used to do StartUp port test for LAN cards.

lpIlsFwdrTest OBJECT IDENTIFIER ::= { lpIlsFwdr 5 }



lpIlsFwdrTestRowStatusTable OBJECT-TYPE
   SYNTAX     SEQUENCE OF LpIlsFwdrTestRowStatusEntry
   ACCESS     not-accessible
   STATUS     mandatory
   DESCRIPTION
     "This entry controls the addition and deletion of 
      lpIlsFwdrTest components."
::= { lpIlsFwdrTest 1 }

lpIlsFwdrTestRowStatusEntry OBJECT-TYPE
   SYNTAX     LpIlsFwdrTestRowStatusEntry
   ACCESS     not-accessible
   STATUS     mandatory
   DESCRIPTION
     "A single entry in the table represents a single 
      lpIlsFwdrTest component."
   INDEX {
      lpIndex,
      lpIlsFwdrIndex,
      lpIlsFwdrTestIndex }
::= { lpIlsFwdrTestRowStatusTable 1 }

LpIlsFwdrTestRowStatusEntry ::= SEQUENCE {
   lpIlsFwdrTestRowStatus
      RowStatus,
   lpIlsFwdrTestComponentName
      DisplayString,
   lpIlsFwdrTestStorageType
      StorageType,
   lpIlsFwdrTestIndex
      NonReplicated }

lpIlsFwdrTestRowStatus OBJECT-TYPE
   SYNTAX     RowStatus 
   ACCESS     read-only
   STATUS     mandatory
   DESCRIPTION
     "This variable is used as the basis for SNMP naming of
      lpIlsFwdrTest components.
      These components cannot be added nor deleted."
::= { lpIlsFwdrTestRowStatusEntry 1 }

lpIlsFwdrTestComponentName OBJECT-TYPE
   SYNTAX     DisplayString 
   ACCESS     read-only
   STATUS     mandatory
   DESCRIPTION
     "This variable provides the component's string name for
      use with the ASCII Console Interface"
::= { lpIlsFwdrTestRowStatusEntry 2 }

lpIlsFwdrTestStorageType OBJECT-TYPE
   SYNTAX     StorageType 
   ACCESS     read-only
   STATUS     mandatory
   DESCRIPTION
     "This variable represents the storage type value for the
      lpIlsFwdrTest tables."
::= { lpIlsFwdrTestRowStatusEntry 4 }

lpIlsFwdrTestIndex OBJECT-TYPE
   SYNTAX     NonReplicated 
   ACCESS     not-accessible
   STATUS     mandatory
   DESCRIPTION
     "This variable represents the index for the lpIlsFwdrTest tables."
::= { lpIlsFwdrTestRowStatusEntry 10 }

lpIlsFwdrTestPTOTable OBJECT-TYPE
   SYNTAX     SEQUENCE OF LpIlsFwdrTestPTOEntry
   ACCESS     not-accessible
   STATUS     mandatory
   DESCRIPTION
     "This group contains the operational data for the LanPortTest 
      component."
::= { lpIlsFwdrTest 10 }

lpIlsFwdrTestPTOEntry OBJECT-TYPE
   SYNTAX     LpIlsFwdrTestPTOEntry
   ACCESS     not-accessible
   STATUS     mandatory
   DESCRIPTION
     "An entry in the lpIlsFwdrTestPTOTable."
   INDEX {
      lpIndex,
      lpIlsFwdrIndex,
      lpIlsFwdrTestIndex }
::= { lpIlsFwdrTestPTOTable 1 }

LpIlsFwdrTestPTOEntry ::= SEQUENCE {
   lpIlsFwdrTestType
      INTEGER,
   lpIlsFwdrTestFrmSize
      Unsigned32,
   lpIlsFwdrTestDuration
      Unsigned32 }

lpIlsFwdrTestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { lpIlsFwdrTestPTOEntry 1 }

lpIlsFwdrTestFrmSize OBJECT-TYPE
   SYNTAX     Unsigned32 (4..4096)
   ACCESS     read-write
   STATUS     mandatory
   DESCRIPTION
     "This attribute defines the size of the test data frames in number of 
      bytes."
   DEFVAL     { 1024 }
::= { lpIlsFwdrTestPTOEntry 2 }

lpIlsFwdrTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpIlsFwdrTestPTOEntry 3 }

lpIlsFwdrTestResultsTable OBJECT-TYPE
   SYNTAX     SEQUENCE OF LpIlsFwdrTestResultsEntry
   ACCESS     not-accessible
   STATUS     mandatory
   DESCRIPTION
     "This group contains all the statistics related attributes of the Test 
      component."
::= { lpIlsFwdrTest 11 }

lpIlsFwdrTestResultsEntry OBJECT-TYPE
   SYNTAX     LpIlsFwdrTestResultsEntry
   ACCESS     not-accessible
   STATUS     mandatory
   DESCRIPTION
     "An entry in the lpIlsFwdrTestResultsTable."
   INDEX {
      lpIndex,
      lpIlsFwdrIndex,
      lpIlsFwdrTestIndex }
::= { lpIlsFwdrTestResultsTable 1 }

LpIlsFwdrTestResultsEntry ::= SEQUENCE {
   lpIlsFwdrTestElapsedTime
      Counter32,
   lpIlsFwdrTestTimeRemaining
      Unsigned32,
   lpIlsFwdrTestCauseOfTermination
      INTEGER,
   lpIlsFwdrTestFrmTx
      PassportCounter64,
   lpIlsFwdrTestBitsTx
      PassportCounter64,
   lpIlsFwdrTestFrmRx
      PassportCounter64,
   lpIlsFwdrTestBitsRx
      PassportCounter64,
   lpIlsFwdrTestErroredFrmRx
      PassportCounter64 }

lpIlsFwdrTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpIlsFwdrTestResultsEntry 4 }

lpIlsFwdrTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpIlsFwdrTestResultsEntry 5 }

lpIlsFwdrTestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { lpIlsFwdrTestResultsEntry 6 }

lpIlsFwdrTestFrmTx OBJECT-TYPE
   SYNTAX     PassportCounter64 
   ACCESS     read-only
   STATUS     mandatory
   DESCRIPTION
     "This attribute is the total number of frames sent during the test 
      period. This counter is not expected to reach its maximum value."
::= { lpIlsFwdrTestResultsEntry 7 }

lpIlsFwdrTestBitsTx OBJECT-TYPE
   SYNTAX     PassportCounter64 
   ACCESS     read-only
   STATUS     mandatory
   DESCRIPTION
     "This attribute is the total number of bits sent during the test period. 
      This counter is not expected to reach its maximum value."
::= { lpIlsFwdrTestResultsEntry 8 }

lpIlsFwdrTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpIlsFwdrTestResultsEntry 9 }

lpIlsFwdrTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { lpIlsFwdrTestResultsEntry 10 }

lpIlsFwdrTestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { lpIlsFwdrTestResultsEntry 11 }


-- Lp/n Ethernet100BaseT/n
-- This component defines an instance of a 100BaseT Ethernet station 
-- attached to a bus. One instance of this component must be created for 
-- each hardware interface.

lpEth100 OBJECT IDENTIFIER ::= { lp 25 }



lpEth100RowStatusTable OBJECT-TYPE
   SYNTAX     SEQUENCE OF LpEth100RowStatusEntry
   ACCESS     not-accessible
   STATUS     mandatory
   DESCRIPTION
     "This entry controls the addition and deletion of 
      lpEth100 components."
::= { lpEth100 1 }

lpEth100RowStatusEntry OBJECT-TYPE
   SYNTAX     LpEth100RowStatusEntry
   ACCESS     not-accessible
   STATUS     mandatory
   DESCRIPTION
     "A single entry in the table represents a single 
      lpEth100 component."
   INDEX {
      lpIndex,
      lpEth100Index }
::= { lpEth100RowStatusTable 1 }

LpEth100RowStatusEntry ::= SEQUENCE {
   lpEth100RowStatus
      RowStatus,
   lpEth100ComponentName
      DisplayString,
   lpEth100StorageType
      StorageType,
   lpEth100Index
      Integer32 }

lpEth100RowStatus OBJECT-TYPE
   SYNTAX     RowStatus 
   ACCESS     read-write
   STATUS     mandatory
   DESCRIPTION
     "This variable is used as the basis for SNMP naming of
      lpEth100 components.
      These components can be added and deleted."
::= { lpEth100RowStatusEntry 1 }

lpEth100ComponentName OBJECT-TYPE
   SYNTAX     DisplayString 
   ACCESS     read-only
   STATUS     mandatory
   DESCRIPTION
     "This variable provides the component's string name for
      use with the ASCII Console Interface"
::= { lpEth100RowStatusEntry 2 }

lpEth100StorageType OBJECT-TYPE
   SYNTAX     StorageType 
   ACCESS     read-only
   STATUS     mandatory
   DESCRIPTION
     "This variable represents the storage type value for the
      lpEth100 tables."
::= { lpEth100RowStatusEntry 4 }

lpEth100Index OBJECT-TYPE
   SYNTAX     Integer32 (0..1)
   ACCESS     not-accessible
   STATUS     mandatory
   DESCRIPTION
     "This variable represents the index for the lpEth100 tables."
::= { lpEth100RowStatusEntry 10 }

lpEth100CidDataTable OBJECT-TYPE
   SYNTAX     SEQUENCE OF LpEth100CidDataEntry
   ACCESS     not-accessible
   STATUS     mandatory
   DESCRIPTION
     "This group contains the attribute for a component's Customer 
      Identifier (CID). Refer to the attribute description for a detailed 
      explanation of CIDs."
::= { lpEth100 10 }

lpEth100CidDataEntry OBJECT-TYPE
   SYNTAX     LpEth100CidDataEntry
   ACCESS     not-accessible
   STATUS     mandatory
   DESCRIPTION
     "An entry in the lpEth100CidDataTable."
   INDEX {
      lpIndex,
      lpEth100Index }
::= { lpEth100CidDataTable 1 }

LpEth100CidDataEntry ::= SEQUENCE {
   lpEth100CustomerIdentifier
      Unsigned32 }

lpEth100CustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpEth100CidDataEntry 1 }

lpEth100IfEntryTable OBJECT-TYPE
   SYNTAX     SEQUENCE OF LpEth100IfEntryEntry
   ACCESS     not-accessible
   STATUS     mandatory
   DESCRIPTION
     "This group contains the provisionable attributes for the ifEntry."
::= { lpEth100 11 }

lpEth100IfEntryEntry OBJECT-TYPE
   SYNTAX     LpEth100IfEntryEntry
   ACCESS     not-accessible
   STATUS     mandatory
   DESCRIPTION
     "An entry in the lpEth100IfEntryTable."
   INDEX {
      lpIndex,
      lpEth100Index }
::= { lpEth100IfEntryTable 1 }

LpEth100IfEntryEntry ::= SEQUENCE {
   lpEth100IfAdminStatus
      INTEGER,
   lpEth100IfIndex
      InterfaceIndex }

lpEth100IfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lpEth100IfEntryEntry 1 }

lpEth100IfIndex OBJECT-TYPE
   SYNTAX     InterfaceIndex (1..65535)
   ACCESS     read-only
   STATUS     mandatory
   DESCRIPTION
     "This is the index for the IfEntry. Its value is automatically initialized 
      during the provisioning process."
::= { lpEth100IfEntryEntry 2 }

lpEth100ProvTable OBJECT-TYPE
   SYNTAX     SEQUENCE OF LpEth100ProvEntry
   ACCESS     not-accessible
   STATUS     mandatory
   DESCRIPTION
     "This group contains the provisionable attributes of the Eth100BaseT 
      component."
::= { lpEth100 12 }

lpEth100ProvEntry OBJECT-TYPE
   SYNTAX     LpEth100ProvEntry
   ACCESS     not-accessible
   STATUS     mandatory
   DESCRIPTION
     "An entry in the lpEth100ProvTable."
   INDEX {
      lpIndex,
      lpEth100Index }
::= { lpEth100ProvTable 1 }

LpEth100ProvEntry ::= SEQUENCE {
   lpEth100DuplexMode
      INTEGER,
   lpEth100LineSpeed
      Unsigned32,
   lpEth100AutoNegotiation
      INTEGER,
   lpEth100ApplicationFramerName
      Link }

lpEth100DuplexMode OBJECT-TYPE
   SYNTAX     INTEGER  {
                 half(1),
                 full(2) }
   ACCESS     read-write
   STATUS     mandatory
   DESCRIPTION
     "This attribute specifies the duplex mode of the port. This attribute is 
      ignored if auto negotiation is successful."
   DEFVAL     { half }
::= { lpEth100ProvEntry 1 }

lpEth100LineSpeed OBJECT-TYPE
   SYNTAX     Unsigned32 (10 | 100)
   ACCESS     read-write
   STATUS     mandatory
   DESCRIPTION
     "This attribute sets the operating speed for the Ethernet 100BaseT port. 
      This attribute is ignored if auto negotiation is successful."
   DEFVAL     { 100 }
::= { lpEth100ProvEntry 2 }

lpEth100AutoNegotiation OBJECT-TYPE
   SYNTAX     INTEGER  {
                 enabled(1),
                 disabled(2) }
   ACCESS     read-write
   STATUS     mandatory
   DESCRIPTION
     "This attribute is used to select whether or not the port does auto 
      negotiation. The provisionable values of duplexMode and lineSpeed are 
      ignored if auto negotiation is successful. Refer to the operational 
      attribute autoNegStatus for auto negotiation results."
   DEFVAL     { enabled }
::= { lpEth100ProvEntry 3 }

lpEth100ApplicationFramerName OBJECT-TYPE
   SYNTAX     Link 
   ACCESS     read-write
   STATUS     mandatory
   DESCRIPTION
     "This attribute contains the component name of a Framer which is 
      associated with the Eth100BaseT component. This defines which Lan 
      Application will be using this Eth100BaseT interface."
::= { lpEth100ProvEntry 4 }

lpEth100AdminInfoTable OBJECT-TYPE
   SYNTAX     SEQUENCE OF LpEth100AdminInfoEntry
   ACCESS     not-accessible
   STATUS     mandatory
   DESCRIPTION
     "This group contains the attributes pertaining to the vendor of the 
      equipment."
::= { lpEth100 13 }

lpEth100AdminInfoEntry OBJECT-TYPE
   SYNTAX     LpEth100AdminInfoEntry
   ACCESS     not-accessible
   STATUS     mandatory
   DESCRIPTION
     "An entry in the lpEth100AdminInfoTable."
   INDEX {
      lpIndex,
      lpEth100Index }
::= { lpEth100AdminInfoTable 1 }

LpEth100AdminInfoEntry ::= SEQUENCE {
   lpEth100Vendor
      AsciiString,
   lpEth100CommentText
      AsciiString }

lpEth100Vendor OBJECT-TYPE
   SYNTAX     AsciiString (SIZE (0..20))
   ACCESS     read-write
   STATUS     mandatory
   DESCRIPTION
     "This is the name of the vendor supplying the facility."
::= { lpEth100AdminInfoEntry 1 }

lpEth100CommentText OBJECT-TYPE
   SYNTAX     AsciiString (SIZE (0..60))
   ACCESS     read-write
   STATUS     mandatory
   DESCRIPTION
     "Any miscellaneous text about the facility."
::= { lpEth100AdminInfoEntry 2 }

lpEth100StateTable OBJECT-TYPE
   SYNTAX     SEQUENCE OF LpEth100StateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpEth100 15 }

lpEth100StateEntry OBJECT-TYPE
   SYNTAX     LpEth100StateEntry
   ACCESS     not-accessible
   STATUS     mandatory
   DESCRIPTION
     "An entry in the lpEth100StateTable."
   INDEX {
      lpIndex,
      lpEth100Index }
::= { lpEth100StateTable 1 }

LpEth100StateEntry ::= SEQUENCE {
   lpEth100AdminState
      INTEGER,
   lpEth100OperationalState
      INTEGER,
   lpEth100UsageState
      INTEGER }

lpEth100AdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpEth100StateEntry 1 }

lpEth100OperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpEth100StateEntry 2 }

lpEth100UsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpEth100StateEntry 3 }

lpEth100OperStatusTable OBJECT-TYPE
   SYNTAX     SEQUENCE OF LpEth100OperStatusEntry
   ACCESS     not-accessible
   STATUS     mandatory
   DESCRIPTION
     "This group includes the Operational Status attribute. This attribute 
      defines the current operational state of this component."
::= { lpEth100 16 }

lpEth100OperStatusEntry OBJECT-TYPE
   SYNTAX     LpEth100OperStatusEntry
   ACCESS     not-accessible
   STATUS     mandatory
   DESCRIPTION
     "An entry in the lpEth100OperStatusTable."
   INDEX {
      lpIndex,
      lpEth100Index }
::= { lpEth100OperStatusTable 1 }

LpEth100OperStatusEntry ::= SEQUENCE {
   lpEth100SnmpOperStatus
      INTEGER }

lpEth100SnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lpEth100OperStatusEntry 1 }

lpEth100OperTable OBJECT-TYPE
   SYNTAX     SEQUENCE OF LpEth100OperEntry
   ACCESS     not-accessible
   STATUS     mandatory
   DESCRIPTION
     "This group contains the Port operational attributes of the Eth100BaseT 
      component."
::= { lpEth100 17 }

lpEth100OperEntry OBJECT-TYPE
   SYNTAX     LpEth100OperEntry
   ACCESS     not-accessible
   STATUS     mandatory
   DESCRIPTION
     "An entry in the lpEth100OperTable."
   INDEX {
      lpIndex,
      lpEth100Index }
::= { lpEth100OperTable 1 }

LpEth100OperEntry ::= SEQUENCE {
   lpEth100MacAddress
      MacAddress,
   lpEth100AutoNegStatus
      INTEGER,
   lpEth100ActualLineSpeed
      Unsigned32,
   lpEth100ActualDuplexMode
      INTEGER }

lpEth100MacAddress OBJECT-TYPE
   SYNTAX     MacAddress (SIZE (6))
   ACCESS     read-only
   STATUS     mandatory
   DESCRIPTION
     "This attribute indicates the medium access controller (MAC) address. 
      The MAC address is displayed in canonical format."
::= { lpEth100OperEntry 1 }

lpEth100AutoNegStatus OBJECT-TYPE
   SYNTAX     INTEGER  {
                 succeeded(1),
                 failed(2),
                 disabled(3) }
   ACCESS     read-only
   STATUS     mandatory
   DESCRIPTION
     "This attribute displays the status of the auto negotiation at the Phy level."
::= { lpEth100OperEntry 4 }

lpEth100ActualLineSpeed OBJECT-TYPE
   SYNTAX     Unsigned32 (10 | 100)
   ACCESS     read-only
   STATUS     mandatory
   DESCRIPTION
     "This attribute indicates the line speed of the Eth100BaseT port."
::= { lpEth100OperEntry 5 }

lpEth100ActualDuplexMode OBJECT-TYPE
   SYNTAX     INTEGER  {
                 half(1),
                 full(2) }
   ACCESS     read-only
   STATUS     mandatory
   DESCRIPTION
     "This attribute indicates whether the hardware is in half duplex or full 
      duplex mode."
::= { lpEth100OperEntry 6 }

lpEth100Eth100StatsTable OBJECT-TYPE
   SYNTAX     SEQUENCE OF LpEth100Eth100StatsEntry
   ACCESS     not-accessible
   STATUS     mandatory
   DESCRIPTION
     "This group contains the statistical attributes for the Eth100BaseT 
      component."
::= { lpEth100 18 }

lpEth100Eth100StatsEntry OBJECT-TYPE
   SYNTAX     LpEth100Eth100StatsEntry
   ACCESS     not-accessible
   STATUS     mandatory
   DESCRIPTION
     "An entry in the lpEth100Eth100StatsTable."
   INDEX {
      lpIndex,
      lpEth100Index }
::= { lpEth100Eth100StatsTable 1 }

LpEth100Eth100StatsEntry ::= SEQUENCE {
   lpEth100FramesTransmittedOk
      Counter32,
   lpEth100FramesReceivedOk
      Counter32,
   lpEth100OctetsTransmittedOk
      Counter32,
   lpEth100OctetsReceivedOk
      Counter32,
   lpEth100UndersizeFrames
      Counter32,
   lpEth100ReceivedOctetsIntoRouterBr
      Counter32,
   lpEth100ReceivedFramesIntoRouterBr
      Counter32 }

lpEth100FramesTransmittedOk OBJECT-TYPE
   SYNTAX     Counter32 
   ACCESS     read-only
   STATUS     mandatory
   DESCRIPTION
     "This attribute counts the number of frames which were transmitted 
      without errors. This counter wraps to zero after it reaches its maximum 
      value."
::= { lpEth100Eth100StatsEntry 1 }

lpEth100FramesReceivedOk OBJECT-TYPE
   SYNTAX     Counter32 
   ACCESS     read-only
   STATUS     mandatory
   DESCRIPTION
     "This attribute counts the number of frames which were received without 
      errors. This counter wraps to zero after it reaches its maximum value."
::= { lpEth100Eth100StatsEntry 2 }

lpEth100OctetsTransmittedOk OBJECT-TYPE
   SYNTAX     Counter32 
   ACCESS     read-only
   STATUS     mandatory
   DESCRIPTION
     "This attribute counts the number of octets which were transmitted 
      without errors. This counter wraps to zero after it reaches its maximum 
      value."
::= { lpEth100Eth100StatsEntry 3 }

lpEth100OctetsReceivedOk OBJECT-TYPE
   SYNTAX     Counter32 
   ACCESS     read-only
   STATUS     mandatory
   DESCRIPTION
     "This attribute counts the number of octets which were received without 
      errors. This counter wraps to zero after it reaches its maximum value."
::= { lpEth100Eth100StatsEntry 4 }

lpEth100UndersizeFrames OBJECT-TYPE
   SYNTAX     Counter32 
   ACCESS     read-only
   STATUS     mandatory
   DESCRIPTION
     "This attribute counts the number of frames that were received but were 
      less than the minimum size (64 bytes). This counter wraps to zero after 
      it reaches its maximum value."
::= { lpEth100Eth100StatsEntry 5 }

lpEth100ReceivedOctetsIntoRouterBr OBJECT-TYPE
   SYNTAX     Counter32 
   ACCESS     read-only
   STATUS     mandatory
   DESCRIPTION
     "This attribute counts the number of octets that were not hardware 
      switched but were passed the Router or Bridge software. This counter 
      wraps to zero after it reaches its maximum value."
::= { lpEth100Eth100StatsEntry 6 }

lpEth100ReceivedFramesIntoRouterBr OBJECT-TYPE
   SYNTAX     Counter32 
   ACCESS     read-only
   STATUS     mandatory
   DESCRIPTION
     "This attribute counts the number of frames which were not hardware 
      switched but were passed to the Router or Bridge software. This counter 
      wraps to zero after it reaches its maximum value."
::= { lpEth100Eth100StatsEntry 7 }

lpEth100StatsTable OBJECT-TYPE
   SYNTAX     SEQUENCE OF LpEth100StatsEntry
   ACCESS     not-accessible
   STATUS     mandatory
   DESCRIPTION
     "This group contains statistical attributes for the		 Ethernet component."
::= { lpEth100 19 }

lpEth100StatsEntry OBJECT-TYPE
   SYNTAX     LpEth100StatsEntry
   ACCESS     not-accessible
   STATUS     mandatory
   DESCRIPTION
     "An entry in the lpEth100StatsTable."
   INDEX {
      lpIndex,
      lpEth100Index }
::= { lpEth100StatsTable 1 }

LpEth100StatsEntry ::= SEQUENCE {
   lpEth100AlignmentErrors
      Counter32,
   lpEth100FcsErrors
      Counter32,
   lpEth100SingleCollisionFrames
      Counter32,
   lpEth100MultipleCollisionFrames
      Counter32,
   lpEth100SqeTestErrors
      Counter32,
   lpEth100DeferredTransmissions
      Counter32,
   lpEth100LateCollisions
      Counter32,
   lpEth100ExcessiveCollisions
      Counter32,
   lpEth100MacTransmitErrors
      Counter32,
   lpEth100CarrierSenseErrors
      Counter32,
   lpEth100FrameTooLongs
      Counter32,
   lpEth100MacReceiveErrors
      Counter32 }

lpEth100AlignmentErrors OBJECT-TYPE
   SYNTAX     Counter32 
   ACCESS     read-only
   STATUS     mandatory
   DESCRIPTION
     "The alignmentErrors counter indicates the number of frames received 
      which were not an integral number of octets in length. Frames will be 
      checked for alignmentErrors before they are checked for Frame Check 
      Sequence (FCS) errors. If there is an alignment error, the error will only 
      be counted here and not in fcsErrors. This counter will wrap around 
      after it reaches its maximum value."
::= { lpEth100StatsEntry 2 }

lpEth100FcsErrors OBJECT-TYPE
   SYNTAX     Counter32 
   ACCESS     read-only
   STATUS     mandatory
   DESCRIPTION
     "The fcsErrors, Frame Check Sequence (FCS) error, counter indicates the 
      number of frames received which were an integral number of octets in 
      length and did not pass the FCS check. This counter will wrap around 
      after it reaches its maximum value."
::= { lpEth100StatsEntry 3 }

lpEth100SingleCollisionFrames OBJECT-TYPE
   SYNTAX     Counter32 
   ACCESS     read-only
   STATUS     mandatory
   DESCRIPTION
     "The singleCollisionFrames counter indicates the number of frames 
      successfully transmitted which experienced exactly one collision. This 
      counter will wrap around after it reaches its maximum value."
::= { lpEth100StatsEntry 4 }

lpEth100MultipleCollisionFrames OBJECT-TYPE
   SYNTAX     Counter32 
   ACCESS     read-only
   STATUS     mandatory
   DESCRIPTION
     "The multipleCollisionFrames counter indicates the number of frames 
      successfully transmitted which experienced more than one collision. 
      This counter will wrap around after it reaches its maximum value."
::= { lpEth100StatsEntry 5 }

lpEth100SqeTestErrors OBJECT-TYPE
   SYNTAX     Counter32 
   ACCESS     read-only
   STATUS     mandatory
   DESCRIPTION
     "The sqeTestErrors, Signal Quality Error (SQE) Test errors, counter 
      indicates the number of times the 'SQE Test Error' message has been 
      generated for the station. This counter will wrap around after it reaches 
      its maximum value."
::= { lpEth100StatsEntry 6 }

lpEth100DeferredTransmissions OBJECT-TYPE
   SYNTAX     Counter32 
   ACCESS     read-only
   STATUS     mandatory
   DESCRIPTION
     "The deferredTransmissions counter indicates the number of frames 
      which experienced a transmission delay because the medium was busy. 
      This counter will wrap around after it reaches its maximum value."
::= { lpEth100StatsEntry 7 }

lpEth100LateCollisions OBJECT-TYPE
   SYNTAX     Counter32 
   ACCESS     read-only
   STATUS     mandatory
   DESCRIPTION
     "The lateCollisions counter indicates the number of times a collision was 
      detected later than 512 bit-times into the transmission of a packet. This 
      counter will wrap around after it reaches its maximum value."
::= { lpEth100StatsEntry 8 }

lpEth100ExcessiveCollisions OBJECT-TYPE
   SYNTAX     Counter32 
   ACCESS     read-only
   STATUS     mandatory
   DESCRIPTION
     "The excessiveCollisions counter indicates the number of frames which 
      failed to get transmitted due to excessive collisions. This counter will 
      wrap around after it reaches its maximum value."
::= { lpEth100StatsEntry 9 }

lpEth100MacTransmitErrors OBJECT-TYPE
   SYNTAX     Counter32 
   ACCESS     read-only
   STATUS     mandatory
   DESCRIPTION
     "The Medium Access Controller (MAC) transmit error counter indicates 
      the number of times that a transmission failed due to internal MAC 
      transmit errors. This counter will wrap around after it reaches its 
      maximum value."
::= { lpEth100StatsEntry 10 }

lpEth100CarrierSenseErrors OBJECT-TYPE
   SYNTAX     Counter32 
   ACCESS     read-only
   STATUS     mandatory
   DESCRIPTION
     "The carrier sense error counter indicates the number of times that the 
      carrier sense condition was lost or never asserted when attempting to 
      transmit a frame. This counter will wrap around after it reaches its 
      maximum value."
::= { lpEth100StatsEntry 11 }

lpEth100FrameTooLongs OBJECT-TYPE
   SYNTAX     Counter32 
   ACCESS     read-only
   STATUS     mandatory
   DESCRIPTION
     "The frame too long counter indicates the number of frames received 
      which exceeded the maximum frame size. This counter will wrap 
      around after it reaches its maximum value."
::= { lpEth100StatsEntry 12 }

lpEth100MacReceiveErrors OBJECT-TYPE
   SYNTAX     Counter32 
   ACCESS     read-only
   STATUS     mandatory
   DESCRIPTION
     "The Medium Access Controller (MAC) receive error counter indicates 
      the number of times a receive failed due to internal MAC receive errors. 
      This counter will wrap around after it reaches its maximum value."
::= { lpEth100StatsEntry 13 }


-- Lp/n Fddi/n LanTest, or
-- Lp/n Ethernet/n LanTest, or
-- Lp/n TokenRing/n LanTest, or
-- Lp/n IlsForwarder/n LanTest
-- The LanTest component is used to control testing on LAN 
-- interfaces. This includes LLC layer loopback, on-card loopback, 
-- SNMP required tests, and any testing to be done in the lab or 
-- manufacturing.

lpEth100Lt OBJECT IDENTIFIER ::= { lpEth100 2 }



lpEth100LtRowStatusTable OBJECT-TYPE
   SYNTAX     SEQUENCE OF LpEth100LtRowStatusEntry
   ACCESS     not-accessible
   STATUS     mandatory
   DESCRIPTION
     "This entry controls the addition and deletion of 
      lpEth100Lt components."
::= { lpEth100Lt 1 }

lpEth100LtRowStatusEntry OBJECT-TYPE
   SYNTAX     LpEth100LtRowStatusEntry
   ACCESS     not-accessible
   STATUS     mandatory
   DESCRIPTION
     "A single entry in the table represents a single 
      lpEth100Lt component."
   INDEX {
      lpIndex,
      lpEth100Index,
      lpEth100LtIndex }
::= { lpEth100LtRowStatusTable 1 }

LpEth100LtRowStatusEntry ::= SEQUENCE {
   lpEth100LtRowStatus
      RowStatus,
   lpEth100LtComponentName
      DisplayString,
   lpEth100LtStorageType
      StorageType,
   lpEth100LtIndex
      NonReplicated }

lpEth100LtRowStatus OBJECT-TYPE
   SYNTAX     RowStatus 
   ACCESS     read-only
   STATUS     mandatory
   DESCRIPTION
     "This variable is used as the basis for SNMP naming of
      lpEth100Lt components.
      These components cannot be added nor deleted."
::= { lpEth100LtRowStatusEntry 1 }

lpEth100LtComponentName OBJECT-TYPE
   SYNTAX     DisplayString 
   ACCESS     read-only
   STATUS     mandatory
   DESCRIPTION
     "This variable provides the component's string name for
      use with the ASCII Console Interface"
::= { lpEth100LtRowStatusEntry 2 }

lpEth100LtStorageType OBJECT-TYPE
   SYNTAX     StorageType 
   ACCESS     read-only
   STATUS     mandatory
   DESCRIPTION
     "This variable represents the storage type value for the
      lpEth100Lt tables."
::= { lpEth100LtRowStatusEntry 4 }

lpEth100LtIndex OBJECT-TYPE
   SYNTAX     NonReplicated 
   ACCESS     not-accessible
   STATUS     mandatory
   DESCRIPTION
     "This variable represents the index for the lpEth100Lt tables."
::= { lpEth100LtRowStatusEntry 10 }

lpEth100LtTopTable OBJECT-TYPE
   SYNTAX     SEQUENCE OF LpEth100LtTopEntry
   ACCESS     not-accessible
   STATUS     mandatory
   DESCRIPTION
     "This group contains the operational data for the LanTest component 
      and its subcomponents."
::= { lpEth100Lt 20 }

lpEth100LtTopEntry OBJECT-TYPE
   SYNTAX     LpEth100LtTopEntry
   ACCESS     not-accessible
   STATUS     mandatory
   DESCRIPTION
     "An entry in the lpEth100LtTopTable."
   INDEX {
      lpIndex,
      lpEth100Index,
      lpEth100LtIndex }
::= { lpEth100LtTopTable 1 }

LpEth100LtTopEntry ::= SEQUENCE {
   lpEth100LtTData
      AsciiString }

lpEth100LtTData OBJECT-TYPE
   SYNTAX     AsciiString (SIZE (0..255))
   ACCESS     read-write
   STATUS     mandatory
   DESCRIPTION
     "This attribute is used to display and set attributes."
::= { lpEth100LtTopEntry 1 }


-- This component compares frames received from the hardware and 
-- emulator during testing.

lpEth100LtFrmCmp OBJECT IDENTIFIER ::= { lpEth100Lt 2 }



lpEth100LtFrmCmpRowStatusTable OBJECT-TYPE
   SYNTAX     SEQUENCE OF LpEth100LtFrmCmpRowStatusEntry
   ACCESS     not-accessible
   STATUS     mandatory
   DESCRIPTION
     "This entry controls the addition and deletion of 
      lpEth100LtFrmCmp components."
::= { lpEth100LtFrmCmp 1 }

lpEth100LtFrmCmpRowStatusEntry OBJECT-TYPE
   SYNTAX     LpEth100LtFrmCmpRowStatusEntry
   ACCESS     not-accessible
   STATUS     mandatory
   DESCRIPTION
     "A single entry in the table represents a single 
      lpEth100LtFrmCmp component."
   INDEX {
      lpIndex,
      lpEth100Index,
      lpEth100LtIndex,
      lpEth100LtFrmCmpIndex }
::= { lpEth100LtFrmCmpRowStatusTable 1 }

LpEth100LtFrmCmpRowStatusEntry ::= SEQUENCE {
   lpEth100LtFrmCmpRowStatus
      RowStatus,
   lpEth100LtFrmCmpComponentName
      DisplayString,
   lpEth100LtFrmCmpStorageType
      StorageType,
   lpEth100LtFrmCmpIndex
      NonReplicated }

lpEth100LtFrmCmpRowStatus OBJECT-TYPE
   SYNTAX     RowStatus 
   ACCESS     read-only
   STATUS     mandatory
   DESCRIPTION
     "This variable is used as the basis for SNMP naming of
      lpEth100LtFrmCmp components.
      These components cannot be added nor deleted."
::= { lpEth100LtFrmCmpRowStatusEntry 1 }

lpEth100LtFrmCmpComponentName OBJECT-TYPE
   SYNTAX     DisplayString 
   ACCESS     read-only
   STATUS     mandatory
   DESCRIPTION
     "This variable provides the component's string name for
      use with the ASCII Console Interface"
::= { lpEth100LtFrmCmpRowStatusEntry 2 }

lpEth100LtFrmCmpStorageType OBJECT-TYPE
   SYNTAX     StorageType 
   ACCESS     read-only
   STATUS     mandatory
   DESCRIPTION
     "This variable represents the storage type value for the
      lpEth100LtFrmCmp tables."
::= { lpEth100LtFrmCmpRowStatusEntry 4 }

lpEth100LtFrmCmpIndex OBJECT-TYPE
   SYNTAX     NonReplicated 
   ACCESS     not-accessible
   STATUS     mandatory
   DESCRIPTION
     "This variable represents the index for the lpEth100LtFrmCmp tables."
::= { lpEth100LtFrmCmpRowStatusEntry 10 }

lpEth100LtFrmCmpTopTable OBJECT-TYPE
   SYNTAX     SEQUENCE OF LpEth100LtFrmCmpTopEntry
   ACCESS     not-accessible
   STATUS     mandatory
   DESCRIPTION
     "This group contains the operational data for the LanTest component 
      and its subcomponents."
::= { lpEth100LtFrmCmp 10 }

lpEth100LtFrmCmpTopEntry OBJECT-TYPE
   SYNTAX     LpEth100LtFrmCmpTopEntry
   ACCESS     not-accessible
   STATUS     mandatory
   DESCRIPTION
     "An entry in the lpEth100LtFrmCmpTopTable."
   INDEX {
      lpIndex,
      lpEth100Index,
      lpEth100LtIndex,
      lpEth100LtFrmCmpIndex }
::= { lpEth100LtFrmCmpTopTable 1 }

LpEth100LtFrmCmpTopEntry ::= SEQUENCE {
   lpEth100LtFrmCmpTData
      AsciiString }

lpEth100LtFrmCmpTData OBJECT-TYPE
   SYNTAX     AsciiString (SIZE (0..255))
   ACCESS     read-write
   STATUS     mandatory
   DESCRIPTION
     "This attribute is used to display and set attributes."
::= { lpEth100LtFrmCmpTopEntry 1 }


-- This component receives its input from FrameBuild and places it 
-- upon the hardware which sends it to the appropriate emulator.

lpEth100LtFrmCpy OBJECT IDENTIFIER ::= { lpEth100Lt 3 }



lpEth100LtFrmCpyRowStatusTable OBJECT-TYPE
   SYNTAX     SEQUENCE OF LpEth100LtFrmCpyRowStatusEntry
   ACCESS     not-accessible
   STATUS     mandatory
   DESCRIPTION
     "This entry controls the addition and deletion of 
      lpEth100LtFrmCpy components."
::= { lpEth100LtFrmCpy 1 }

lpEth100LtFrmCpyRowStatusEntry OBJECT-TYPE
   SYNTAX     LpEth100LtFrmCpyRowStatusEntry
   ACCESS     not-accessible
   STATUS     mandatory
   DESCRIPTION
     "A single entry in the table represents a single 
      lpEth100LtFrmCpy component."
   INDEX {
      lpIndex,
      lpEth100Index,
      lpEth100LtIndex,
      lpEth100LtFrmCpyIndex }
::= { lpEth100LtFrmCpyRowStatusTable 1 }

LpEth100LtFrmCpyRowStatusEntry ::= SEQUENCE {
   lpEth100LtFrmCpyRowStatus
      RowStatus,
   lpEth100LtFrmCpyComponentName
      DisplayString,
   lpEth100LtFrmCpyStorageType
      StorageType,
   lpEth100LtFrmCpyIndex
      NonReplicated }

lpEth100LtFrmCpyRowStatus OBJECT-TYPE
   SYNTAX     RowStatus 
   ACCESS     read-only
   STATUS     mandatory
   DESCRIPTION
     "This variable is used as the basis for SNMP naming of
      lpEth100LtFrmCpy components.
      These components cannot be added nor deleted."
::= { lpEth100LtFrmCpyRowStatusEntry 1 }

lpEth100LtFrmCpyComponentName OBJECT-TYPE
   SYNTAX     DisplayString 
   ACCESS     read-only
   STATUS     mandatory
   DESCRIPTION
     "This variable provides the component's string name for
      use with the ASCII Console Interface"
::= { lpEth100LtFrmCpyRowStatusEntry 2 }

lpEth100LtFrmCpyStorageType OBJECT-TYPE
   SYNTAX     StorageType 
   ACCESS     read-only
   STATUS     mandatory
   DESCRIPTION
     "This variable represents the storage type value for the
      lpEth100LtFrmCpy tables."
::= { lpEth100LtFrmCpyRowStatusEntry 4 }

lpEth100LtFrmCpyIndex OBJECT-TYPE
   SYNTAX     NonReplicated 
   ACCESS     not-accessible
   STATUS     mandatory
   DESCRIPTION
     "This variable represents the index for the lpEth100LtFrmCpy tables."
::= { lpEth100LtFrmCpyRowStatusEntry 10 }

lpEth100LtFrmCpyTopTable OBJECT-TYPE
   SYNTAX     SEQUENCE OF LpEth100LtFrmCpyTopEntry
   ACCESS     not-accessible
   STATUS     mandatory
   DESCRIPTION
     "This group contains the operational data for the LanTest component 
      and its subcomponents."
::= { lpEth100LtFrmCpy 10 }

lpEth100LtFrmCpyTopEntry OBJECT-TYPE
   SYNTAX     LpEth100LtFrmCpyTopEntry
   ACCESS     not-accessible
   STATUS     mandatory
   DESCRIPTION
     "An entry in the lpEth100LtFrmCpyTopTable."
   INDEX {
      lpIndex,
      lpEth100Index,
      lpEth100LtIndex,
      lpEth100LtFrmCpyIndex }
::= { lpEth100LtFrmCpyTopTable 1 }

LpEth100LtFrmCpyTopEntry ::= SEQUENCE {
   lpEth100LtFrmCpyTData
      AsciiString }

lpEth100LtFrmCpyTData OBJECT-TYPE
   SYNTAX     AsciiString (SIZE (0..255))
   ACCESS     read-write
   STATUS     mandatory
   DESCRIPTION
     "This attribute is used to display and set attributes."
::= { lpEth100LtFrmCpyTopEntry 1 }


-- This component controls the emulator and hardware to ensure 
-- frames output from each will match in FrameCompare.

lpEth100LtPrtCfg OBJECT IDENTIFIER ::= { lpEth100Lt 4 }



lpEth100LtPrtCfgRowStatusTable OBJECT-TYPE
   SYNTAX     SEQUENCE OF LpEth100LtPrtCfgRowStatusEntry
   ACCESS     not-accessible
   STATUS     mandatory
   DESCRIPTION
     "This entry controls the addition and deletion of 
      lpEth100LtPrtCfg components."
::= { lpEth100LtPrtCfg 1 }

lpEth100LtPrtCfgRowStatusEntry OBJECT-TYPE
   SYNTAX     LpEth100LtPrtCfgRowStatusEntry
   ACCESS     not-accessible
   STATUS     mandatory
   DESCRIPTION
     "A single entry in the table represents a single 
      lpEth100LtPrtCfg component."
   INDEX {
      lpIndex,
      lpEth100Index,
      lpEth100LtIndex,
      lpEth100LtPrtCfgIndex }
::= { lpEth100LtPrtCfgRowStatusTable 1 }

LpEth100LtPrtCfgRowStatusEntry ::= SEQUENCE {
   lpEth100LtPrtCfgRowStatus
      RowStatus,
   lpEth100LtPrtCfgComponentName
      DisplayString,
   lpEth100LtPrtCfgStorageType
      StorageType,
   lpEth100LtPrtCfgIndex
      NonReplicated }

lpEth100LtPrtCfgRowStatus OBJECT-TYPE
   SYNTAX     RowStatus 
   ACCESS     read-only
   STATUS     mandatory
   DESCRIPTION
     "This variable is used as the basis for SNMP naming of
      lpEth100LtPrtCfg components.
      These components cannot be added nor deleted."
::= { lpEth100LtPrtCfgRowStatusEntry 1 }

lpEth100LtPrtCfgComponentName OBJECT-TYPE
   SYNTAX     DisplayString 
   ACCESS     read-only
   STATUS     mandatory
   DESCRIPTION
     "This variable provides the component's string name for
      use with the ASCII Console Interface"
::= { lpEth100LtPrtCfgRowStatusEntry 2 }

lpEth100LtPrtCfgStorageType OBJECT-TYPE
   SYNTAX     StorageType 
   ACCESS     read-only
   STATUS     mandatory
   DESCRIPTION
     "This variable represents the storage type value for the
      lpEth100LtPrtCfg tables."
::= { lpEth100LtPrtCfgRowStatusEntry 4 }

lpEth100LtPrtCfgIndex OBJECT-TYPE
   SYNTAX     NonReplicated 
   ACCESS     not-accessible
   STATUS     mandatory
   DESCRIPTION
     "This variable represents the index for the lpEth100LtPrtCfg tables."
::= { lpEth100LtPrtCfgRowStatusEntry 10 }

lpEth100LtPrtCfgTopTable OBJECT-TYPE
   SYNTAX     SEQUENCE OF LpEth100LtPrtCfgTopEntry
   ACCESS     not-accessible
   STATUS     mandatory
   DESCRIPTION
     "This group contains the operational data for the LanTest component 
      and its subcomponents."
::= { lpEth100LtPrtCfg 10 }

lpEth100LtPrtCfgTopEntry OBJECT-TYPE
   SYNTAX     LpEth100LtPrtCfgTopEntry
   ACCESS     not-accessible
   STATUS     mandatory
   DESCRIPTION
     "An entry in the lpEth100LtPrtCfgTopTable."
   INDEX {
      lpIndex,
      lpEth100Index,
      lpEth100LtIndex,
      lpEth100LtPrtCfgIndex }
::= { lpEth100LtPrtCfgTopTable 1 }

LpEth100LtPrtCfgTopEntry ::= SEQUENCE {
   lpEth100LtPrtCfgTData
      AsciiString }

lpEth100LtPrtCfgTData OBJECT-TYPE
   SYNTAX     AsciiString (SIZE (0..255))
   ACCESS     read-write
   STATUS     mandatory
   DESCRIPTION
     "This attribute is used to display and set attributes."
::= { lpEth100LtPrtCfgTopEntry 1 }


-- LanTest Framebuild
-- This component controls the building of all frames built and sent by 
-- the LanTest component. Each component under FrameBuild builds 
-- a portion of a packet or frame.

lpEth100LtFb OBJECT IDENTIFIER ::= { lpEth100Lt 5 }



lpEth100LtFbRowStatusTable OBJECT-TYPE
   SYNTAX     SEQUENCE OF LpEth100LtFbRowStatusEntry
   ACCESS     not-accessible
   STATUS     mandatory
   DESCRIPTION
     "This entry controls the addition and deletion of 
      lpEth100LtFb components."
::= { lpEth100LtFb 1 }

lpEth100LtFbRowStatusEntry OBJECT-TYPE
   SYNTAX     LpEth100LtFbRowStatusEntry
   ACCESS     not-accessible
   STATUS     mandatory
   DESCRIPTION
     "A single entry in the table represents a single 
      lpEth100LtFb component."
   INDEX {
      lpIndex,
      lpEth100Index,
      lpEth100LtIndex,
      lpEth100LtFbIndex }
::= { lpEth100LtFbRowStatusTable 1 }

LpEth100LtFbRowStatusEntry ::= SEQUENCE {
   lpEth100LtFbRowStatus
      RowStatus,
   lpEth100LtFbComponentName
      DisplayString,
   lpEth100LtFbStorageType
      StorageType,
   lpEth100LtFbIndex
      NonReplicated }

lpEth100LtFbRowStatus OBJECT-TYPE
   SYNTAX     RowStatus 
   ACCESS     read-only
   STATUS     mandatory
   DESCRIPTION
     "This variable is used as the basis for SNMP naming of
      lpEth100LtFb components.
      These components cannot be added nor deleted."
::= { lpEth100LtFbRowStatusEntry 1 }

lpEth100LtFbComponentName OBJECT-TYPE
   SYNTAX     DisplayString 
   ACCESS     read-only
   STATUS     mandatory
   DESCRIPTION
     "This variable provides the component's string name for
      use with the ASCII Console Interface"
::= { lpEth100LtFbRowStatusEntry 2 }

lpEth100LtFbStorageType OBJECT-TYPE
   SYNTAX     StorageType 
   ACCESS     read-only
   STATUS     mandatory
   DESCRIPTION
     "This variable represents the storage type value for the
      lpEth100LtFb tables."
::= { lpEth100LtFbRowStatusEntry 4 }

lpEth100LtFbIndex OBJECT-TYPE
   SYNTAX     NonReplicated 
   ACCESS     not-accessible
   STATUS     mandatory
   DESCRIPTION
     "This variable represents the index for the lpEth100LtFb tables."
::= { lpEth100LtFbRowStatusEntry 10 }

lpEth100LtFbTopTable OBJECT-TYPE
   SYNTAX     SEQUENCE OF LpEth100LtFbTopEntry
   ACCESS     not-accessible
   STATUS     mandatory
   DESCRIPTION
     "This group contains the operational data for the LanTest component 
      and its subcomponents."
::= { lpEth100LtFb 20 }

lpEth100LtFbTopEntry OBJECT-TYPE
   SYNTAX     LpEth100LtFbTopEntry
   ACCESS     not-accessible
   STATUS     mandatory
   DESCRIPTION
     "An entry in the lpEth100LtFbTopTable."
   INDEX {
      lpIndex,
      lpEth100Index,
      lpEth100LtIndex,
      lpEth100LtFbIndex }
::= { lpEth100LtFbTopTable 1 }

LpEth100LtFbTopEntry ::= SEQUENCE {
   lpEth100LtFbTData
      AsciiString }

lpEth100LtFbTData OBJECT-TYPE
   SYNTAX     AsciiString (SIZE (0..255))
   ACCESS     read-write
   STATUS     mandatory
   DESCRIPTION
     "This attribute is used to display and set attributes."
::= { lpEth100LtFbTopEntry 1 }


-- LanTest TransmitInfo
-- This component builds a transmit header which is attached to all 
-- frames transmitted on LAN interfaces.

lpEth100LtFbTxInfo OBJECT IDENTIFIER ::= { lpEth100LtFb 2 }



lpEth100LtFbTxInfoRowStatusTable OBJECT-TYPE
   SYNTAX     SEQUENCE OF LpEth100LtFbTxInfoRowStatusEntry
   ACCESS     not-accessible
   STATUS     mandatory
   DESCRIPTION
     "This entry controls the addition and deletion of 
      lpEth100LtFbTxInfo components."
::= { lpEth100LtFbTxInfo 1 }

lpEth100LtFbTxInfoRowStatusEntry OBJECT-TYPE
   SYNTAX     LpEth100LtFbTxInfoRowStatusEntry
   ACCESS     not-accessible
   STATUS     mandatory
   DESCRIPTION
     "A single entry in the table represents a single 
      lpEth100LtFbTxInfo component."
   INDEX {
      lpIndex,
      lpEth100Index,
      lpEth100LtIndex,
      lpEth100LtFbIndex,
      lpEth100LtFbTxInfoIndex }
::= { lpEth100LtFbTxInfoRowStatusTable 1 }

LpEth100LtFbTxInfoRowStatusEntry ::= SEQUENCE {
   lpEth100LtFbTxInfoRowStatus
      RowStatus,
   lpEth100LtFbTxInfoComponentName
      DisplayString,
   lpEth100LtFbTxInfoStorageType
      StorageType,
   lpEth100LtFbTxInfoIndex
      NonReplicated }

lpEth100LtFbTxInfoRowStatus OBJECT-TYPE
   SYNTAX     RowStatus 
   ACCESS     read-only
   STATUS     mandatory
   DESCRIPTION
     "This variable is used as the basis for SNMP naming of
      lpEth100LtFbTxInfo components.
      These components cannot be added nor deleted."
::= { lpEth100LtFbTxInfoRowStatusEntry 1 }

lpEth100LtFbTxInfoComponentName OBJECT-TYPE
   SYNTAX     DisplayString 
   ACCESS     read-only
   STATUS     mandatory
   DESCRIPTION
     "This variable provides the component's string name for
      use with the ASCII Console Interface"
::= { lpEth100LtFbTxInfoRowStatusEntry 2 }

lpEth100LtFbTxInfoStorageType OBJECT-TYPE
   SYNTAX     StorageType 
   ACCESS     read-only
   STATUS     mandatory
   DESCRIPTION
     "This variable represents the storage type value for the
      lpEth100LtFbTxInfo tables."
::= { lpEth100LtFbTxInfoRowStatusEntry 4 }

lpEth100LtFbTxInfoIndex OBJECT-TYPE
   SYNTAX     NonReplicated 
   ACCESS     not-accessible
   STATUS     mandatory
   DESCRIPTION
     "This variable represents the index for the lpEth100LtFbTxInfo tables."
::= { lpEth100LtFbTxInfoRowStatusEntry 10 }

lpEth100LtFbTxInfoTopTable OBJECT-TYPE
   SYNTAX     SEQUENCE OF LpEth100LtFbTxInfoTopEntry
   ACCESS     not-accessible
   STATUS     mandatory
   DESCRIPTION
     "This group contains the operational data for the LanTest component 
      and its subcomponents."
::= { lpEth100LtFbTxInfo 10 }

lpEth100LtFbTxInfoTopEntry OBJECT-TYPE
   SYNTAX     LpEth100LtFbTxInfoTopEntry
   ACCESS     not-accessible
   STATUS     mandatory
   DESCRIPTION
     "An entry in the lpEth100LtFbTxInfoTopTable."
   INDEX {
      lpIndex,
      lpEth100Index,
      lpEth100LtIndex,
      lpEth100LtFbIndex,
      lpEth100LtFbTxInfoIndex }
::= { lpEth100LtFbTxInfoTopTable 1 }

LpEth100LtFbTxInfoTopEntry ::= SEQUENCE {
   lpEth100LtFbTxInfoTData
      AsciiString }

lpEth100LtFbTxInfoTData OBJECT-TYPE
   SYNTAX     AsciiString (SIZE (0..255))
   ACCESS     read-write
   STATUS     mandatory
   DESCRIPTION
     "This attribute is used to display and set attributes."
::= { lpEth100LtFbTxInfoTopEntry 1 }


-- LanTest FddiMac
-- This component builds an FDDI MAC header which is attached to 
-- all FDDI frames.

lpEth100LtFbFddiMac OBJECT IDENTIFIER ::= { lpEth100LtFb 3 }



lpEth100LtFbFddiMacRowStatusTable OBJECT-TYPE
   SYNTAX     SEQUENCE OF LpEth100LtFbFddiMacRowStatusEntry
   ACCESS     not-accessible
   STATUS     mandatory
   DESCRIPTION
     "This entry controls the addition and deletion of 
      lpEth100LtFbFddiMac components."
::= { lpEth100LtFbFddiMac 1 }

lpEth100LtFbFddiMacRowStatusEntry OBJECT-TYPE
   SYNTAX     LpEth100LtFbFddiMacRowStatusEntry
   ACCESS     not-accessible
   STATUS     mandatory
   DESCRIPTION
     "A single entry in the table represents a single 
      lpEth100LtFbFddiMac component."
   INDEX {
      lpIndex,
      lpEth100Index,
      lpEth100LtIndex,
      lpEth100LtFbIndex,
      lpEth100LtFbFddiMacIndex }
::= { lpEth100LtFbFddiMacRowStatusTable 1 }

LpEth100LtFbFddiMacRowStatusEntry ::= SEQUENCE {
   lpEth100LtFbFddiMacRowStatus
      RowStatus,
   lpEth100LtFbFddiMacComponentName
      DisplayString,
   lpEth100LtFbFddiMacStorageType
      StorageType,
   lpEth100LtFbFddiMacIndex
      NonReplicated }

lpEth100LtFbFddiMacRowStatus OBJECT-TYPE
   SYNTAX     RowStatus 
   ACCESS     read-only
   STATUS     mandatory
   DESCRIPTION
     "This variable is used as the basis for SNMP naming of
      lpEth100LtFbFddiMac components.
      These components cannot be added nor deleted."
::= { lpEth100LtFbFddiMacRowStatusEntry 1 }

lpEth100LtFbFddiMacComponentName OBJECT-TYPE
   SYNTAX     DisplayString 
   ACCESS     read-only
   STATUS     mandatory
   DESCRIPTION
     "This variable provides the component's string name for
      use with the ASCII Console Interface"
::= { lpEth100LtFbFddiMacRowStatusEntry 2 }

lpEth100LtFbFddiMacStorageType OBJECT-TYPE
   SYNTAX     StorageType 
   ACCESS     read-only
   STATUS     mandatory
   DESCRIPTION
     "This variable represents the storage type value for the
      lpEth100LtFbFddiMac tables."
::= { lpEth100LtFbFddiMacRowStatusEntry 4 }

lpEth100LtFbFddiMacIndex OBJECT-TYPE
   SYNTAX     NonReplicated 
   ACCESS     not-accessible
   STATUS     mandatory
   DESCRIPTION
     "This variable represents the index for the lpEth100LtFbFddiMac tables."
::= { lpEth100LtFbFddiMacRowStatusEntry 10 }

lpEth100LtFbFddiMacTopTable OBJECT-TYPE
   SYNTAX     SEQUENCE OF LpEth100LtFbFddiMacTopEntry
   ACCESS     not-accessible
   STATUS     mandatory
   DESCRIPTION
     "This group contains the operational data for the LanTest component 
      and its subcomponents."
::= { lpEth100LtFbFddiMac 10 }

lpEth100LtFbFddiMacTopEntry OBJECT-TYPE
   SYNTAX     LpEth100LtFbFddiMacTopEntry
   ACCESS     not-accessible
   STATUS     mandatory
   DESCRIPTION
     "An entry in the lpEth100LtFbFddiMacTopTable."
   INDEX {
      lpIndex,
      lpEth100Index,
      lpEth100LtIndex,
      lpEth100LtFbIndex,
      lpEth100LtFbFddiMacIndex }
::= { lpEth100LtFbFddiMacTopTable 1 }

LpEth100LtFbFddiMacTopEntry ::= SEQUENCE {
   lpEth100LtFbFddiMacTData
      AsciiString }

lpEth100LtFbFddiMacTData OBJECT-TYPE
   SYNTAX     AsciiString (SIZE (0..255))
   ACCESS     read-write
   STATUS     mandatory
   DESCRIPTION
     "This attribute is used to display and set attributes."
::= { lpEth100LtFbFddiMacTopEntry 1 }


-- LanTest EthernetMac
-- This component builds an Ethernet MAC header which is attached 
-- to all Ethernet frames.

lpEth100LtFbMacEnet OBJECT IDENTIFIER ::= { lpEth100LtFb 4 }



lpEth100LtFbMacEnetRowStatusTable OBJECT-TYPE
   SYNTAX     SEQUENCE OF LpEth100LtFbMacEnetRowStatusEntry
   ACCESS     not-accessible
   STATUS     mandatory
   DESCRIPTION
     "This entry controls the addition and deletion of 
      lpEth100LtFbMacEnet components."
::= { lpEth100LtFbMacEnet 1 }

lpEth100LtFbMacEnetRowStatusEntry OBJECT-TYPE
   SYNTAX     LpEth100LtFbMacEnetRowStatusEntry
   ACCESS     not-accessible
   STATUS     mandatory
   DESCRIPTION
     "A single entry in the table represents a single 
      lpEth100LtFbMacEnet component."
   INDEX {
      lpIndex,
      lpEth100Index,
      lpEth100LtIndex,
      lpEth100LtFbIndex,
      lpEth100LtFbMacEnetIndex }
::= { lpEth100LtFbMacEnetRowStatusTable 1 }

LpEth100LtFbMacEnetRowStatusEntry ::= SEQUENCE {
   lpEth100LtFbMacEnetRowStatus
      RowStatus,
   lpEth100LtFbMacEnetComponentName
      DisplayString,
   lpEth100LtFbMacEnetStorageType
      StorageType,
   lpEth100LtFbMacEnetIndex
      NonReplicated }

lpEth100LtFbMacEnetRowStatus OBJECT-TYPE
   SYNTAX     RowStatus 
   ACCESS     read-only
   STATUS     mandatory
   DESCRIPTION
     "This variable is used as the basis for SNMP naming of
      lpEth100LtFbMacEnet components.
      These components cannot be added nor deleted."
::= { lpEth100LtFbMacEnetRowStatusEntry 1 }

lpEth100LtFbMacEnetComponentName OBJECT-TYPE
   SYNTAX     DisplayString 
   ACCESS     read-only
   STATUS     mandatory
   DESCRIPTION
     "This variable provides the component's string name for
      use with the ASCII Console Interface"
::= { lpEth100LtFbMacEnetRowStatusEntry 2 }

lpEth100LtFbMacEnetStorageType OBJECT-TYPE
   SYNTAX     StorageType 
   ACCESS     read-only
   STATUS     mandatory
   DESCRIPTION
     "This variable represents the storage type value for the
      lpEth100LtFbMacEnet tables."
::= { lpEth100LtFbMacEnetRowStatusEntry 4 }

lpEth100LtFbMacEnetIndex OBJECT-TYPE
   SYNTAX     NonReplicated 
   ACCESS     not-accessible
   STATUS     mandatory
   DESCRIPTION
     "This variable represents the index for the lpEth100LtFbMacEnet tables."
::= { lpEth100LtFbMacEnetRowStatusEntry 10 }

lpEth100LtFbMacEnetTopTable OBJECT-TYPE
   SYNTAX     SEQUENCE OF LpEth100LtFbMacEnetTopEntry
   ACCESS     not-accessible
   STATUS     mandatory
   DESCRIPTION
     "This group contains the operational data for the LanTest component 
      and its subcomponents."
::= { lpEth100LtFbMacEnet 10 }

lpEth100LtFbMacEnetTopEntry OBJECT-TYPE
   SYNTAX     LpEth100LtFbMacEnetTopEntry
   ACCESS     not-accessible
   STATUS     mandatory
   DESCRIPTION
     "An entry in the lpEth100LtFbMacEnetTopTable."
   INDEX {
      lpIndex,
      lpEth100Index,
      lpEth100LtIndex,
      lpEth100LtFbIndex,
      lpEth100LtFbMacEnetIndex }
::= { lpEth100LtFbMacEnetTopTable 1 }

LpEth100LtFbMacEnetTopEntry ::= SEQUENCE {
   lpEth100LtFbMacEnetTData
      AsciiString }

lpEth100LtFbMacEnetTData OBJECT-TYPE
   SYNTAX     AsciiString (SIZE (0..255))
   ACCESS     read-write
   STATUS     mandatory
   DESCRIPTION
     "This attribute is used to display and set attributes."
::= { lpEth100LtFbMacEnetTopEntry 1 }


-- LanTest TokenRingMac
-- This component builds a Token Ring MAC header which is attached 
-- to all Token Ring frames.

lpEth100LtFbMacTr OBJECT IDENTIFIER ::= { lpEth100LtFb 5 }



lpEth100LtFbMacTrRowStatusTable OBJECT-TYPE
   SYNTAX     SEQUENCE OF LpEth100LtFbMacTrRowStatusEntry
   ACCESS     not-accessible
   STATUS     mandatory
   DESCRIPTION
     "This entry controls the addition and deletion of 
      lpEth100LtFbMacTr components."
::= { lpEth100LtFbMacTr 1 }

lpEth100LtFbMacTrRowStatusEntry OBJECT-TYPE
   SYNTAX     LpEth100LtFbMacTrRowStatusEntry
   ACCESS     not-accessible
   STATUS     mandatory
   DESCRIPTION
     "A single entry in the table represents a single 
      lpEth100LtFbMacTr component."
   INDEX {
      lpIndex,
      lpEth100Index,
      lpEth100LtIndex,
      lpEth100LtFbIndex,
      lpEth100LtFbMacTrIndex }
::= { lpEth100LtFbMacTrRowStatusTable 1 }

LpEth100LtFbMacTrRowStatusEntry ::= SEQUENCE {
   lpEth100LtFbMacTrRowStatus
      RowStatus,
   lpEth100LtFbMacTrComponentName
      DisplayString,
   lpEth100LtFbMacTrStorageType
      StorageType,
   lpEth100LtFbMacTrIndex
      NonReplicated }

lpEth100LtFbMacTrRowStatus OBJECT-TYPE
   SYNTAX     RowStatus 
   ACCESS     read-only
   STATUS     mandatory
   DESCRIPTION
     "This variable is used as the basis for SNMP naming of
      lpEth100LtFbMacTr components.
      These components cannot be added nor deleted."
::= { lpEth100LtFbMacTrRowStatusEntry 1 }

lpEth100LtFbMacTrComponentName OBJECT-TYPE
   SYNTAX     DisplayString 
   ACCESS     read-only
   STATUS     mandatory
   DESCRIPTION
     "This variable provides the component's string name for
      use with the ASCII Console Interface"
::= { lpEth100LtFbMacTrRowStatusEntry 2 }

lpEth100LtFbMacTrStorageType OBJECT-TYPE
   SYNTAX     StorageType 
   ACCESS     read-only
   STATUS     mandatory
   DESCRIPTION
     "This variable represents the storage type value for the
      lpEth100LtFbMacTr tables."
::= { lpEth100LtFbMacTrRowStatusEntry 4 }

lpEth100LtFbMacTrIndex OBJECT-TYPE
   SYNTAX     NonReplicated 
   ACCESS     not-accessible
   STATUS     mandatory
   DESCRIPTION
     "This variable represents the index for the lpEth100LtFbMacTr tables."
::= { lpEth100LtFbMacTrRowStatusEntry 10 }

lpEth100LtFbMacTrTopTable OBJECT-TYPE
   SYNTAX     SEQUENCE OF LpEth100LtFbMacTrTopEntry
   ACCESS     not-accessible
   STATUS     mandatory
   DESCRIPTION
     "This group contains the operational data for the LanTest component 
      and its subcomponents."
::= { lpEth100LtFbMacTr 10 }

lpEth100LtFbMacTrTopEntry OBJECT-TYPE
   SYNTAX     LpEth100LtFbMacTrTopEntry
   ACCESS     not-accessible
   STATUS     mandatory
   DESCRIPTION
     "An entry in the lpEth100LtFbMacTrTopTable."
   INDEX {
      lpIndex,
      lpEth100Index,
      lpEth100LtIndex,
      lpEth100LtFbIndex,
      lpEth100LtFbMacTrIndex }
::= { lpEth100LtFbMacTrTopTable 1 }

LpEth100LtFbMacTrTopEntry ::= SEQUENCE {
   lpEth100LtFbMacTrTData
      AsciiString }

lpEth100LtFbMacTrTData OBJECT-TYPE
   SYNTAX     AsciiString (SIZE (0..255))
   ACCESS     read-write
   STATUS     mandatory
   DESCRIPTION
     "This attribute is used to display and set attributes."
::= { lpEth100LtFbMacTrTopEntry 1 }


-- This component adds a data field to frame.

lpEth100LtFbData OBJECT IDENTIFIER ::= { lpEth100LtFb 6 }



lpEth100LtFbDataRowStatusTable OBJECT-TYPE
   SYNTAX     SEQUENCE OF LpEth100LtFbDataRowStatusEntry
   ACCESS     not-accessible
   STATUS     mandatory
   DESCRIPTION
     "This entry controls the addition and deletion of 
      lpEth100LtFbData components."
::= { lpEth100LtFbData 1 }

lpEth100LtFbDataRowStatusEntry OBJECT-TYPE
   SYNTAX     LpEth100LtFbDataRowStatusEntry
   ACCESS     not-accessible
   STATUS     mandatory
   DESCRIPTION
     "A single entry in the table represents a single 
      lpEth100LtFbData component."
   INDEX {
      lpIndex,
      lpEth100Index,
      lpEth100LtIndex,
      lpEth100LtFbIndex,
      lpEth100LtFbDataIndex }
::= { lpEth100LtFbDataRowStatusTable 1 }

LpEth100LtFbDataRowStatusEntry ::= SEQUENCE {
   lpEth100LtFbDataRowStatus
      RowStatus,
   lpEth100LtFbDataComponentName
      DisplayString,
   lpEth100LtFbDataStorageType
      StorageType,
   lpEth100LtFbDataIndex
      NonReplicated }

lpEth100LtFbDataRowStatus OBJECT-TYPE
   SYNTAX     RowStatus 
   ACCESS     read-only
   STATUS     mandatory
   DESCRIPTION
     "This variable is used as the basis for SNMP naming of
      lpEth100LtFbData components.
      These components cannot be added nor deleted."
::= { lpEth100LtFbDataRowStatusEntry 1 }

lpEth100LtFbDataComponentName OBJECT-TYPE
   SYNTAX     DisplayString 
   ACCESS     read-only
   STATUS     mandatory
   DESCRIPTION
     "This variable provides the component's string name for
      use with the ASCII Console Interface"
::= { lpEth100LtFbDataRowStatusEntry 2 }

lpEth100LtFbDataStorageType OBJECT-TYPE
   SYNTAX     StorageType 
   ACCESS     read-only
   STATUS     mandatory
   DESCRIPTION
     "This variable represents the storage type value for the
      lpEth100LtFbData tables."
::= { lpEth100LtFbDataRowStatusEntry 4 }

lpEth100LtFbDataIndex OBJECT-TYPE
   SYNTAX     NonReplicated 
   ACCESS     not-accessible
   STATUS     mandatory
   DESCRIPTION
     "This variable represents the index for the lpEth100LtFbData tables."
::= { lpEth100LtFbDataRowStatusEntry 10 }

lpEth100LtFbDataTopTable OBJECT-TYPE
   SYNTAX     SEQUENCE OF LpEth100LtFbDataTopEntry
   ACCESS     not-accessible
   STATUS     mandatory
   DESCRIPTION
     "This group contains the operational data for the LanTest component 
      and its subcomponents."
::= { lpEth100LtFbData 10 }

lpEth100LtFbDataTopEntry OBJECT-TYPE
   SYNTAX     LpEth100LtFbDataTopEntry
   ACCESS     not-accessible
   STATUS     mandatory
   DESCRIPTION
     "An entry in the lpEth100LtFbDataTopTable."
   INDEX {
      lpIndex,
      lpEth100Index,
      lpEth100LtIndex,
      lpEth100LtFbIndex,
      lpEth100LtFbDataIndex }
::= { lpEth100LtFbDataTopTable 1 }

LpEth100LtFbDataTopEntry ::= SEQUENCE {
   lpEth100LtFbDataTData
      AsciiString }

lpEth100LtFbDataTData OBJECT-TYPE
   SYNTAX     AsciiString (SIZE (0..255))
   ACCESS     read-write
   STATUS     mandatory
   DESCRIPTION
     "This attribute is used to display and set attributes."
::= { lpEth100LtFbDataTopEntry 1 }


-- LanTest IpHeader
-- This component adds an IP header to a frame or packet.

lpEth100LtFbIpH OBJECT IDENTIFIER ::= { lpEth100LtFb 7 }



lpEth100LtFbIpHRowStatusTable OBJECT-TYPE
   SYNTAX     SEQUENCE OF LpEth100LtFbIpHRowStatusEntry
   ACCESS     not-accessible
   STATUS     mandatory
   DESCRIPTION
     "This entry controls the addition and deletion of 
      lpEth100LtFbIpH components."
::= { lpEth100LtFbIpH 1 }

lpEth100LtFbIpHRowStatusEntry OBJECT-TYPE
   SYNTAX     LpEth100LtFbIpHRowStatusEntry
   ACCESS     not-accessible
   STATUS     mandatory
   DESCRIPTION
     "A single entry in the table represents a single 
      lpEth100LtFbIpH component."
   INDEX {
      lpIndex,
      lpEth100Index,
      lpEth100LtIndex,
      lpEth100LtFbIndex,
      lpEth100LtFbIpHIndex }
::= { lpEth100LtFbIpHRowStatusTable 1 }

LpEth100LtFbIpHRowStatusEntry ::= SEQUENCE {
   lpEth100LtFbIpHRowStatus
      RowStatus,
   lpEth100LtFbIpHComponentName
      DisplayString,
   lpEth100LtFbIpHStorageType
      StorageType,
   lpEth100LtFbIpHIndex
      NonReplicated }

lpEth100LtFbIpHRowStatus OBJECT-TYPE
   SYNTAX     RowStatus 
   ACCESS     read-only
   STATUS     mandatory
   DESCRIPTION
     "This variable is used as the basis for SNMP naming of
      lpEth100LtFbIpH components.
      These components cannot be added nor deleted."
::= { lpEth100LtFbIpHRowStatusEntry 1 }

lpEth100LtFbIpHComponentName OBJECT-TYPE
   SYNTAX     DisplayString 
   ACCESS     read-only
   STATUS     mandatory
   DESCRIPTION
     "This variable provides the component's string name for
      use with the ASCII Console Interface"
::= { lpEth100LtFbIpHRowStatusEntry 2 }

lpEth100LtFbIpHStorageType OBJECT-TYPE
   SYNTAX     StorageType 
   ACCESS     read-only
   STATUS     mandatory
   DESCRIPTION
     "This variable represents the storage type value for the
      lpEth100LtFbIpH tables."
::= { lpEth100LtFbIpHRowStatusEntry 4 }

lpEth100LtFbIpHIndex OBJECT-TYPE
   SYNTAX     NonReplicated 
   ACCESS     not-accessible
   STATUS     mandatory
   DESCRIPTION
     "This variable represents the index for the lpEth100LtFbIpH tables."
::= { lpEth100LtFbIpHRowStatusEntry 10 }

lpEth100LtFbIpHTopTable OBJECT-TYPE
   SYNTAX     SEQUENCE OF LpEth100LtFbIpHTopEntry
   ACCESS     not-accessible
   STATUS     mandatory
   DESCRIPTION
     "This group contains the operational data for the LanTest component 
      and its subcomponents."
::= { lpEth100LtFbIpH 10 }

lpEth100LtFbIpHTopEntry OBJECT-TYPE
   SYNTAX     LpEth100LtFbIpHTopEntry
   ACCESS     not-accessible
   STATUS     mandatory
   DESCRIPTION
     "An entry in the lpEth100LtFbIpHTopTable."
   INDEX {
      lpIndex,
      lpEth100Index,
      lpEth100LtIndex,
      lpEth100LtFbIndex,
      lpEth100LtFbIpHIndex }
::= { lpEth100LtFbIpHTopTable 1 }

LpEth100LtFbIpHTopEntry ::= SEQUENCE {
   lpEth100LtFbIpHTData
      AsciiString }

lpEth100LtFbIpHTData OBJECT-TYPE
   SYNTAX     AsciiString (SIZE (0..255))
   ACCESS     read-write
   STATUS     mandatory
   DESCRIPTION
     "This attribute is used to display and set attributes."
::= { lpEth100LtFbIpHTopEntry 1 }


-- LanTest LlcHeader
-- This component adds an LLC 802.2 or Ethernet header to a frame 
-- or packet.

lpEth100LtFbLlch OBJECT IDENTIFIER ::= { lpEth100LtFb 8 }



lpEth100LtFbLlchRowStatusTable OBJECT-TYPE
   SYNTAX     SEQUENCE OF LpEth100LtFbLlchRowStatusEntry
   ACCESS     not-accessible
   STATUS     mandatory
   DESCRIPTION
     "This entry controls the addition and deletion of 
      lpEth100LtFbLlch components."
::= { lpEth100LtFbLlch 1 }

lpEth100LtFbLlchRowStatusEntry OBJECT-TYPE
   SYNTAX     LpEth100LtFbLlchRowStatusEntry
   ACCESS     not-accessible
   STATUS     mandatory
   DESCRIPTION
     "A single entry in the table represents a single 
      lpEth100LtFbLlch component."
   INDEX {
      lpIndex,
      lpEth100Index,
      lpEth100LtIndex,
      lpEth100LtFbIndex,
      lpEth100LtFbLlchIndex }
::= { lpEth100LtFbLlchRowStatusTable 1 }

LpEth100LtFbLlchRowStatusEntry ::= SEQUENCE {
   lpEth100LtFbLlchRowStatus
      RowStatus,
   lpEth100LtFbLlchComponentName
      DisplayString,
   lpEth100LtFbLlchStorageType
      StorageType,
   lpEth100LtFbLlchIndex
      NonReplicated }

lpEth100LtFbLlchRowStatus OBJECT-TYPE
   SYNTAX     RowStatus 
   ACCESS     read-only
   STATUS     mandatory
   DESCRIPTION
     "This variable is used as the basis for SNMP naming of
      lpEth100LtFbLlch components.
      These components cannot be added nor deleted."
::= { lpEth100LtFbLlchRowStatusEntry 1 }

lpEth100LtFbLlchComponentName OBJECT-TYPE
   SYNTAX     DisplayString 
   ACCESS     read-only
   STATUS     mandatory
   DESCRIPTION
     "This variable provides the component's string name for
      use with the ASCII Console Interface"
::= { lpEth100LtFbLlchRowStatusEntry 2 }

lpEth100LtFbLlchStorageType OBJECT-TYPE
   SYNTAX     StorageType 
   ACCESS     read-only
   STATUS     mandatory
   DESCRIPTION
     "This variable represents the storage type value for the
      lpEth100LtFbLlch tables."
::= { lpEth100LtFbLlchRowStatusEntry 4 }

lpEth100LtFbLlchIndex OBJECT-TYPE
   SYNTAX     NonReplicated 
   ACCESS     not-accessible
   STATUS     mandatory
   DESCRIPTION
     "This variable represents the index for the lpEth100LtFbLlch tables."
::= { lpEth100LtFbLlchRowStatusEntry 10 }

lpEth100LtFbLlchTopTable OBJECT-TYPE
   SYNTAX     SEQUENCE OF LpEth100LtFbLlchTopEntry
   ACCESS     not-accessible
   STATUS     mandatory
   DESCRIPTION
     "This group contains the operational data for the LanTest component 
      and its subcomponents."
::= { lpEth100LtFbLlch 10 }

lpEth100LtFbLlchTopEntry OBJECT-TYPE
   SYNTAX     LpEth100LtFbLlchTopEntry
   ACCESS     not-accessible
   STATUS     mandatory
   DESCRIPTION
     "An entry in the lpEth100LtFbLlchTopTable."
   INDEX {
      lpIndex,
      lpEth100Index,
      lpEth100LtIndex,
      lpEth100LtFbIndex,
      lpEth100LtFbLlchIndex }
::= { lpEth100LtFbLlchTopTable 1 }

LpEth100LtFbLlchTopEntry ::= SEQUENCE {
   lpEth100LtFbLlchTData
      AsciiString }

lpEth100LtFbLlchTData OBJECT-TYPE
   SYNTAX     AsciiString (SIZE (0..255))
   ACCESS     read-write
   STATUS     mandatory
   DESCRIPTION
     "This attribute is used to display and set attributes."
::= { lpEth100LtFbLlchTopEntry 1 }


-- This component adds an AppleTalk header to a frame or packet.

lpEth100LtFbAppleH OBJECT IDENTIFIER ::= { lpEth100LtFb 9 }



lpEth100LtFbAppleHRowStatusTable OBJECT-TYPE
   SYNTAX     SEQUENCE OF LpEth100LtFbAppleHRowStatusEntry
   ACCESS     not-accessible
   STATUS     mandatory
   DESCRIPTION
     "This entry controls the addition and deletion of 
      lpEth100LtFbAppleH components."
::= { lpEth100LtFbAppleH 1 }

lpEth100LtFbAppleHRowStatusEntry OBJECT-TYPE
   SYNTAX     LpEth100LtFbAppleHRowStatusEntry
   ACCESS     not-accessible
   STATUS     mandatory
   DESCRIPTION
     "A single entry in the table represents a single 
      lpEth100LtFbAppleH component."
   INDEX {
      lpIndex,
      lpEth100Index,
      lpEth100LtIndex,
      lpEth100LtFbIndex,
      lpEth100LtFbAppleHIndex }
::= { lpEth100LtFbAppleHRowStatusTable 1 }

LpEth100LtFbAppleHRowStatusEntry ::= SEQUENCE {
   lpEth100LtFbAppleHRowStatus
      RowStatus,
   lpEth100LtFbAppleHComponentName
      DisplayString,
   lpEth100LtFbAppleHStorageType
      StorageType,
   lpEth100LtFbAppleHIndex
      NonReplicated }

lpEth100LtFbAppleHRowStatus OBJECT-TYPE
   SYNTAX     RowStatus 
   ACCESS     read-only
   STATUS     mandatory
   DESCRIPTION
     "This variable is used as the basis for SNMP naming of
      lpEth100LtFbAppleH components.
      These components cannot be added nor deleted."
::= { lpEth100LtFbAppleHRowStatusEntry 1 }

lpEth100LtFbAppleHComponentName OBJECT-TYPE
   SYNTAX     DisplayString 
   ACCESS     read-only
   STATUS     mandatory
   DESCRIPTION
     "This variable provides the component's string name for
      use with the ASCII Console Interface"
::= { lpEth100LtFbAppleHRowStatusEntry 2 }

lpEth100LtFbAppleHStorageType OBJECT-TYPE
   SYNTAX     StorageType 
   ACCESS     read-only
   STATUS     mandatory
   DESCRIPTION
     "This variable represents the storage type value for the
      lpEth100LtFbAppleH tables."
::= { lpEth100LtFbAppleHRowStatusEntry 4 }

lpEth100LtFbAppleHIndex OBJECT-TYPE
   SYNTAX     NonReplicated 
   ACCESS     not-accessible
   STATUS     mandatory
   DESCRIPTION
     "This variable represents the index for the lpEth100LtFbAppleH tables."
::= { lpEth100LtFbAppleHRowStatusEntry 10 }

lpEth100LtFbAppleHTopTable OBJECT-TYPE
   SYNTAX     SEQUENCE OF LpEth100LtFbAppleHTopEntry
   ACCESS     not-accessible
   STATUS     mandatory
   DESCRIPTION
     "This group contains the operational data for the LanTest component 
      and its subcomponents."
::= { lpEth100LtFbAppleH 10 }

lpEth100LtFbAppleHTopEntry OBJECT-TYPE
   SYNTAX     LpEth100LtFbAppleHTopEntry
   ACCESS     not-accessible
   STATUS     mandatory
   DESCRIPTION
     "An entry in the lpEth100LtFbAppleHTopTable."
   INDEX {
      lpIndex,
      lpEth100Index,
      lpEth100LtIndex,
      lpEth100LtFbIndex,
      lpEth100LtFbAppleHIndex }
::= { lpEth100LtFbAppleHTopTable 1 }

LpEth100LtFbAppleHTopEntry ::= SEQUENCE {
   lpEth100LtFbAppleHTData
      AsciiString }

lpEth100LtFbAppleHTData OBJECT-TYPE
   SYNTAX     AsciiString (SIZE (0..255))
   ACCESS     read-write
   STATUS     mandatory
   DESCRIPTION
     "This attribute is used to display and set attributes."
::= { lpEth100LtFbAppleHTopEntry 1 }


-- This component adds an IPX header to a frame or packet.

lpEth100LtFbIpxH OBJECT IDENTIFIER ::= { lpEth100LtFb 10 }



lpEth100LtFbIpxHRowStatusTable OBJECT-TYPE
   SYNTAX     SEQUENCE OF LpEth100LtFbIpxHRowStatusEntry
   ACCESS     not-accessible
   STATUS     mandatory
   DESCRIPTION
     "This entry controls the addition and deletion of 
      lpEth100LtFbIpxH components."
::= { lpEth100LtFbIpxH 1 }

lpEth100LtFbIpxHRowStatusEntry OBJECT-TYPE
   SYNTAX     LpEth100LtFbIpxHRowStatusEntry
   ACCESS     not-accessible
   STATUS     mandatory
   DESCRIPTION
     "A single entry in the table represents a single 
      lpEth100LtFbIpxH component."
   INDEX {
      lpIndex,
      lpEth100Index,
      lpEth100LtIndex,
      lpEth100LtFbIndex,
      lpEth100LtFbIpxHIndex }
::= { lpEth100LtFbIpxHRowStatusTable 1 }

LpEth100LtFbIpxHRowStatusEntry ::= SEQUENCE {
   lpEth100LtFbIpxHRowStatus
      RowStatus,
   lpEth100LtFbIpxHComponentName
      DisplayString,
   lpEth100LtFbIpxHStorageType
      StorageType,
   lpEth100LtFbIpxHIndex
      NonReplicated }

lpEth100LtFbIpxHRowStatus OBJECT-TYPE
   SYNTAX     RowStatus 
   ACCESS     read-only
   STATUS     mandatory
   DESCRIPTION
     "This variable is used as the basis for SNMP naming of
      lpEth100LtFbIpxH components.
      These components cannot be added nor deleted."
::= { lpEth100LtFbIpxHRowStatusEntry 1 }

lpEth100LtFbIpxHComponentName OBJECT-TYPE
   SYNTAX     DisplayString 
   ACCESS     read-only
   STATUS     mandatory
   DESCRIPTION
     "This variable provides the component's string name for
      use with the ASCII Console Interface"
::= { lpEth100LtFbIpxHRowStatusEntry 2 }

lpEth100LtFbIpxHStorageType OBJECT-TYPE
   SYNTAX     StorageType 
   ACCESS     read-only
   STATUS     mandatory
   DESCRIPTION
     "This variable represents the storage type value for the
      lpEth100LtFbIpxH tables."
::= { lpEth100LtFbIpxHRowStatusEntry 4 }

lpEth100LtFbIpxHIndex OBJECT-TYPE
   SYNTAX     NonReplicated 
   ACCESS     not-accessible
   STATUS     mandatory
   DESCRIPTION
     "This variable represents the index for the lpEth100LtFbIpxH tables."
::= { lpEth100LtFbIpxHRowStatusEntry 10 }

lpEth100LtFbIpxHTopTable OBJECT-TYPE
   SYNTAX     SEQUENCE OF LpEth100LtFbIpxHTopEntry
   ACCESS     not-accessible
   STATUS     mandatory
   DESCRIPTION
     "This group contains the operational data for the LanTest component 
      and its subcomponents."
::= { lpEth100LtFbIpxH 10 }

lpEth100LtFbIpxHTopEntry OBJECT-TYPE
   SYNTAX     LpEth100LtFbIpxHTopEntry
   ACCESS     not-accessible
   STATUS     mandatory
   DESCRIPTION
     "An entry in the lpEth100LtFbIpxHTopTable."
   INDEX {
      lpIndex,
      lpEth100Index,
      lpEth100LtIndex,
      lpEth100LtFbIndex,
      lpEth100LtFbIpxHIndex }
::= { lpEth100LtFbIpxHTopTable 1 }

LpEth100LtFbIpxHTopEntry ::= SEQUENCE {
   lpEth100LtFbIpxHTData
      AsciiString }

lpEth100LtFbIpxHTData OBJECT-TYPE
   SYNTAX     AsciiString (SIZE (0..255))
   ACCESS     read-write
   STATUS     mandatory
   DESCRIPTION
     "This attribute is used to display and set attributes."
::= { lpEth100LtFbIpxHTopEntry 1 }


-- LanTest Control
-- This component controls the overall testing by telling the 
-- FrameBuild component to start and check the FrameCompare 
-- component to see if the test is complete.

lpEth100LtCntl OBJECT IDENTIFIER ::= { lpEth100Lt 6 }



lpEth100LtCntlRowStatusTable OBJECT-TYPE
   SYNTAX     SEQUENCE OF LpEth100LtCntlRowStatusEntry
   ACCESS     not-accessible
   STATUS     mandatory
   DESCRIPTION
     "This entry controls the addition and deletion of 
      lpEth100LtCntl components."
::= { lpEth100LtCntl 1 }

lpEth100LtCntlRowStatusEntry OBJECT-TYPE
   SYNTAX     LpEth100LtCntlRowStatusEntry
   ACCESS     not-accessible
   STATUS     mandatory
   DESCRIPTION
     "A single entry in the table represents a single 
      lpEth100LtCntl component."
   INDEX {
      lpIndex,
      lpEth100Index,
      lpEth100LtIndex,
      lpEth100LtCntlIndex }
::= { lpEth100LtCntlRowStatusTable 1 }

LpEth100LtCntlRowStatusEntry ::= SEQUENCE {
   lpEth100LtCntlRowStatus
      RowStatus,
   lpEth100LtCntlComponentName
      DisplayString,
   lpEth100LtCntlStorageType
      StorageType,
   lpEth100LtCntlIndex
      NonReplicated }

lpEth100LtCntlRowStatus OBJECT-TYPE
   SYNTAX     RowStatus 
   ACCESS     read-only
   STATUS     mandatory
   DESCRIPTION
     "This variable is used as the basis for SNMP naming of
      lpEth100LtCntl components.
      These components cannot be added nor deleted."
::= { lpEth100LtCntlRowStatusEntry 1 }

lpEth100LtCntlComponentName OBJECT-TYPE
   SYNTAX     DisplayString 
   ACCESS     read-only
   STATUS     mandatory
   DESCRIPTION
     "This variable provides the component's string name for
      use with the ASCII Console Interface"
::= { lpEth100LtCntlRowStatusEntry 2 }

lpEth100LtCntlStorageType OBJECT-TYPE
   SYNTAX     StorageType 
   ACCESS     read-only
   STATUS     mandatory
   DESCRIPTION
     "This variable represents the storage type value for the
      lpEth100LtCntl tables."
::= { lpEth100LtCntlRowStatusEntry 4 }

lpEth100LtCntlIndex OBJECT-TYPE
   SYNTAX     NonReplicated 
   ACCESS     not-accessible
   STATUS     mandatory
   DESCRIPTION
     "This variable represents the index for the lpEth100LtCntl tables."
::= { lpEth100LtCntlRowStatusEntry 10 }

lpEth100LtCntlTopTable OBJECT-TYPE
   SYNTAX     SEQUENCE OF LpEth100LtCntlTopEntry
   ACCESS     not-accessible
   STATUS     mandatory
   DESCRIPTION
     "This group contains the operational data for the LanTest component 
      and its subcomponents."
::= { lpEth100LtCntl 10 }

lpEth100LtCntlTopEntry OBJECT-TYPE
   SYNTAX     LpEth100LtCntlTopEntry
   ACCESS     not-accessible
   STATUS     mandatory
   DESCRIPTION
     "An entry in the lpEth100LtCntlTopTable."
   INDEX {
      lpIndex,
      lpEth100Index,
      lpEth100LtIndex,
      lpEth100LtCntlIndex }
::= { lpEth100LtCntlTopTable 1 }

LpEth100LtCntlTopEntry ::= SEQUENCE {
   lpEth100LtCntlTData
      AsciiString }

lpEth100LtCntlTData OBJECT-TYPE
   SYNTAX     AsciiString (SIZE (0..255))
   ACCESS     read-write
   STATUS     mandatory
   DESCRIPTION
     "This attribute is used to display and set attributes."
::= { lpEth100LtCntlTopEntry 1 }


-- Lp/n Fddi/n Test, or
-- Lp/n Ethernet/n Test, or
-- Lp/n TokenRing/n Test, or
-- Lp/n IlsForwarder/n Test
-- The Test component is used to do StartUp port test for LAN cards.

lpEth100Test OBJECT IDENTIFIER ::= { lpEth100 3 }



lpEth100TestRowStatusTable OBJECT-TYPE
   SYNTAX     SEQUENCE OF LpEth100TestRowStatusEntry
   ACCESS     not-accessible
   STATUS     mandatory
   DESCRIPTION
     "This entry controls the addition and deletion of 
      lpEth100Test components."
::= { lpEth100Test 1 }

lpEth100TestRowStatusEntry OBJECT-TYPE
   SYNTAX     LpEth100TestRowStatusEntry
   ACCESS     not-accessible
   STATUS     mandatory
   DESCRIPTION
     "A single entry in the table represents a single 
      lpEth100Test component."
   INDEX {
      lpIndex,
      lpEth100Index,
      lpEth100TestIndex }
::= { lpEth100TestRowStatusTable 1 }

LpEth100TestRowStatusEntry ::= SEQUENCE {
   lpEth100TestRowStatus
      RowStatus,
   lpEth100TestComponentName
      DisplayString,
   lpEth100TestStorageType
      StorageType,
   lpEth100TestIndex
      NonReplicated }

lpEth100TestRowStatus OBJECT-TYPE
   SYNTAX     RowStatus 
   ACCESS     read-only
   STATUS     mandatory
   DESCRIPTION
     "This variable is used as the basis for SNMP naming of
      lpEth100Test components.
      These components cannot be added nor deleted."
::= { lpEth100TestRowStatusEntry 1 }

lpEth100TestComponentName OBJECT-TYPE
   SYNTAX     DisplayString 
   ACCESS     read-only
   STATUS     mandatory
   DESCRIPTION
     "This variable provides the component's string name for
      use with the ASCII Console Interface"
::= { lpEth100TestRowStatusEntry 2 }

lpEth100TestStorageType OBJECT-TYPE
   SYNTAX     StorageType 
   ACCESS     read-only
   STATUS     mandatory
   DESCRIPTION
     "This variable represents the storage type value for the
      lpEth100Test tables."
::= { lpEth100TestRowStatusEntry 4 }

lpEth100TestIndex OBJECT-TYPE
   SYNTAX     NonReplicated 
   ACCESS     not-accessible
   STATUS     mandatory
   DESCRIPTION
     "This variable represents the index for the lpEth100Test tables."
::= { lpEth100TestRowStatusEntry 10 }

lpEth100TestPTOTable OBJECT-TYPE
   SYNTAX     SEQUENCE OF LpEth100TestPTOEntry
   ACCESS     not-accessible
   STATUS     mandatory
   DESCRIPTION
     "This group contains the operational data for the LanPortTest 
      component."
::= { lpEth100Test 10 }

lpEth100TestPTOEntry OBJECT-TYPE
   SYNTAX     LpEth100TestPTOEntry
   ACCESS     not-accessible
   STATUS     mandatory
   DESCRIPTION
     "An entry in the lpEth100TestPTOTable."
   INDEX {
      lpIndex,
      lpEth100Index,
      lpEth100TestIndex }
::= { lpEth100TestPTOTable 1 }

LpEth100TestPTOEntry ::= SEQUENCE {
   lpEth100TestType
      INTEGER,
   lpEth100TestFrmSize
      Unsigned32,
   lpEth100TestDuration
      Unsigned32 }

lpEth100TestType OBJECT-TYPE
   SYNTAX     INTEGER  {
                 onCard(0),
                 normal(1),
                 wrapA(257),
                 wrapB(258),
                 thruA(259),
                 thruB(260),
                 extWrapA(263),
                 extWrapB(264),
                 extThruA(265),
                 extThruB(266),
                 extWrapAB(267),
                 extWrapBA(268) }
   ACCESS     read-write
   STATUS     mandatory
   DESCRIPTION
     "This attribute is the type of test to be run. The available test types 
      include the following: card test sets up an internal loop on the board 
      and runs a bit error rate test; manual test assumes the line is looped 
      back externally and a bit error rate test is performed; localLoop test 
      loops back the local modem and performs a bit error rate test; 
      remoteLoop test loops back the remote modem (or CSU) and 
      performs a bit error rate test; externalLoop test loops back the line 
      to the far end; payloadLoop test only loops back the payload data 
      received from the incoming line; Note that localLoop, remoteLoop 
      and payloadLoop are not supported by all function processors."
::= { lpEth100TestPTOEntry 1 }

lpEth100TestFrmSize OBJECT-TYPE
   SYNTAX     Unsigned32 (4..4096)
   ACCESS     read-write
   STATUS     mandatory
   DESCRIPTION
     "This attribute defines the size of the test data frames in number of 
      bytes."
   DEFVAL     { 1024 }
::= { lpEth100TestPTOEntry 2 }

lpEth100TestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpEth100TestPTOEntry 3 }

lpEth100TestResultsTable OBJECT-TYPE
   SYNTAX     SEQUENCE OF LpEth100TestResultsEntry
   ACCESS     not-accessible
   STATUS     mandatory
   DESCRIPTION
     "This group contains all the statistics related attributes of the Test 
      component."
::= { lpEth100Test 11 }

lpEth100TestResultsEntry OBJECT-TYPE
   SYNTAX     LpEth100TestResultsEntry
   ACCESS     not-accessible
   STATUS     mandatory
   DESCRIPTION
     "An entry in the lpEth100TestResultsTable."
   INDEX {
      lpIndex,
      lpEth100Index,
      lpEth100TestIndex }
::= { lpEth100TestResultsTable 1 }

LpEth100TestResultsEntry ::= SEQUENCE {
   lpEth100TestElapsedTime
      Counter32,
   lpEth100TestTimeRemaining
      Unsigned32,
   lpEth100TestCauseOfTermination
      INTEGER,
   lpEth100TestFrmTx
      PassportCounter64,
   lpEth100TestBitsTx
      PassportCounter64,
   lpEth100TestFrmRx
      PassportCounter64,
   lpEth100TestBitsRx
      PassportCounter64,
   lpEth100TestErroredFrmRx
      PassportCounter64 }

lpEth100TestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpEth100TestResultsEntry 4 }

lpEth100TestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpEth100TestResultsEntry 5 }

lpEth100TestCauseOfTermination OBJECT-TYPE
   SYNTAX     INTEGER  {
                 testTimeExpired(0),
                 stoppedByOperator(1),
                 unknown(2),
                 neverStarted(3),
                 testRunning(4) }
   ACCESS     read-only
   STATUS     mandatory
   DESCRIPTION
     "This attribute records the reason the test is terminated."
   DEFVAL     { neverStarted }
::= { lpEth100TestResultsEntry 6 }

lpEth100TestFrmTx OBJECT-TYPE
   SYNTAX     PassportCounter64 
   ACCESS     read-only
   STATUS     mandatory
   DESCRIPTION
     "This attribute is the total number of frames sent during the test 
      period. This counter is not expected to reach its maximum value."
::= { lpEth100TestResultsEntry 7 }

lpEth100TestBitsTx OBJECT-TYPE
   SYNTAX     PassportCounter64 
   ACCESS     read-only
   STATUS     mandatory
   DESCRIPTION
     "This attribute is the total number of bits sent during the test period. 
      This counter is not expected to reach its maximum value."
::= { lpEth100TestResultsEntry 8 }

lpEth100TestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpEth100TestResultsEntry 9 }

lpEth100TestBitsRx OBJECT-TYPE
   SYNTAX     PassportCounter64 
   ACCESS     read-only
   STATUS     mandatory
   DESCRIPTION
     "This attribute is the total number of bits received during the test 
      period. This counter is not expected to reach its maximum value. 
      The counter will wrap around to 0 if it does reach its maximum 
      value."
::= { lpEth100TestResultsEntry 10 }

lpEth100TestErroredFrmRx OBJECT-TYPE
   SYNTAX     PassportCounter64 
   ACCESS     read-only
   STATUS     mandatory
   DESCRIPTION
     "This attribute is the total number of errored frames received during 
      the test period. This counter is not expected to reach its maximum 
      value. The counter will wrap around to 0 if it does reach its 
      maximum value."
::= { lpEth100TestResultsEntry 11 }


-- LanApplication/n
-- The LanApplication component, using the Framer subcomponent, is 
-- used to provide the interface between the VirtualRouter ProtocolPort 
-- and a LAN component such as Ethernet, Fddi, or TokenRing.

la OBJECT IDENTIFIER ::= { components 105 }



laRowStatusTable OBJECT-TYPE
   SYNTAX     SEQUENCE OF LaRowStatusEntry
   ACCESS     not-accessible
   STATUS     mandatory
   DESCRIPTION
     "This entry controls the addition and deletion of 
      la components."
::= { la 1 }

laRowStatusEntry OBJECT-TYPE
   SYNTAX     LaRowStatusEntry
   ACCESS     not-accessible
   STATUS     mandatory
   DESCRIPTION
     "A single entry in the table represents a single 
      la component."
   INDEX {
      laIndex }
::= { laRowStatusTable 1 }

LaRowStatusEntry ::= SEQUENCE {
   laRowStatus
      RowStatus,
   laComponentName
      DisplayString,
   laStorageType
      StorageType,
   laIndex
      Integer32 }

laRowStatus OBJECT-TYPE
   SYNTAX     RowStatus 
   ACCESS     read-write
   STATUS     mandatory
   DESCRIPTION
     "This variable is used as the basis for SNMP naming of
      la components.
      These components can be added and deleted."
::= { laRowStatusEntry 1 }

laComponentName OBJECT-TYPE
   SYNTAX     DisplayString 
   ACCESS     read-only
   STATUS     mandatory
   DESCRIPTION
     "This variable provides the component's string name for
      use with the ASCII Console Interface"
::= { laRowStatusEntry 2 }

laStorageType OBJECT-TYPE
   SYNTAX     StorageType 
   ACCESS     read-only
   STATUS     mandatory
   DESCRIPTION
     "This variable represents the storage type value for the
      la tables."
::= { laRowStatusEntry 4 }

laIndex OBJECT-TYPE
   SYNTAX     Integer32 (0..255)
   ACCESS     not-accessible
   STATUS     mandatory
   DESCRIPTION
     "This variable represents the index for the la tables."
::= { laRowStatusEntry 10 }

laCidDataTable OBJECT-TYPE
   SYNTAX     SEQUENCE OF LaCidDataEntry
   ACCESS     not-accessible
   STATUS     mandatory
   DESCRIPTION
     "This group contains the attribute for a component's Customer 
      Identifier (CID). Refer to the attribute description for a detailed 
      explanation of CIDs."
::= { la 10 }

laCidDataEntry OBJECT-TYPE
   SYNTAX     LaCidDataEntry
   ACCESS     not-accessible
   STATUS     mandatory
   DESCRIPTION
     "An entry in the laCidDataTable."
   INDEX {
      laIndex }
::= { laCidDataTable 1 }

LaCidDataEntry ::= SEQUENCE {
   laCustomerIdentifier
      Unsigned32 }

laCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { laCidDataEntry 1 }

laMediaProvTable OBJECT-TYPE
   SYNTAX     SEQUENCE OF LaMediaProvEntry
   ACCESS     not-accessible
   STATUS     mandatory
   DESCRIPTION
     "This group contains the base provisioning data for the Media 
      Application component."
::= { la 11 }

laMediaProvEntry OBJECT-TYPE
   SYNTAX     LaMediaProvEntry
   ACCESS     not-accessible
   STATUS     mandatory
   DESCRIPTION
     "An entry in the laMediaProvTable."
   INDEX {
      laIndex }
::= { laMediaProvTable 1 }

LaMediaProvEntry ::= SEQUENCE {
   laLinkToProtocolPort
      Link }

laLinkToProtocolPort OBJECT-TYPE
   SYNTAX     Link 
   ACCESS     read-write
   STATUS     mandatory
   DESCRIPTION
     "This attribute contains a protocol port component name. The attribute 
      associates the application with a protocol port."
::= { laMediaProvEntry 1 }

laIfEntryTable OBJECT-TYPE
   SYNTAX     SEQUENCE OF LaIfEntryEntry
   ACCESS     not-accessible
   STATUS     mandatory
   DESCRIPTION
     "This group contains the provisionable attributes for the ifEntry."
::= { la 12 }

laIfEntryEntry OBJECT-TYPE
   SYNTAX     LaIfEntryEntry
   ACCESS     not-accessible
   STATUS     mandatory
   DESCRIPTION
     "An entry in the laIfEntryTable."
   INDEX {
      laIndex }
::= { laIfEntryTable 1 }

LaIfEntryEntry ::= SEQUENCE {
   laIfAdminStatus
      INTEGER,
   laIfIndex
      InterfaceIndex }

laIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { laIfEntryEntry 1 }

laIfIndex OBJECT-TYPE
   SYNTAX     InterfaceIndex (1..65535)
   ACCESS     read-only
   STATUS     mandatory
   DESCRIPTION
     "This is the index for the IfEntry. Its value is automatically initialized 
      during the provisioning process."
::= { laIfEntryEntry 2 }

laStateTable OBJECT-TYPE
   SYNTAX     SEQUENCE OF LaStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { la 13 }

laStateEntry OBJECT-TYPE
   SYNTAX     LaStateEntry
   ACCESS     not-accessible
   STATUS     mandatory
   DESCRIPTION
     "An entry in the laStateTable."
   INDEX {
      laIndex }
::= { laStateTable 1 }

LaStateEntry ::= SEQUENCE {
   laAdminState
      INTEGER,
   laOperationalState
      INTEGER,
   laUsageState
      INTEGER }

laAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { laStateEntry 1 }

laOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { laStateEntry 2 }

laUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { laStateEntry 3 }

laOperStatusTable OBJECT-TYPE
   SYNTAX     SEQUENCE OF LaOperStatusEntry
   ACCESS     not-accessible
   STATUS     mandatory
   DESCRIPTION
     "This group includes the Operational Status attribute. This attribute 
      defines the current operational state of this component."
::= { la 14 }

laOperStatusEntry OBJECT-TYPE
   SYNTAX     LaOperStatusEntry
   ACCESS     not-accessible
   STATUS     mandatory
   DESCRIPTION
     "An entry in the laOperStatusTable."
   INDEX {
      laIndex }
::= { laOperStatusTable 1 }

LaOperStatusEntry ::= SEQUENCE {
   laSnmpOperStatus
      INTEGER }

laSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { laOperStatusEntry 1 }


-- LanApplication/n Framer
-- The Framer component is used to link a LanApplication to a Lan 
-- interface such as Ethernet, Fddi, TokenRing or Ethernet100BaseT.

laFramer OBJECT IDENTIFIER ::= { la 2 }



laFramerRowStatusTable OBJECT-TYPE
   SYNTAX     SEQUENCE OF LaFramerRowStatusEntry
   ACCESS     not-accessible
   STATUS     mandatory
   DESCRIPTION
     "This entry controls the addition and deletion of 
      laFramer components."
::= { laFramer 1 }

laFramerRowStatusEntry OBJECT-TYPE
   SYNTAX     LaFramerRowStatusEntry
   ACCESS     not-accessible
   STATUS     mandatory
   DESCRIPTION
     "A single entry in the table represents a single 
      laFramer component."
   INDEX {
      laIndex,
      laFramerIndex }
::= { laFramerRowStatusTable 1 }

LaFramerRowStatusEntry ::= SEQUENCE {
   laFramerRowStatus
      RowStatus,
   laFramerComponentName
      DisplayString,
   laFramerStorageType
      StorageType,
   laFramerIndex
      NonReplicated }

laFramerRowStatus OBJECT-TYPE
   SYNTAX     RowStatus 
   ACCESS     read-only
   STATUS     mandatory
   DESCRIPTION
     "This variable is used as the basis for SNMP naming of
      laFramer components.
      These components cannot be added nor deleted."
::= { laFramerRowStatusEntry 1 }

laFramerComponentName OBJECT-TYPE
   SYNTAX     DisplayString 
   ACCESS     read-only
   STATUS     mandatory
   DESCRIPTION
     "This variable provides the component's string name for
      use with the ASCII Console Interface"
::= { laFramerRowStatusEntry 2 }

laFramerStorageType OBJECT-TYPE
   SYNTAX     StorageType 
   ACCESS     read-only
   STATUS     mandatory
   DESCRIPTION
     "This variable represents the storage type value for the
      laFramer tables."
::= { laFramerRowStatusEntry 4 }

laFramerIndex OBJECT-TYPE
   SYNTAX     NonReplicated 
   ACCESS     not-accessible
   STATUS     mandatory
   DESCRIPTION
     "This variable represents the index for the laFramer tables."
::= { laFramerRowStatusEntry 10 }

laFramerProvTable OBJECT-TYPE
   SYNTAX     SEQUENCE OF LaFramerProvEntry
   ACCESS     not-accessible
   STATUS     mandatory
   DESCRIPTION
     "This group contains the link to the Lan interface such as Ethernet, Fddi, 
      or TokenRing."
::= { laFramer 10 }

laFramerProvEntry OBJECT-TYPE
   SYNTAX     LaFramerProvEntry
   ACCESS     not-accessible
   STATUS     mandatory
   DESCRIPTION
     "An entry in the laFramerProvTable."
   INDEX {
      laIndex,
      laFramerIndex }
::= { laFramerProvTable 1 }

LaFramerProvEntry ::= SEQUENCE {
   laFramerInterfaceName
      Link }

laFramerInterfaceName OBJECT-TYPE
   SYNTAX     Link 
   ACCESS     read-write
   STATUS     obsolete
   DESCRIPTION
     "This attribute associates the LanApplication with a specific Lan interface 
      such as Ethernet, Fddi, or TokenRing. This also defines the 
      LogicalProcessor on which Framer's parent component (as well as 
      Framer itself) will run. This attribute is OBSOLETED and is redefined 
      above as InterfaceName. The new attribute type is a LIST OF LINK 
      with a maximum of two (2) HW components in a list.
      DESCRIPTION"
::= { laFramerProvEntry 1 }

laFramerInterfaceNamesTable OBJECT-TYPE
   SYNTAX     SEQUENCE OF LaFramerInterfaceNamesEntry
   ACCESS     not-accessible
   STATUS     mandatory
   DESCRIPTION
     "This attribute associates the LanApplication with a specific Lan interface 
      such as Ethernet, Fddi, or TokenRing. This also defines the 
      LogicalProcessor on which Framer's parent component (as well as 
      Framer itself) will run. Only one (1) LAN interface can be linked to a 
      Framer except for Ethernet100BaseT LAN interface, for which up to 
      two (2) interfaces residing on the same LogicalProcessor can be linked.
      DESCRIPTION"
::= { laFramer 431 }

laFramerInterfaceNamesEntry OBJECT-TYPE
   SYNTAX     LaFramerInterfaceNamesEntry
   ACCESS     not-accessible
   STATUS     mandatory
   DESCRIPTION
     "An entry in the laFramerInterfaceNamesTable."
   INDEX {
      laIndex,
      laFramerIndex,
      laFramerInterfaceNamesValue }
::= { laFramerInterfaceNamesTable 1 }

LaFramerInterfaceNamesEntry ::= SEQUENCE {
   laFramerInterfaceNamesValue
      Link,
   laFramerInterfaceNamesRowStatus
      RowStatus }

laFramerInterfaceNamesValue OBJECT-TYPE
   SYNTAX     Link 
   ACCESS     read-write
   STATUS     mandatory
   DESCRIPTION
     "This variable represents both the value and the index for the
      laFramerInterfaceNamesTable."
::= { laFramerInterfaceNamesEntry 1 }

laFramerInterfaceNamesRowStatus OBJECT-TYPE
   SYNTAX     RowStatus 
   ACCESS     write-only
   STATUS     mandatory
   DESCRIPTION
     "This variable is used to control the addition and deletion 
      of individual values of the laFramerInterfaceNamesTable."
::= { laFramerInterfaceNamesEntry 2 }




-- 
-- Version and Compliance statements
-- 



-- Object-Group Statement:
-- A list of all current accessible leaf objects.

-- OBJECTS { lpEnetLtFrmCmpComponentName,
--           lpTrTransmitBeacons,
--           lpFiTransmitCounts,
--           lpEnetLtFbIpHStorageType,
--           lpIlsFwdrFramesReceived,
--           lpIlsFwdrLtFbIpxHTData,
--           lpFiRingLatency,
--           lpFiTvxExpiredCounts,
--           lpFiLtFbTxInfoComponentName,
--           lpEnetTestRowStatus,
--           lpEnetLtFbMacEnetRowStatus,
--           lpEnetLtFbDataTData,
--           lpFiAcceptAa,
--           lpTrLtCntlComponentName,
--           lpFiRingOpCounts,
--           lpFiStatusReportPolicy,
--           lpTrTokenErrors,
--           lpFiLtCntlTData,
--           lpIlsFwdrTestBitsTx,
--           lpIlsFwdrUsageState,
--           lpFiLtFbFddiMacStorageType,
--           lpFiOldDownstreamNeighbor,
--           lpEnetLtCntlStorageType,
--           lpTrGroupAddress,
--           lpEnetMacAddress,
--           lpTrLtPrtCfgRowStatus,
--           laIfAdminStatus,
--           lpEnetLtFbAppleHTData,
--           lpEnetLtFbIpxHComponentName,
--           laCustomerIdentifier,
--           lpEth100LtFbAppleHComponentName,
--           lpFiNotCopiedCounts,
--           lpEth100ReceivedOctetsIntoRouterBr,
--           lpIlsFwdrLtFbTxInfoTData,
--           lpFiLtFrmCpyTData,
--           lpEnetLtFbLlchRowStatus,
--           lpEnetMultipleCollisionFrames,
--           lpTrLtFrmCmpRowStatus,
--           lpEth100LtFbMacEnetRowStatus,
--           lpEth100FramesReceivedOk,
--           lpIlsFwdrLtFbMacTrRowStatus,
--           lpIlsFwdrTestFrmSize,
--           lpFiTestFrmTx,
--           lpFiValidTransmissionTimer,
--           lpEnetLtFrmCpyStorageType,
--           lpFiNcOldUpstreamNeighbor,
--           lpEnetLtFbIpHTData,
--           lpIlsFwdrTestElapsedTime,
--           lpFiUserData,
--           lpEth100LtFbIpHStorageType,
--           lpIlsFwdrLtFbAppleHStorageType,
--           lpFiLtFbStorageType,
--           lpIlsFwdrLtFbMacEnetTData,
--           lpEnetLtFbMacTrComponentName,
--           lpFiLtPrtCfgRowStatus,
--           lpEth100TestTimeRemaining,
--           lpEnetLtFbTxInfoComponentName,
--           lpTrTestTimeRemaining,
--           lpEth100TestType,
--           laLinkToProtocolPort,
--           lpFiTestFrmRx,
--           lpEnetComponentName,
--           lpTrTestType,
--           lpFiLtFbFddiMacTData,
--           lpFiPhyStorageType,
--           lpTrLtFbDataComponentName,
--           lpTrTestElapsedTime,
--           lpEnetLtCntlTData,
--           lpFiTestDuration,
--           lpFiCustomerIdentifier,
--           lpTrRemoveRings,
--           lpEnetLtFbFddiMacStorageType,
--           lpTrIfIndex,
--           lpIlsFwdrLtPrtCfgRowStatus,
--           lpEnetFrameTooLongs,
--           lpFiLtFbMacTrStorageType,
--           lpEth100CommentText,
--           lpEth100LtFbIpxHRowStatus,
--           lpTrCommentText,
--           lpTrLtFbIpxHRowStatus,
--           lpEth100LtFbLlchTData,
--           lpFiLtFbDataRowStatus,
--           laComponentName,
--           lpTrLtFbAppleHComponentName,
--           lpEnetLtFrmCpyTData,
--           lpEth100SingleCollisionFrames,
--           lpEth100StorageType,
--           lpTrStorageType,
--           lpFiLateCounts,
--           lpIlsFwdrTestErroredFrmRx,
--           lpIlsFwdrLtFbMacEnetComponentName,
--           lpFiLtFbTData,
--           lpEth100LtFbIpHComponentName,
--           lpEth100FramesTransmittedOk,
--           lpFiFrameErrorFlag,
--           lpTrLtFbIpHComponentName,
--           lpFiLtFbAppleHRowStatus,
--           lpIlsFwdrLtFbDataRowStatus,
--           lpTrComponentName,
--           lpEth100AdminState,
--           lpFiDownstreamNeighbor,
--           lpEnetLtFbStorageType,
--           lpTrAdminState,
--           lpIlsFwdrTestTimeRemaining,
--           lpFiAcceptBs,
--           lpEth100LtFbTxInfoRowStatus,
--           lpTrApplicationFramerName,
--           lpTrLtStorageType,
--           lpTrLtFbTxInfoRowStatus,
--           lpIlsFwdrProcessedCount,
--           lpIlsFwdrLtFbDataComponentName,
--           lpEnetTestFrmRx,
--           lpEth100LateCollisions,
--           lpEnetLtFbFddiMacTData,
--           lpEth100ExcessiveCollisions,
--           lpFiLtFbIpHRowStatus,
--           lpEnetIfAdminStatus,
--           lpFiPhyLemRejectCounts,
--           lpEth100LtCntlComponentName,
--           lpFiLtFbMacTrTData,
--           lpEnetCustomerIdentifier,
--           lpFiLtFrmCmpStorageType,
--           lpEth100TestBitsTx,
--           lpEth100TestRowStatus,
--           lpIlsFwdrLtFbRowStatus,
--           lpFiNcUpstreamNeighbor,
--           lpTrTestBitsTx,
--           lpEth100TestStorageType,
--           lpEth100LtFbMacEnetStorageType,
--           lpEnetSingleCollisionFrames,
--           lpTrTestStorageType,
--           lpEnetLtFbMacTrStorageType,
--           lpEth100LtFrmCmpStorageType,
--           lpIlsFwdrLtFbAppleHComponentName,
--           lpTrChipSet,
--           lpEnetLtFbDataRowStatus,
--           lpEnetAlignmentErrors,
--           lpIlsFwdrStorageType,
--           lpTrRingState,
--           lpFiLtCntlRowStatus,
--           lpTrLtFrmCpyComponentName,
--           lpFiVersion,
--           lpEth100TestCauseOfTermination,
--           lpEth100LtCntlStorageType,
--           lpIlsFwdrLtFbIpHComponentName,
--           lpEnetMacReceiveErrors,
--           lpEnetLtFbTData,
--           laFramerStorageType,
--           lpFiTestErroredFrmRx,
--           lpEth100ApplicationFramerName,
--           lpEth100LtTData,
--           lpIlsFwdrAdminState,
--           lpEnetLtFbAppleHRowStatus,
--           lpTrLtTData,
--           lpFiComponentName,
--           lpTrLtFbLlchStorageType,
--           lpIlsFwdrLtStorageType,
--           lpIlsFwdrLtFbTxInfoRowStatus,
--           lpFiLtFrmCpyRowStatus,
--           lpTrTestComponentName,
--           lpEth100LtFbMacEnetTData,
--           lpFiTestCauseOfTermination,
--           lpEth100LtFrmCmpComponentName,
--           lpEnetLtPrtCfgStorageType,
--           lpTrLtFrmCpyStorageType,
--           lpTrRingRecoverys,
--           lpEth100LineSpeed,
--           lpFiLtFrmCmpTData,
--           lpFiLtFbIpxHStorageType,
--           lpEnetLtFbIpHRowStatus,
--           lpEth100LtFbFddiMacComponentName,
--           lpIlsFwdrLtCntlComponentName,
--           lpFiLtFbIpHStorageType,
--           lpTrLtFbFddiMacComponentName,
--           lpTrProductId,
--           lpTrLtFbMacEnetTData,
--           lpFiLtComponentName,
--           lpEnetLtFrmCmpStorageType,
--           lpIlsFwdrTestStorageType,
--           lpIlsFwdrLtFbMacEnetStorageType,
--           lpFiErrorCounts,
--           lpTrSoftErrors,
--           lpEth100AutoNegotiation,
--           lpEth100LtRowStatus,
--           laUsageState,
--           lpFiLtPrtCfgTData,
--           lpTrLtFbMacEnetStorageType,
--           lpIlsFwdrLtFrmCpyComponentName,
--           lpFiPhyLerCutoff,
--           lpEth100LtFbMacTrTData,
--           lpEnetLtCntlRowStatus,
--           lpFiTestComponentName,
--           lpFiLtFbMacEnetComponentName,
--           lpTrLobeWires,
--           lpIlsFwdrTestBitsRx,
--           lpEth100LtFbFddiMacTData,
--           lpFiLtFbTxInfoStorageType,
--           lpTrTestBitsRx,
--           lpTrLtFbLlchTData,
--           lpIlsFwdrLtTData,
--           lpEnetTestErroredFrmRx,
--           lpIlsFwdrLtFbLlchStorageType,
--           lpTrLtFbComponentName,
--           lpEth100LtFbMacTrStorageType,
--           lpFiNcOldDownstreamNeighbor,
--           lpFiNeighborNotifyInterval,
--           lpEnetLtPrtCfgTData,
--           lpFiEcmState,
--           lpEnetLtFrmCpyRowStatus,
--           lpFiLtFbIpxHTData,
--           lpFiPhyLemCounts,
--           lpEnetTestCauseOfTermination,
--           lpEth100DeferredTransmissions,
--           lpEnetLtFrmCmpTData,
--           lpEnetLtFbIpxHStorageType,
--           lpFiLtFbLlchComponentName,
--           lpFiLtFbRowStatus,
--           lpIlsFwdrLtFbLlchComponentName,
--           lpFiLostCounts,
--           lpEnetLtComponentName,
--           lpFiUsageState,
--           lpEth100SnmpOperStatus,
--           lpTrLtFbMacTrComponentName,
--           lpTrSnmpOperStatus,
--           lpEth100LtFbMacTrComponentName,
--           lpFiLtFbComponentName,
--           lpFiPhyRowStatus,
--           lpEnetTestFrmTx,
--           lpTrRingStatus,
--           lpTrFunctionalAddress,
--           lpEnetLtFbFddiMacRowStatus,
--           lpFiLtFbTxInfoTData,
--           lpEnetTestComponentName,
--           lpEnetLtFbMacEnetComponentName,
--           lpFiLtFbMacTrRowStatus,
--           lpFiTestFrmSize,
--           lpIlsFwdrLtFbLlchTData,
--           lpEnetLtFbTxInfoStorageType,
--           lpEnetSqeTestErrors,
--           lpTrUpStream,
--           lpFiTestElapsedTime,
--           lpEth100ReceivedFramesIntoRouterBr,
--           lpEth100LtFbDataStorageType,
--           lpIlsFwdrLtFbAppleHTData,
--           lpIlsFwdrLtFrmCmpRowStatus,
--           lpIlsFwdrTestType,
--           lpTrLtFbDataStorageType,
--           lpEth100RowStatus,
--           lpTrFrameCopiedErrors,
--           lpTrRowStatus,
--           lpEth100LtPrtCfgComponentName,
--           lpTrLtFbMacEnetRowStatus,
--           lpEnetLtFbIpxHTData,
--           lpTrLtPrtCfgComponentName,
--           laFramerInterfaceNamesRowStatus,
--           lpTrVendor,
--           lpEnetTestBitsRx,
--           lpEnetLtFbLlchComponentName,
--           lpTrLostFrameErrors,
--           lpTrLtFrmCmpComponentName,
--           lpIlsFwdrLtFbMacTrComponentName,
--           lpIlsFwdrSnmpOperStatus,
--           lpTrLtRowStatus,
--           lpFiTokenCounts,
--           lpEnetLtFbMacEnetStorageType,
--           lpEth100ActualLineSpeed,
--           lpEth100LtFbIpxHComponentName,
--           lpTrOperationalState,
--           lpFiCfState,
--           lpTrLineErrors,
--           laOperationalState,
--           lpFiNcDownstreamNeighbor,
--           lpEth100LtFbDataComponentName,
--           lpTrLtFbIpHStorageType,
--           lpFiLtFrmCmpRowStatus,
--           lpEnetLtFbTxInfoTData,
--           lpIlsFwdrErrorCount,
--           lpIlsFwdrTestFrmTx,
--           lpEnetLtFbLlchStorageType,
--           lpTrTestRowStatus,
--           lpEnetLtFbMacTrRowStatus,
--           lpEnetTestFrmSize,
--           lpTrLtFbDataTData,
--           lpIlsFwdrLtFbDataStorageType,
--           lpEnetTestElapsedTime,
--           lpEth100LtFbIpHRowStatus,
--           laStorageType,
--           lpIlsFwdrRowStatus,
--           lpIlsFwdrLtPrtCfgComponentName,
--           lpEth100LtFbTData,
--           lpFiCopiedCounts,
--           lpTrMonitorParticipate,
--           lpEth100MacAddress,
--           lpTrLtCntlStorageType,
--           lpFiTestTimeRemaining,
--           lpFiPhyLerFlag,
--           lpEth100LtFbAppleHTData,
--           lpTrRingSpeed,
--           lpEth100LtStorageType,
--           lpFiTestType,
--           lpTrLtFbAppleHTData,
--           lpTrLtFbIpxHComponentName,
--           lpFiLtFbDataComponentName,
--           lpTrSingleStation,
--           lpIlsFwdrLtFrmCmpComponentName,
--           lpEth100LtFbLlchRowStatus,
--           lpEth100MultipleCollisionFrames,
--           lpTrLtFbLlchRowStatus,
--           lpIlsFwdrLtRowStatus,
--           lpEth100OctetsTransmittedOk,
--           lpIlsFwdrIfIndex,
--           lpIlsFwdrOperationalState,
--           lpFiPhyLerEstimate,
--           lpEth100LtFbIpHTData,
--           lpEnetLtPrtCfgRowStatus,
--           lpEth100LtFbTxInfoComponentName,
--           laFramerRowStatus,
--           lpTrLtFbIpHTData,
--           lpFiCommentText,
--           lpFiLtFbIpxHRowStatus,
--           lpTrFreqErrors,
--           lpIlsFwdrLtFbIpHStorageType,
--           lpIlsFwdrLtFbFddiMacComponentName,
--           lpFiLtFbAppleHComponentName,
--           lpEth100TestFrmSize,
--           lpEth100LtPrtCfgRowStatus,
--           lpFiDupAddressTest,
--           lpEnetLtFrmCmpRowStatus,
--           lpIlsFwdrLtFbMacTrTData,
--           lpIlsFwdrLtFbMacEnetRowStatus,
--           lpFiStorageType,
--           lpIlsFwdrLtFbDataTData,
--           lpFiPhySignalBitsRcvd,
--           lpEth100Vendor,
--           lpTrLtFbTxInfoComponentName,
--           lpEth100LtFbDataTData,
--           lpEnetFcsErrors,
--           lpEth100LtFrmCpyStorageType,
--           lpFiLtFbIpHComponentName,
--           lpEth100LtCntlTData,
--           lpTrLtCntlTData,
--           lpIlsFwdrComponentName,
--           lpFiAdminState,
--           lpIlsFwdrLtCntlStorageType,
--           lpTrLtFbFddiMacStorageType,
--           lpEth100FrameTooLongs,
--           lpFiApplicationFramerName,
--           lpFiLtStorageType,
--           lpFiLtFbTxInfoRowStatus,
--           lpIlsFwdrLtFbIpxHComponentName,
--           lpEnetTestTimeRemaining,
--           lpFiOperationalState,
--           lpEnetTestType,
--           lpEth100LtFrmCmpRowStatus,
--           lpEnetLtFbDataComponentName,
--           lpIlsFwdrLtFbIpxHRowStatus,
--           lpFiLtFbFddiMacRowStatus,
--           lpTrLtFrmCpyTData,
--           lpFiLtCntlComponentName,
--           lpEnetCarrierSenseErrors,
--           lpIlsFwdrLtFrmCpyStorageType,
--           lpEnetUsageState,
--           lpFiTestBitsTx,
--           lpIlsFwdrLtFbIpHTData,
--           lpTrTestFrmTx,
--           lpFiTestStorageType,
--           lpFiLtFbMacEnetStorageType,
--           lpEnetCommentText,
--           lpEnetLtFbIpxHRowStatus,
--           lpTrLtFbAppleHStorageType,
--           lpEnetLtFbAppleHComponentName,
--           lpEth100LtFbStorageType,
--           lpFiPhyLctFailCounts,
--           lpEnetLtFbMacTrTData,
--           lpTrLtFbStorageType,
--           lpIlsFwdrLtFbTxInfoComponentName,
--           lpFiLtFrmCpyComponentName,
--           lpEnetStorageType,
--           lpEnetLtFbComponentName,
--           lpFiPhyPcmState,
--           lpFiTestBitsRx,
--           lpEth100LtFrmCpyComponentName,
--           lpTrTestFrmRx,
--           lpIlsFwdrLtCntlTData,
--           lpIlsFwdrLinkToTrafficSourceValue,
--           lpEnetLtFbIpHComponentName,
--           lpEth100IfAdminStatus,
--           lpFiAcceptAs,
--           lpEth100TestDuration,
--           lpFiLtTData,
--           lpFiBypassPresent,
--           lpEth100CustomerIdentifier,
--           lpTrTestDuration,
--           lpFiLtFbLlchStorageType,
--           lpEnetAdminState,
--           lpTrCustomerIdentifier,
--           lpFiNcMacAddress,
--           lpEth100OctetsReceivedOk,
--           lpEnetApplicationFramerName,
--           lpEnetLtStorageType,
--           lpEnetLtFbTxInfoRowStatus,
--           lpFiPhyNeighborType,
--           lpTrLtFbMacTrStorageType,
--           lpFiUseThruBa,
--           lpIlsFwdrLtCntlRowStatus,
--           lpTrLtFbFddiMacTData,
--           lpEth100LtFbDataRowStatus,
--           lpIlsFwdrLtFrmCpyTData,
--           lpTrLtFbDataRowStatus,
--           lpEth100AlignmentErrors,
--           lpFiLtFbFddiMacComponentName,
--           lpEth100LtFbMacEnetComponentName,
--           lpFiLtFbMacEnetTData,
--           lpTrAcErrors,
--           lpTrRingOpenStatus,
--           lpEnetLtCntlComponentName,
--           lpIlsFwdrLtFbLlchRowStatus,
--           lpEnetHeartbeatPacket,
--           lpEnetTestBitsTx,
--           laAdminState,
--           lpEnetTestStorageType,
--           lpTrNcUpStream,
--           lpTrLtFbTData,
--           laRowStatus,
--           lpEth100LtFbAppleHRowStatus,
--           lpEth100TestFrmTx,
--           lpIlsFwdrLtFbStorageType,
--           lpTrLtFbAppleHRowStatus,
--           laSnmpOperStatus,
--           lpEth100IfIndex,
--           lpTrBurstErrors,
--           laIfIndex,
--           lpIlsFwdrTestCauseOfTermination,
--           lpEnetLtFrmCpyComponentName,
--           lpEnetMacTransmitErrors,
--           lpIlsFwdrTestFrmRx,
--           lpEth100LtPrtCfgStorageType,
--           lpEth100LtPrtCfgTData,
--           lpIlsFwdrLtFbFddiMacTData,
--           lpEnetLtFbRowStatus,
--           lpTrLtPrtCfgStorageType,
--           lpFiLtFbLlchTData,
--           lpFiOldUpstreamNeighbor,
--           lpIlsFwdrIfAdminStatus,
--           lpTrMacAddress,
--           lpIlsFwdrTestDuration,
--           lpTrLtFbIpHRowStatus,
--           lpEnetLtTData,
--           lpTrIfAdminStatus,
--           lpEth100LtFbComponentName,
--           lpFiAcceptBm,
--           lpTrLtFbMacTrTData,
--           lpTrLtFrmCmpStorageType,
--           lpEth100LtFbTxInfoStorageType,
--           lpIlsFwdrLtFbMacTrStorageType,
--           lpTrSignalLoss,
--           lpEth100TestFrmRx,
--           lpEnetTestDuration,
--           lpFiPhyComponentName,
--           lpIlsFwdrLtFbFddiMacStorageType,
--           lpEth100ActualDuplexMode,
--           lpFiRmtState,
--           lpFiAcceptAm,
--           lpFiLtFrmCmpComponentName,
--           lpEnetOperationalState,
--           lpEnetLtFbFddiMacComponentName,
--           lpTrReceiveCongestions,
--           lpEnetLtFbMacEnetTData,
--           lpEth100UndersizeFrames,
--           lpTrLtCntlRowStatus,
--           lpFiLtFbMacTrComponentName,
--           lpFiSnmpOperStatus,
--           lpIlsFwdrLtFbTData,
--           lpFiIfIndex,
--           lpFiPhyLinkErrorMonitor,
--           lpEth100TestErroredFrmRx,
--           lpIlsFwdrLtFbAppleHRowStatus,
--           lpTrTestErroredFrmRx,
--           lpEth100ComponentName,
--           lpFiTraceMaxExpirationTimer,
--           lpEth100TestComponentName,
--           lpTrLtPrtCfgTData,
--           lpEth100LtFrmCpyRowStatus,
--           lpTrNcMacAddress,
--           lpTrLtFrmCpyRowStatus,
--           lpIlsFwdrLtPrtCfgStorageType,
--           lpFiPhySignalBitsTxmt,
--           lpTrHardErrors,
--           lpEth100LtFrmCmpTData,
--           lpEnetLateCollisions,
--           lpTrTestCauseOfTermination,
--           lpEth100UsageState,
--           lpIlsFwdrLtFbIpHRowStatus,
--           lpEnetLtFbLlchTData,
--           lpEth100LtFbIpxHStorageType,
--           lpTrLtFrmCmpTData,
--           lpTrLtFbIpxHStorageType,
--           lpFiLtFbDataStorageType,
--           lpIlsFwdrLtFrmCmpStorageType,
--           lpEth100MacTransmitErrors,
--           lpEth100LtFbLlchStorageType,
--           lpEth100LtComponentName,
--           lpFiRowStatus,
--           lpIlsFwdrLtFbComponentName,
--           lpTrLtComponentName,
--           lpEth100LtFrmCpyTData,
--           lpFiLtPrtCfgComponentName,
--           lpFiVendor,
--           lpFiFrameCounts,
--           lpEnetDeferredTransmissions,
--           lpEth100FcsErrors,
--           lpEth100LtFbFddiMacRowStatus,
--           lpFiLtFbAppleHStorageType,
--           lpTrLtFbFddiMacRowStatus,
--           lpFiTokenMaxTimer,
--           lpIlsFwdrFramesDiscarded,
--           lpIlsFwdrTestRowStatus,
--           lpFiLtRowStatus,
--           lpFiTokenRequestTimer,
--           lpTrLtFbMacEnetComponentName,
--           lpEnetSnmpOperStatus,
--           lpEnetExcessiveCollisions,
--           lpFiUpstreamNeighbor,
--           lpEnetIfIndex,
--           lpEth100SqeTestErrors,
--           lpTrLtFbTxInfoStorageType,
--           lpEth100LtFbAppleHStorageType,
--           lpFiMacAddress,
--           lpIlsFwdrLtPrtCfgTData,
--           lpEth100MacReceiveErrors,
--           lpFiPhySignalState,
--           lpFiIfAdminStatus,
--           lpTrAbortTransErrors,
--           lpIlsFwdrLtFrmCpyRowStatus,
--           lpEth100AutoNegStatus,
--           lpEth100LtFbIpxHTData,
--           lpFiTestRowStatus,
--           lpFiLtFbMacEnetRowStatus,
--           lpTrLtFbIpxHTData,
--           lpFiTokenNegotiatedTimer,
--           lpFiLtFbDataTData,
--           lpEth100CarrierSenseErrors,
--           lpEth100DuplexMode,
--           lpIlsFwdrLtFrmCmpTData,
--           lpIlsFwdrLtFbIpxHStorageType,
--           laFramerComponentName,
--           lpEth100LtFbLlchComponentName,
--           lpEth100LtFbRowStatus,
--           lpTrInternalErrors,
--           lpEnetLtFbDataStorageType,
--           lpTrLtFbRowStatus,
--           lpIlsFwdrLtComponentName,
--           lpTrLtFbLlchComponentName,
--           lpFiLtFbIpHTData,
--           lpEnetRowStatus,
--           lpTrNodeAddress,
--           lpFiLtCntlStorageType,
--           lpTrUsageState,
--           lpEth100TestBitsRx,
--           lpEnetLtPrtCfgComponentName,
--           laFramerInterfaceNamesValue,
--           lpEnetVendor,
--           lpFiLtFbAppleHTData,
--           lpFiLtFbIpxHComponentName,
--           lpEth100OperationalState,
--           lpIlsFwdrLtFbFddiMacRowStatus,
--           lpFiLtPrtCfgStorageType,
--           lpFiLtFbLlchRowStatus,
--           lpEth100LtFbTxInfoTData,
--           lpEnetLtFbAppleHStorageType,
--           lpIlsFwdrTestComponentName,
--           lpTrLtFbTxInfoTData,
--           lpFiAcceptBb,
--           lpEnetLtRowStatus,
--           lpEth100LtFbMacTrRowStatus,
--           lpIlsFwdrLtFbTxInfoStorageType,
--           lpFiLtFrmCpyStorageType,
--           lpEth100LtFbFddiMacStorageType,
--           lpTrLtFbMacTrRowStatus,
--           lpTrTestFrmSize,
--           lpTrLastTimeBeaconSent,
--           lpFiPhyLerAlarm,
--           lpEth100LtCntlRowStatus,
--           lpEth100TestElapsedTime }
-- STATUS  mandatory
-- DESCRIPTION
--   "A list of all current accessible leaf objects."

lanDriversGroup OBJECT IDENTIFIER ::= { lanDriversMIB 1 }
lanDriversGroupBE OBJECT IDENTIFIER ::= { lanDriversGroup 5 }
lanDriversGroupBE01 OBJECT IDENTIFIER ::= { lanDriversGroupBE 2 }
lanDriversGroupBE01A OBJECT
