CTRON-SFCS-MIB DEFINITIONS ::= BEGIN

--  ctron-sfcs-mib.txt
--  Revision: 1.00.01
--  Date: March 23, 1999
 
 
--  Cabletron Systems, Inc.
--  35 Industrial Way, P.O. Box 5005
--  Rochester, NH 03867-0505
--  (603) 332-9400
--  support@ctron.com
 
--  This module provides authoritative definitions for Cabletron's
--  enterprise specific Secure Fast Cell Switching MIB.
--
--  This module will be extended, as required.
--
 
--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.
--  Copyright October 98 Cabletron Systems
--
 

               IMPORTS
                     OBJECT-TYPE
                               FROM RFC-1212
                     DisplayString
                               FROM RFC1213-MIB
                     enterprises, IpAddress, TimeTicks
                               FROM RFC1155-SMI
                     TruthValue
                               FROM SNMPv2-TC
                     atmVcCrossConnectIndex, atmVcCrossConnectLowIfIndex, 
                     atmVcCrossConnectLowVpi, atmVcCrossConnectLowVci, 
                     atmVcCrossConnectHighIfIndex, atmVcCrossConnectHighVpi, 
                     atmVcCrossConnectHighVci
                               FROM ATM-MIB;

cabletron               OBJECT IDENTIFIER ::= { enterprises 52 }

mibs                    OBJECT IDENTIFIER ::= { cabletron 4 }

ctron                   OBJECT IDENTIFIER ::= { mibs 1 }

ctDataLink              OBJECT IDENTIFIER ::= { ctron 2 }

ctSwitch                OBJECT IDENTIFIER ::= { ctDataLink 11 }

ctsfSwitch              OBJECT IDENTIFIER ::= { ctSwitch 1 }

ctSFCS                  OBJECT IDENTIFIER ::= { ctsfSwitch 1 }


-- The SFCS Groups.

-- The SFCS System Groups (switch system)
sfcsSystem              OBJECT IDENTIFIER ::= { ctSFCS 1 }
        sfcsSysConfig           OBJECT IDENTIFIER ::= { sfcsSystem 1 }
        sfcsSysStatus           OBJECT IDENTIFIER ::= { sfcsSystem 2 }
        sfcsSysSystemCfg        OBJECT IDENTIFIER ::= { sfcsSystem 3 }
        sfcsSysBPCfg        OBJECT IDENTIFIER ::= { sfcsSystem 4 }

-- All groups from here on represent a single switch module

-- The SFCS Engine Groups
sfcsEngine              OBJECT IDENTIFIER ::= { ctSFCS 2 }
        sfcsConfig              OBJECT IDENTIFIER ::= { sfcsEngine 1 }
        sfcsStatus              OBJECT IDENTIFIER ::= { sfcsEngine 2 }
        sfcsUPCEngine           OBJECT IDENTIFIER ::= { sfcsEngine 3 }
        sfcsStatisticsEngine    OBJECT IDENTIFIER ::= { sfcsEngine 4 }
        sfcsPacketDiscardEngine OBJECT IDENTIFIER ::= { sfcsEngine 5 }


-- The SFCS ANIM Groups
sfcsANIM                OBJECT IDENTIFIER ::= { ctSFCS 3 }
        sfcsANIMConfig          OBJECT IDENTIFIER ::= { sfcsANIM 1 }
        sfcsANIMStatistics      OBJECT IDENTIFIER ::= { sfcsANIM 2 }
        sfcsANIMPic		OBJECT IDENTIFIER ::= { sfcsANIM 3 }


--  The SFCS Interface Groups
sfcsInterface           OBJECT IDENTIFIER ::= { ctSFCS 4 }
        sfcsInterfaceConfig     OBJECT IDENTIFIER ::= { sfcsInterface 1 }
        sfcsInterfaceStatistics OBJECT IDENTIFIER ::= { sfcsInterface 2 }


--  The SFCS Queue Groups
sfcsQueue               OBJECT IDENTIFIER ::= { ctSFCS 5 }
        sfcsQueueConfig         OBJECT IDENTIFIER ::= { sfcsQueue 1 }
        sfcsQueueStatistics     OBJECT IDENTIFIER ::= { sfcsQueue 2 }


--  The SFCS Connection Groups
sfcsConnection          OBJECT IDENTIFIER ::= { ctSFCS 7 }
        sfcsConnectionConfig      OBJECT IDENTIFIER ::= { sfcsConnection 1 }
        sfcsConnectionStatistics  OBJECT IDENTIFIER ::= { sfcsConnection 2 }
        sfcsConnectionError       OBJECT IDENTIFIER ::= { sfcsConnection 3 }


--  The SFCS Connection API Group
sfcsConnectionAPI       OBJECT IDENTIFIER ::= { ctSFCS 8 }


--  The SFCS CTM Groups
sfcsCTM                 OBJECT IDENTIFIER ::= { ctSFCS 9 }
        sfcsCTMInterfaceConfig       OBJECT IDENTIFIER ::= { sfcsCTM 1 }
        sfcsCTMInterfaceStatistics   OBJECT IDENTIFIER ::= { sfcsCTM 2 }
        sfcsCTMQueueConfig           OBJECT IDENTIFIER ::= { sfcsCTM 3 }
        sfcsCTMQueueStatistics       OBJECT IDENTIFIER ::= { sfcsCTM 4 }


--  The SFCS Bandwidth Managment Groups
sfcsBWMgr              OBJECT IDENTIFIER ::= { ctSFCS 12 }
        sfcsBwNims            OBJECT IDENTIFIER ::= { sfcsBWMgr 1 }
        sfcsBwPorts           OBJECT IDENTIFIER ::= { sfcsBWMgr 2 }
        sfcsBwPortPools           OBJECT IDENTIFIER ::= { sfcsBWMgr 3 }
        sfcsBuffPools             OBJECT IDENTIFIER ::= { sfcsBWMgr 4 }


--  The ANIM Proxy Groups
sfcsProxy               OBJECT IDENTIFIER ::= { ctSFCS 13 }
        sfcsProxyConfig         OBJECT IDENTIFIER ::= { sfcsProxy 1 }
        sfcsProxyTrans          OBJECT IDENTIFIER ::= { sfcsProxy 2 }
        sfcsProxyRead           OBJECT IDENTIFIER ::= { sfcsProxy 3 }



sfcsSysConfigTable OBJECT IDENTIFIER ::= { sfcsSysConfig 1 }

sfcsSysConfigEnt OBJECT IDENTIFIER ::= { sfcsSysConfigTable 1 }
        
sfcsSysConfigAdminStatus     OBJECT-TYPE
        SYNTAX  INTEGER {
                        enabled(1),          --  startup the SFCS
                        disabled(2),         --  shutdown the SFCS
                        other(3)             --  none of the following
                }
        ACCESS  read-write
        STATUS  mandatory
        DESCRIPTION
                "Sets the administrative state of the SFCS switching
                 services for this virtual switch.  This controls the
                 SFCS state at a chassis level.  Regardless of the
                 per-interface state of each SFCS switching element
                 and the state of active connections, writing the value
                 disabled(2) will cause the entire switch to immediately
                 shutdown.
                                 enabled(1)    --  startup the SFCS
                                 disabled(2)   --  shutdown the SFCS
                                 other(3)      --  none of the following"
        ::= { sfcsSysConfigEnt 1 }

sfcsSysConfigOperStatus     OBJECT-TYPE
        SYNTAX  INTEGER {
                        enabled(1),           --  running
                        disabled(2),          --  not running
                        other(3),             --  none of the following
                        pending-disable(4),   --  shut-down in progress
                        pending-enable(5),    --  start-up in progress
                        invalid-config(6)     --  not running,invalid config
                }
        ACCESS  read-only
        STATUS  mandatory
        DESCRIPTION
                "Indicates the current operating condition of this switch.
                        enabled(1)          --  running
                        disabled(2)         --  not running
                        other(3)            --  none of the following
                        pending-disable(4)  --  shut-down in progress
                        pending-enable(5)   --  start-up in progress
                        invalid-config(6)   --  not running,invalid config"
        ::= { sfcsSysConfigEnt 2 }
            
sfcsSysConfigOperTime  OBJECT-TYPE
        SYNTAX  TimeTicks
        ACCESS  read-only
        STATUS  mandatory
        DESCRIPTION
                "Indicates the amount of time (# of time ticks) that
                 this switch system has been in its current operational
                 state."
        ::= { sfcsSysConfigEnt 3 }

sfcsSysConfigLastChange  OBJECT-TYPE
        SYNTAX  TimeTicks
        ACCESS  read-only
        STATUS  mandatory
        DESCRIPTION
                "Indicates the last time a change was made to the
                 configuration entry for this switch."
        ::= { sfcsSysConfigEnt 4 }

sfcsSysConfigSwitchCapacity     OBJECT-TYPE
        SYNTAX  INTEGER
        ACCESS  read-only
        STATUS  mandatory
        DESCRIPTION
                "Indicates the maximum front panel bandwidth based on current
		 hardware configuration of the switch in Mbps"
        ::= { sfcsSysConfigEnt 5 }

sfcsSysConfigMaxCnxEntries      OBJECT-TYPE
        SYNTAX  INTEGER
        ACCESS  read-only
        STATUS  mandatory
        DESCRIPTION
                "Indicates the maximum number of connections which
                 can be established on this switch."
        ::= { sfcsSysConfigEnt 6 }

sfcsSysConfigMaxStatEntries     OBJECT-TYPE
        SYNTAX  INTEGER
        ACCESS  read-only
        STATUS  mandatory
        DESCRIPTION
                "Indicates the maximum number of stats enabled VCs for this
                 switch."
        ::= { sfcsSysConfigEnt 7 }

sfcsSysConfigMaxUpcEntries      OBJECT-TYPE
        SYNTAX  INTEGER
        ACCESS  read-only
        STATUS  mandatory
        DESCRIPTION
                "Indicates the maximum number of UPC enabled VCs for this
                 switch."
        ::= { sfcsSysConfigEnt 8 }

sfcsSysConfigNumberANIMS        OBJECT-TYPE
        SYNTAX  INTEGER
        ACCESS  read-only
        STATUS  mandatory
        DESCRIPTION
                "Indicates the number of ATM Network Inteface Modules
                 currently configured on this switch."
        ::= { sfcsSysConfigEnt 9 }

sfcsSysConfigInterfaceCapability        OBJECT-TYPE
        SYNTAX  INTEGER
        ACCESS  read-only
        STATUS  mandatory
        DESCRIPTION
                "Indicates the total bandwidth capability(of the engine)
		 for this switch expressed in Mbps."
        ::= { sfcsSysConfigEnt 10 }

sfcsSysConfigTypeofSwitch       OBJECT-TYPE
        SYNTAX  INTEGER {
                        other           (1),
                        sfcellswitch    (2),
                        sfpacketswitch  (3)
                }
        ACCESS  read-only
        STATUS  mandatory
        DESCRIPTION
                "Indicates what type of switch this is.
                        other(1)
                        sfcellswitch(2)
                        sfpacketswitch(3)"
        ::= { sfcsSysConfigEnt 11 }

sfcsSysConfigPolicingSupport    OBJECT-TYPE
        SYNTAX  TruthValue
        ACCESS  read-only
        STATUS  mandatory
        DESCRIPTION
                "Indicates whether or not this switch supports policing.
                        supported(1)
                        not supported(2)"
        ::= { sfcsSysConfigEnt 12 }

sfcsSysConfigPnniNsapPrefix        OBJECT-TYPE
        SYNTAX  OCTET STRING (SIZE(13))
        ACCESS  read-write
        STATUS  mandatory
        DESCRIPTION
                "This is the 13 byte NSAP prefix to use
                 with address registration."
        ::= { sfcsSysConfigEnt 13 }

sfcsSysConfigPnniNodeLevel        OBJECT-TYPE
        SYNTAX  INTEGER 
        ACCESS  read-write
        STATUS  mandatory
        DESCRIPTION
                "This is the PNNI node level value. 
                 The range can be from 0 to 104."
        ::= { sfcsSysConfigEnt 14 }

sfcsSysConfigPnniAddessingMode    OBJECT-TYPE
        SYNTAX  INTEGER 
        ACCESS  read-write
        STATUS  mandatory
        DESCRIPTION
                "This is the PNNI addressing mode - that 
                 can range from 0 to 2.
                 0 - Auto Mode using MAC
                 1 - Auto Mode using board#
                 2 - Manual "
        ::= { sfcsSysConfigEnt 15 }

sfcsSysConfigPnniAddessingAdmnStatus    OBJECT-TYPE
        SYNTAX  INTEGER 
        ACCESS  read-write
        STATUS  mandatory
        DESCRIPTION
                "This is the PNNI addressing admn status.
                 Down - 2. Up - 1."
        ::= { sfcsSysConfigEnt 16 }

sfcsSysConfigFMVer        OBJECT-TYPE
        SYNTAX  OCTET STRING (SIZE(8))
        ACCESS  read-only
        STATUS  mandatory
        DESCRIPTION
                "This is the Firmware Revision of the switch."
        ::= { sfcsSysConfigEnt 17 }

sfcsSysConfigCTMSlotMask        OBJECT-TYPE
        SYNTAX  INTEGER
        ACCESS  read-only
        STATUS  mandatory
        DESCRIPTION
                "This is the slot mask for all ctm boards in the chassis.
		 The least significant bit represents slot 1."
        ::= { sfcsSysConfigEnt 18 }

sfcsSysConfigMaxfreecva         OBJECT-TYPE
        SYNTAX  INTEGER
        ACCESS  read-write
        STATUS  mandatory
        DESCRIPTION
                "This is the maximum number of CAC connection blocks that
        CAC will allow on its free list. The default is 1024. If too low
        CAC performance will degrade (thrashing control blocks), If too high,
        memory exhaustion may occur. 
         "
        ::= { sfcsSysConfigEnt 19 }

sfcsSysConfigUBR         OBJECT-TYPE
        SYNTAX  INTEGER
        ACCESS  read-write
        STATUS  mandatory
        DESCRIPTION
                "For the set operation: UBR_Cfg is set across all boards in the 
                 chassis (that are operational and manageable).
                 For the get operation: UBR_Cfg setting is retrived from the 
                 current chassis manager only (one slot only).
                 IF boards are introduced or re-introduced to the chassis their 
                 UBR value will be 0. In order to insure a required UBR_Cfg value 
                 the set operation should be proformed after slot insertions or 
                 re-insertions are completed to the chassis. "
        ::= { sfcsSysConfigEnt 20 }


--  SFCS System Status Table
--  This table contains the objects that pertain to the operational status
--  of a virtual switch.


sfcsSysStatusTable OBJECT IDENTIFIER ::= { sfcsSysStatus 1 }

sfcsSysStatusEnt OBJECT IDENTIFIER ::= { sfcsSysStatusTable 1 }

sfcsSysStatusTdmCellCount       OBJECT-TYPE
        SYNTAX          OCTET STRING
        ACCESS          read-only
        STATUS          mandatory
        DESCRIPTION
                "Indicates the total number of cells being transfered
                 across the TDM for the entire switch."
        ::= { sfcsSysStatusEnt 1 }

sfcsSysStatusTdmUtilization     OBJECT-TYPE
        SYNTAX          INTEGER (0..100)
        ACCESS          read-only
        STATUS          mandatory
        DESCRIPTION
                "Indicates the total percentage TDM utilization for the switch."
        ::= { sfcsSysStatusEnt 2 }

sfcsSysStatusCurrCnxEntries     OBJECT-TYPE
        SYNTAX  INTEGER
        ACCESS  read-only
        STATUS  mandatory
        DESCRIPTION
                "Indicates the current number of connection entries for
                 this switch."
        ::= { sfcsSysStatusEnt 3 }

sfcsSysStatusCurrUPCEntries     OBJECT-TYPE
        SYNTAX  INTEGER
        ACCESS  read-only
        STATUS  mandatory
        DESCRIPTION
                "Indicates the current number of UPC entries for this
                 switch."
        ::= { sfcsSysStatusEnt 4 }

sfcsSysStatusCurrStatsEntries   OBJECT-TYPE
        SYNTAX  INTEGER
        ACCESS  read-only
        STATUS  mandatory
        DESCRIPTION
                "Indicates the current number of statistics entries for
                 this switch."
        ::= { sfcsSysStatusEnt 5 }

sfcsSysStatusAllocatedBw           OBJECT-TYPE
        SYNTAX  INTEGER
        ACCESS  read-only
        STATUS  mandatory
        DESCRIPTION
                "Indicates the current allocated bandwidth of the switch in
		 bits per second."
        ::= { sfcsSysStatusEnt 6 }



--  SFCS System Configuration Table set up as a SYSTEM MIB
--  This table contains the objects that pertain to the setup and
--  configuration of the virtual switch.
 
sfcsSysSystemCfgTable OBJECT IDENTIFIER ::= { sfcsSysSystemCfg 1 }
 
sfcsSysSystemCfgEnt OBJECT IDENTIFIER ::= { sfcsSysSystemCfgTable 1 }
 
sfcsSysConfigAdminReset      OBJECT-TYPE
        SYNTAX  INTEGER {
                        other(1),            --  none of the following
                        reset(2)             --  force a reset
                }
 
   ACCESS  read-write
        STATUS  mandatory
        DESCRIPTION
                "Resets this virtual switch. Writing a value of
                 reset(2) will force a restart of the entire switch,
                 without any graceful shutdown.  Any active
                 connections or services will be interrupted.
                        other(1)     --  none of the following
                        reset(2)     --  force a reset"
        ::= { sfcsSysSystemCfgEnt 1 }
 
sfcsSysConfigATOMPersistance        OBJECT-TYPE
        SYNTAX  INTEGER {
                                enabled (1),
                                disabled (2)
        }
        ACCESS  read-write
        STATUS  mandatory
        DESCRIPTION
                "This enables or disables ATOM mib persistance.
                              enabled(1)
                              disabled(2)"
        ::= { sfcsSysSystemCfgEnt 2 }
 
sfcsSysConfigVcSize        OBJECT-TYPE
        SYNTAX  INTEGER
        ACCESS  read-write
        STATUS  mandatory
        DESCRIPTION
                "This entry is the size of VCs allocated for all
                 VPs in the switch."
        ::= { sfcsSysSystemCfgEnt 3 }
 
sfcsSysConfigPowerUpDiags        OBJECT-TYPE
        SYNTAX  INTEGER {
                                enabled (1),
                                disabled (2)
        }
        ACCESS  read-write
        STATUS  mandatory
        DESCRIPTION
                "This enables or disables power up diags.
                              enabled(1)
                              disabled(2)"
        ::= { sfcsSysSystemCfgEnt 4 }
 

--  SFCS System Back Plane Table set up as a SYSTEM MIB
--  This table contains the objects that pertain to the setup and
--  configuration of the virtual switch.
 
sfcsSysBPTable OBJECT IDENTIFIER ::= { sfcsSysBPCfg 1 }
 
sfcsSysBPEnt OBJECT IDENTIFIER ::= { sfcsSysBPTable 1 }

sfcsSysBPClkSelect        OBJECT-TYPE
        SYNTAX  INTEGER 
        ACCESS  read-write
        STATUS  mandatory
        DESCRIPTION
                "This enables one of two backplane clocks from any slot.
                 A valid entry is any number that correspond to a slot
                 having a board supporting this mib. A write to this mib
                 will fail if the board with the number selected is deriving 
                 its clock from the backplane. A value of 0 indicates that no 
                 board is driving the backplane."
        ::= { sfcsSysBPEnt 1 }


--  From here forward, all objects represent the switch modules.


--  SFCS Engine Group
--  This group contains the objects that pertain to switching engines at
--  a switch module, slot-instanced level.  This group contains four sub-groups:
--  configuration status, statistics, UPC Engine, and statistics engine.


--  SFCS Engine Configuration Table
--  This table contains the objects that pertain to the setup and
--  configuration of a single SFCS module.

sfcsConfigTable                 OBJECT-TYPE
        SYNTAX  SEQUENCE OF SfcsConfigEntry
        ACCESS  not-accessible
        STATUS  mandatory
        DESCRIPTION
                "This table contains the configuration and administrative
                 information for each SFCS module.  Essentially, a
                 separate SFCS instance exists for each switch module.
                 If SFCS is not configured on a module, than an entry
                 will not exist."
        ::= { sfcsConfig 1 }

sfcsConfigEntry                 OBJECT-TYPE
        SYNTAX  SfcsConfigEntry
        ACCESS  not-accessible
        STATUS  mandatory
        DESCRIPTION
                "Each entry specifies the SFCS configuration for the
                 SFCS module."
        INDEX   { sfcsConfigSlotIndex }
        ::= { sfcsConfigTable 1 }

SfcsConfigEntry ::=
        SEQUENCE {
                sfcsConfigSlotIndex             INTEGER,
                sfcsConfigAdminStatus           INTEGER,
                sfcsConfigAdminReset            INTEGER,
                sfcsConfigOperStatus            INTEGER,
                sfcsConfigOperTime              TimeTicks,
                sfcsConfigLastChange            TimeTicks,
                sfcsConfigVersion               INTEGER,
                sfcsConfigMibRev                DisplayString,
                sfcsConfigSwitchHostPort        INTEGER,
                sfcsConfigHostCtrlATMAddr       OCTET STRING,
                sfcsConfigSwitchCapacity        INTEGER,
                sfcsConfigMaxCnxEntries         INTEGER,
                sfcsConfigMaxStatEntries        INTEGER,
                sfcsConfigMaxUpcEntries         INTEGER,
                sfcsConfigNumberANIMS           INTEGER,
                sfcsConfigBwCapability          INTEGER,
                sfcsConfigMasterClock1Source    INTEGER,
                sfcsConfigMasterClock2Source    INTEGER,
		sfcsConfigMasterClock1Standby   INTEGER,
		sfcsConfigMasterClock2Standby   INTEGER
		}

sfcsConfigSlotIndex             OBJECT-TYPE
        SYNTAX  INTEGER
        ACCESS  read-only
        STATUS  mandatory
        DESCRIPTION
                "The primary index to the SFCS switch table.  This
                 identifies the chassis slot number for this switch
                 module."
        ::= { sfcsConfigEntry 1 }

sfcsConfigAdminStatus           OBJECT-TYPE
        SYNTAX  INTEGER {
                        enabled(1),         --  startup the SFCS
                        disabled(2),        --  shutdown the SFCS
                        other(3)            --  none of the following
                }
        ACCESS  read-write
        STATUS  mandatory
        DESCRIPTION
                "Sets the administrative state of the SFCS switching
                 services for this SFCS module.  This controls the
                 SFCS state at a module level.  Regardless of the
                 per-interface state of each SFCS switching interface
                 and the state of active connections, writing the value
                 disabled(2) will cause the SFCS to immediately
                 shutdown.  A gracefull shutdown will be attempted.
                            enabled(1)     --  startup the SFCS
                            disabled(2)    --  shutdown the SFCS
                            other(3)       --  none of the following"
        ::= { sfcsConfigEntry 2 }

sfcsConfigAdminReset            OBJECT-TYPE
        SYNTAX  INTEGER {
                        other(1),             --  none of the following
                        reset(2)              --  force a reset
                }
        ACCESS  read-write
        STATUS  mandatory
        DESCRIPTION
                "Resets this SFCS module. Writing a value of
                 reset(2) will force a soft restart of the SFCS
                 without any graceful shutdown.  Any active
                 connections or services will be interrupted.
                        other(1)       --  none of the following
                        reset(2)       --  force a reset"
        ::= { sfcsConfigEntry 3 }

sfcsConfigOperStatus            OBJECT-TYPE
        SYNTAX  INTEGER {
                        enabled(1),           --  running
                        disabled(2),          --  not running
                        other(3),             --  none of the following
                        pending-disable(4),   --  shut-down in progress
                        pending-enable(5),    --  start-up in progress
                        invalid-config(6)     --  not running,invalid config
                }
        ACCESS  read-only
        STATUS  mandatory
        DESCRIPTION
                "Indicates the current operating condition of the SFCS
                 module.
                        enabled(1)           --  running
                        disabled(2)          --  not running
                        other(3)             --  none of the following
                        pending-disable(4)   --  shut-down in progress
                        pending-enable(5)    --  start-up in progress
                        invalid-config(6)    --  not running,invalid config"
        ::= { sfcsConfigEntry 4 }
            
sfcsConfigOperTime              OBJECT-TYPE
        SYNTAX  TimeTicks
        ACCESS  read-only
        STATUS  mandatory
        DESCRIPTION
                "Indicates the amount of time (# of time ticks) that this
                 SFCS module has been in its current operational state."
        ::= { sfcsConfigEntry 5 }

sfcsConfigLastChange            OBJECT-TYPE
        SYNTAX  TimeTicks
        ACCESS  read-only
        STATUS  mandatory
        DESCRIPTION
                "Indicates the last time a change was made to the
                 configuration entry for this SFCS switch module."
        ::= { sfcsConfigEntry 6 }

sfcsConfigVersion               OBJECT-TYPE
        SYNTAX  INTEGER
        ACCESS  read-only
        STATUS  mandatory
        DESCRIPTION
                "Indicates the current revision level of the SFCS MIB
                 for this switch module expressed as an integer."
        ::= { sfcsConfigEntry 7 }

sfcsConfigMibRev                OBJECT-TYPE
        SYNTAX  DisplayString
        ACCESS  read-only
        STATUS  mandatory
        DESCRIPTION
                "Indicates in textual format the current revision level
                 of the Cabletron SFCS MIB for this switch module."
        ::= { sfcsConfigEntry 8 }

sfcsConfigSwitchHostPort                OBJECT-TYPE
        SYNTAX  INTEGER
        ACCESS  read-only
        STATUS  mandatory
        DESCRIPTION
                "Indicates the switch port that is attached to the host."
        ::= { sfcsConfigEntry 9 }

sfcsConfigHostCtrlATMAddr       OBJECT-TYPE
        SYNTAX  OCTET STRING
        ACCESS  read-only
        STATUS  mandatory
        DESCRIPTION
                "Indicates the ATM address of the host. (SAR)"
        ::= { sfcsConfigEntry 10 }

sfcsConfigSwitchCapacity        OBJECT-TYPE
        SYNTAX  INTEGER
        ACCESS  read-only
        STATUS  mandatory
        DESCRIPTION
                "Indicates the front panel bandwidth based on the hardware
		 that is currently installed, in Mbps.
                 (number of ports and the port type)"
        ::= { sfcsConfigEntry 11 }

sfcsConfigMaxCnxEntries         OBJECT-TYPE
        SYNTAX  INTEGER
        ACCESS  read-only
        STATUS  mandatory
        DESCRIPTION
                "Indicates the maximum number of connections which
                 can be established on this switch module."
        ::= { sfcsConfigEntry 12 }

sfcsConfigMaxStatEntries        OBJECT-TYPE
        SYNTAX  INTEGER
        ACCESS  read-only
        STATUS  mandatory
        DESCRIPTION
                "Indicates the maximum number of stats enabled VCs for this
                 switch module."
        ::= { sfcsConfigEntry 13 }

sfcsConfigMaxUpcEntries         OBJECT-TYPE
        SYNTAX  INTEGER
        ACCESS  read-only
        STATUS  mandatory
        DESCRIPTION
                "Indicates the maximum number of UPC enabled VCs for this
                 switch module."
        ::= { sfcsConfigEntry 14 }

sfcsConfigNumberANIMS           OBJECT-TYPE
        SYNTAX  INTEGER
        ACCESS  read-only
        STATUS  mandatory
        DESCRIPTION
                "Indicates the number of ATM Network Inteface Modules
                 currently configured on this switch module."
        ::= { sfcsConfigEntry 15 }

sfcsConfigBwCapability          OBJECT-TYPE
        SYNTAX  INTEGER
        ACCESS  read-only
        STATUS  mandatory
        DESCRIPTION
                "Indicates the total bandwidth capability for this 
		 switch engine expressed in Mbps."
        ::= { sfcsConfigEntry 16 }


sfcsConfigMasterClock1Source         OBJECT-TYPE

        SYNTAX  INTEGER{
                   anim-one-clk(1),
                   anim-two-clk(2),
                   anim-three-clk(3),
                   anim-four-clk(4),
                   backplane-one(5),
                   backplane-two(6)
                       } 
        ACCESS  read-write
        STATUS  mandatory
        DESCRIPTION
                "Indicates the clocking source for MasterClock1 on each board.
                 The write will fail if it is also currently the source of the 
                 backplane. The write will also fail if the board does not support
                 backplane clocking."

        ::= { sfcsConfigEntry 17 }

sfcsConfigMasterClock2Source         OBJECT-TYPE

        SYNTAX  INTEGER{
                   anim-one-clk(1),
                   anim-two-clk(2),
                   anim-three-clk(3),
                   anim-four-clk(4),
                   backplane-one(5),
                   backplane-two(6)
                       }
        ACCESS  read-write
        STATUS  mandatory
        DESCRIPTION
                "Indicates the clocking source for MasterClock2 on each board.
                 The write will fail if it is also currently the source of the 
                 backplane. The write will also fail if the board does not support
                 backplane clocking."

        ::= { sfcsConfigEntry 18 }


sfcsConfigMasterClock1Standby         OBJECT-TYPE
 
        SYNTAX  INTEGER{
                   anim-one-clk(1),
                   anim-two-clk(2),
                   anim-three-clk(3),
                   anim-four-clk(4),
                   backplane-one(5),
		   backplane-two(6),
                   none(7)
		       }
        ACCESS  read-write
        STATUS  mandatory
        DESCRIPTION
                "Indicates the clocking stand-by for MasterClock1 on each board.
                 The write will fail if it is also currently the source of the
                 backplane. The write will also fail if the board does not support
                 backplane clocking. If this value is none(7) and an interrupt on
		 the primary interface for MasterClock1 is received. MasterClock1 
		 will switch to that anims local clock."
 
        ::= { sfcsConfigEntry 19 }

sfcsConfigMasterClock2Standby         OBJECT-TYPE
 
        SYNTAX  INTEGER{
                   anim-one-clk(1),
                   anim-two-clk(2),
                   anim-three-clk(3),
                   anim-four-clk(4),
                   backplane-one(5),
                   backplane-two(6),
                   none(7)
                       }
        ACCESS  read-write
        STATUS  mandatory
        DESCRIPTION
                "Indicates the clocking stand-by for MasterClock2 on each board.
                 The write will fail if it is also currently the source of the
                 backplane. The write will also fail if the board does not support
                 backplane clocking. If this value is none(7) and an interrupt on
                 the primary interface for MasterClock1 is received. MasterClock1 
                 will switch to that anims local clock."
 
        ::= { sfcsConfigEntry 20 }
 
--  SFCS Status Table
--  This table contains the objects that pertain to the operational status
--  of a single SFCS module.

sfcsStatusTable                 OBJECT-TYPE
        SYNTAX  SEQUENCE OF SfcsStatusEntry
        ACCESS  not-accessible
        STATUS  mandatory
        DESCRIPTION
                "This table contains the status information for each SFCS
                 switch module."
        ::= { sfcsStatus 1 }

sfcsStatusEntry                 OBJECT-TYPE
        SYNTAX  SfcsStatusEntry
        ACCESS  not-accessible
        STATUS  mandatory
        DESCRIPTION
                "Each entry contains the SFCS statistics for the SFCS
                instance."
        INDEX   { sfcsStatusSlotIndex }
        ::= { sfcsStatusTable 1 }

SfcsStatusEntry ::=
        SEQUENCE {
                sfcsStatusSlotIndex             INTEGER,
                sfcsStatusTdmCellCount          OCTET STRING,
                sfcsStatusTdmUtilization        INTEGER,
                sfcsStatusCurrCnxEntries        INTEGER,
                sfcsStatusCurrUPCEntries        INTEGER,
                sfcsStatusCurrStatsEntries      INTEGER,
                sfcsStatusCurrCtmAgent          INTEGER
	        }
sfcsStatusSlotIndex             OBJECT-TYPE
        SYNTAX  INTEGER
        ACCESS  read-only
        STATUS  mandatory
        DESCRIPTION
                "The primary index to the SFCS switch table.  This
                 identifies the chassis slot number for this SFCS module."
        ::= { sfcsStatusEntry 1 }
        
sfcsStatusTdmCellCount          OBJECT-TYPE
        SYNTAX  OCTET STRING
        ACCESS  read-only
        STATUS  mandatory
        DESCRIPTION
                "Indicates the total number of cells being transfered
                 across the TDM for this switch module."
        ::= { sfcsStatusEntry 2 }

sfcsStatusTdmUtilization        OBJECT-TYPE
        SYNTAX  INTEGER (0..100)
        ACCESS  read-only
        STATUS  mandatory
        DESCRIPTION
                "Indicates the percentage TDM utilization for this switch
                 module."
        ::= { sfcsStatusEntry 3 }

sfcsStatusCurrCnxEntries        OBJECT-TYPE
        SYNTAX  INTEGER
        ACCESS  read-only
        STATUS  mandatory
        DESCRIPTION
                "Indicates the current number of connection entries for
                 this switch module."
        ::= { sfcsStatusEntry 4 }

sfcsStatusCurrUPCEntries        OBJECT-TYPE
        SYNTAX  INTEGER
        ACCESS  read-only
        STATUS  mandatory
        DESCRIPTION
                "Indicates the current number of UPC entries for this
                 switch module."
        ::= { sfcsStatusEntry 5 }

sfcsStatusCurrStatsEntries      OBJECT-TYPE
        SYNTAX  INTEGER
        ACCESS  read-only
        STATUS  mandatory
        DESCRIPTION
                "Indicates the current number of statistics entries for
                 this switch module."
        ::= { sfcsStatusEntry 6 }

sfcsStatusCurrCtmAgent          OBJECT-TYPE
        SYNTAX  INTEGER
        ACCESS  read-only
        STATUS  mandatory
        DESCRIPTION
                "Indicates the current board number of
                 the ctm agent for this switch module."
        ::= { sfcsStatusEntry 7 }
 
--  SFCS UPC Engine Table

--  This table contains the objects that pertain to UPC Engine
--  monitoring and statistics of a single instance, slot number indexed
--  SFCS module.

sfcsUPCTable                    OBJECT-TYPE
        SYNTAX  SEQUENCE OF SfcsUPCEntry
        ACCESS  not-accessible
        STATUS  mandatory
        DESCRIPTION
                "This table contains the Usage Parameter Control info
                 for this SFCS module."
        ::= { sfcsUPCEngine 1 }

sfcsUPCEntry                    OBJECT-TYPE
        SYNTAX  SfcsUPCEntry
        ACCESS  not-accessible
        STATUS  mandatory
        DESCRIPTION
                "Each entry contains the UPC data for the SFCS instance."
        INDEX   { sfcsUPCSlotIndex }
        ::= { sfcsUPCTable 1 }

SfcsUPCEntry ::=
        SEQUENCE {
                sfcsUPCSlotIndex                INTEGER,
                sfcsUPCAdminStatus              INTEGER,
                sfcsUPCOperStatus               INTEGER,
                sfcsUPCReset                    INTEGER,
                sfcsUPCOperTime                 TimeTicks
       		}
sfcsUPCSlotIndex                OBJECT-TYPE
        SYNTAX  INTEGER
        ACCESS  read-only
        STATUS  mandatory
        DESCRIPTION
                "The primary index to the SFCS switch table.  This
                 identifies the slot number for this SFCS module."
        ::= { sfcsUPCEntry 1 }

sfcsUPCAdminStatus              OBJECT-TYPE
        SYNTAX          INTEGER {
                            enabled(1),
                            disabled(2),
                            other(3)
                        }
        ACCESS          read-write
        STATUS          mandatory
        DESCRIPTION
                "Sets the administrative state of the SFCS module's
                 UPC engine.
                            enabled(1)
                            disabled(2)
                            other(3)"
        ::= { sfcsUPCEntry 2 }

sfcsUPCOperStatus               OBJECT-TYPE
        SYNTAX          INTEGER {
                            enabled(1),
                            disabled(2),
                            other(3)
                        }
        ACCESS          read-only
        STATUS          mandatory
        DESCRIPTION
                "Indicates the operational state of the SFCS module's
                 UPC engine."
        ::= { sfcsUPCEntry 3 }

sfcsUPCReset                    OBJECT-TYPE
        SYNTAX          INTEGER {
                            other(1),
                            reset(2)
                        }
        ACCESS          read-write
        STATUS          mandatory
        DESCRIPTION
                "Resets the UPC engine for this SFCS module.
                            other(1)
                            reset(2)"
        ::= { sfcsUPCEntry 4 }

sfcsUPCOperTime                 OBJECT-TYPE
        SYNTAX          TimeTicks
        ACCESS          read-only
        STATUS          mandatory
        DESCRIPTION
                "Indicates the amount of time (# of time ticks) that
                 the UPC engine has been active for this switch module."
        ::= { sfcsUPCEntry 5 }



--  SFCS Statistics Engine Table

--  This table contains the objects that pertain to Statistics Engine
--  for a single SFCS module.

sfcsStatsEngineTable            OBJECT-TYPE
        SYNTAX  SEQUENCE OF SfcsStatsEngineEntry
        ACCESS  not-accessible
        STATUS  mandatory
        DESCRIPTION
                "This table contains information for the Statistics engine
                 for a particular switch module."
        ::= { sfcsStatisticsEngine 1 }

sfcsStatsEngineEntry            OBJECT-TYPE
        SYNTAX  SfcsStatsEngineEntry
        ACCESS  not-accessible
        STATUS  mandatory
        DESCRIPTION
                "Each entry contains the statistics engine data for the
                 SFCS module."
        INDEX   { sfcsStatsEngineSlotIndex }
        ::= { sfcsStatsEngineTable 1 }

SfcsStatsEngineEntry ::=
        SEQUENCE {
                sfcsStatsEngineSlotIndex        INTEGER,
                sfcsStatsEngineAdminStatus      INTEGER,
                sfcsStatsEngineOperStatus       INTEGER,
                sfcsStatsEngineReset            INTEGER,
                sfcsStatsEngineOperTime         TimeTicks
        }

sfcsStatsEngineSlotIndex        OBJECT-TYPE
        SYNTAX  INTEGER
        ACCESS  read-only
        STATUS  mandatory
        DESCRIPTION
                "The primary index to the SFCS stats engine table.
                 This identifies the chassis slot number for this SFCS
                 module."
        ::= { sfcsStatsEngineEntry 1 }

sfcsStatsEngineAdminStatus      OBJECT-TYPE
        SYNTAX          INTEGER {
                            enabled(1),
                            disabled(2),
                            other(3)
                        }
        ACCESS          read-write
        STATUS          mandatory
        DESCRIPTION
                "Sets the administrative state of the SFCS switch
                 statistics engine.  Writing a value of enabled(1) causes
                 these counters to become active for this SFCS switch
                 instance.  Writing a value of disabled(2) causes
                 these counters to become inactive for this SFCS
                 module.
                            enabled(1)
                            disabled(2)
                            other(3)"
        ::= { sfcsStatsEngineEntry 2 }

sfcsStatsEngineOperStatus       OBJECT-TYPE
        SYNTAX          INTEGER {
                            enabled(1),
                            disabled(2),
                            other(3)
                        }
        ACCESS          read-only
        STATUS          mandatory
        DESCRIPTION
                "Indicates the operational state of the SFCS switch
                 statistics engine for this switch module.
                            enabled(1)
                            disabled(2)
                            other(3)"
        ::= { sfcsStatsEngineEntry 3 }

sfcsStatsEngineReset            OBJECT-TYPE
        SYNTAX          INTEGER {
                            other(1),
                            reset(2)
                        }
        ACCESS          read-write
        STATUS          mandatory
        DESCRIPTION
                "Resets the SFCS switch counters for this SFCS module.
                 Writing a value of reset(2) resets the SFCS switch
                 counters to 0 and causes sfcsStatsEngineOperTime
                 to also be reset to 0.
                            other(1)
                            reset(2)"
        ::= { sfcsStatsEngineEntry 4 }

sfcsStatsEngineOperTime OBJECT-TYPE
        SYNTAX          TimeTicks
        ACCESS          read-only
        STATUS          mandatory
        DESCRIPTION
                "Indicates the amount of time (# of time ticks) that
                 the SFCS switch statistics have been active for this
                 switch module."
        ::= { sfcsStatsEngineEntry 5 }


--  SFCS Packet Discard Engine Table

--  This table contains the objects that pertain to Packet Discard Engine
--  for a single SFCS module.

sfcsPacketDiscardEngineTable            OBJECT-TYPE
        SYNTAX  SEQUENCE OF SfcsPacketDiscardEngineEntry
        ACCESS  not-accessible
        STATUS  mandatory
        DESCRIPTION
                "This table contains information for the Packet Discard engine
                 for a particular switch module."
        ::= { sfcsPacketDiscardEngine 1 }

sfcsPacketDiscardEngineEntry            OBJECT-TYPE
        SYNTAX  SfcsPacketDiscardEngineEntry
        ACCESS  not-accessible
        STATUS  mandatory
        DESCRIPTION
                "Each entry contains the packet discard engine data for the
                 SFCS module."
        INDEX   { sfcsPacketDiscardEngineSlotIndex }
        ::= { sfcsPacketDiscardEngineTable 1 }

SfcsPacketDiscardEngineEntry ::=
        SEQUENCE {
                sfcsPacketDiscardEngineSlotIndex        INTEGER,
                sfcsPacketDiscardEngineAdminStatus      INTEGER,
                sfcsPacketDiscardEngineOperStatus       INTEGER,
                sfcsPacketDiscardEngineReset            INTEGER,
                sfcsPacketDiscardEngineEPDPercentage    INTEGER,
                sfcsPacketDiscardEngineOperTime         TimeTicks
        }

sfcsPacketDiscardEngineSlotIndex        OBJECT-TYPE
        SYNTAX  INTEGER
        ACCESS  read-only
        STATUS  mandatory
        DESCRIPTION
                "The primary index to the SFCS packet discard engine table.
                 This identifies the chassis slot number for this SFCS
                 module."
        ::= { sfcsPacketDiscardEngineEntry 1 }

sfcsPacketDiscardEngineAdminStatus      OBJECT-TYPE
        SYNTAX          INTEGER {
                            enabled(1),
                            disabled(2),
                            other(3)
                        }
        ACCESS          read-write
        STATUS          mandatory
        DESCRIPTION
                "Sets the administrative state of the SFCS switch
                 packet discard engine.  Writing a value of enabled(1) causes
                 these packet discard registers to become active for this SFCS switch
                 instance.  Writing a value of disabled(2) causes
                 these packet discard registers to become inactive for this SFCS
                 module.
                            enabled(1)
                            disabled(2)
                            other(3)"
        ::= { sfcsPacketDiscardEngineEntry 2 }

sfcsPacketDiscardEngineOperStatus       OBJECT-TYPE
        SYNTAX          INTEGER {
                            enabled(1),
                            disabled(2),
                            other(3)
                        }
        ACCESS          read-only
        STATUS          mandatory
        DESCRIPTION
                "Indicates the operational state of the SFCS switch
                 packet discard engine for this switch module.
                            enabled(1)
                            disabled(2)
                            other(3)"
        ::= { sfcsPacketDiscardEngineEntry 3 }

sfcsPacketDiscardEngineReset            OBJECT-TYPE
        SYNTAX          INTEGER {
                            other(1),
                            reset(2)
                        }
        ACCESS          read-write
        STATUS          mandatory
        DESCRIPTION
                "Resets the SFCS switch registers for this SFCS module.
                 Writing a value of reset(2) resets the SFCS switch packet
                 discard registers to 0 and causes sfcsPacketDiscardEngineOperTime
                 to also be reset to 0.
                            other(1)
                            reset(2)"
        ::= { sfcsPacketDiscardEngineEntry 4 }

sfcsPacketDiscardEngineEPDPercentage            OBJECT-TYPE
        SYNTAX          INTEGER (0..100)
        ACCESS          read-write
        STATUS          mandatory
        DESCRIPTION
                "Sets the Early Packet Discard threshold percentage for every
                 port, and every priority on a single blade."
        ::= { sfcsPacketDiscardEngineEntry 5 }

sfcsPacketDiscardEngineOperTime OBJECT-TYPE
        SYNTAX          TimeTicks
        ACCESS          read-only
        STATUS          mandatory
        DESCRIPTION
                "Indicates the amount of time (# of time ticks) that
                 the SFCS switch packet discard engine has been active for this
                 switch module."
        ::= { sfcsPacketDiscardEngineEntry 6 }


--  SFCS Switching ANIM Group
--  This group contains the managed objects used to setup and
--  configure the SFCS ANIMS.  This group contains two sub-groups:
--  configuration status and statistics.


--  SFCS ANIM Configuration Status Table
--  This table contains the managed objects used to set-up and configure
--  each SFCS ANIM.

sfcsANIMConfigTable     OBJECT-TYPE
        SYNTAX  SEQUENCE OF SfcsANIMConfigEntry
        ACCESS  not-accessible
        STATUS  mandatory
        DESCRIPTION
                "This table contains the configuration information for
                 each SFCS ANIM instance."
        ::= { sfcsANIMConfig 1 }

sfcsANIMConfigEntry    OBJECT-TYPE
        SYNTAX  SfcsANIMConfigEntry
        ACCESS  not-accessible
        STATUS  mandatory
        DESCRIPTION
                "Each entry contains the SFCS config info for the SFCS
                instance."
        INDEX   { sfcsANIMConfigANIMIndex }
        ::= { sfcsANIMConfigTable 1 }

SfcsANIMConfigEntry ::=
        SEQUENCE {
                sfcsANIMConfigANIMIndex         INTEGER,
                sfcsANIMConfigAdminStatus       INTEGER,
                sfcsANIMConfigOperStatus        INTEGER,
                sfcsANIMConfigANIMType          OBJECT IDENTIFIER,
                sfcsANIMConfigNumInterfaces     INTEGER,
                sfcsANIMConfigLineRate          INTEGER,
                sfcsANIMConfigToMB              INTEGER,
                sfcsANIMConfigMBClockSelect     INTEGER

        }

sfcsANIMConfigANIMIndex OBJECT-TYPE
        SYNTAX  INTEGER
        ACCESS  read-only
        STATUS  mandatory
        DESCRIPTION
                "This index specifies which ANIM we are dealing
                 with. This reference is in the same format as
                 MIB II's InterfaceIndex."
        ::= { sfcsANIMConfigEntry 1 }

sfcsANIMConfigAdminStatus       OBJECT-TYPE
        SYNTAX          INTEGER {
                            enabled(1),
                            disabled(2),
                            other(3)
                        }
        ACCESS          read-write
        STATUS          mandatory
        DESCRIPTION
                "Sets the administrative state of the SFCS switch
                 ANIM.
                            enabled(1)
                            disabled(2)
                            other(3)"
        ::= { sfcsANIMConfigEntry 2 }

sfcsANIMConfigOperStatus     OBJECT-TYPE
        SYNTAX          INTEGER {
                            enabled(1),
                            disabled(2),
                            other(3)
                        }
        ACCESS          read-only
        STATUS          mandatory
        DESCRIPTION
                "Indicates the operational state of the SFCS switch
                 ANIM for this SFCS ANIM instance.
                            enabled(1)
                            disabled(2)
                            other(3)"
        ::= { sfcsANIMConfigEntry 3 }

sfcsANIMConfigANIMType     OBJECT-TYPE
        SYNTAX         OBJECT IDENTIFIER 
        ACCESS  read-only
        STATUS  mandatory
        DESCRIPTION
                "Indicates the type of physical interface for this
                 ANIM. The types are described in ctron.oids"
        ::= { sfcsANIMConfigEntry 4 }
        
sfcsANIMConfigNumInterfaces     OBJECT-TYPE
        SYNTAX  INTEGER
        ACCESS  read-only
        STATUS  mandatory
        DESCRIPTION
                "Indicates the number of operational interfaces for
                 this ANIM."
        ::= { sfcsANIMConfigEntry 5 }

sfcsANIMConfigLineRate          OBJECT-TYPE
        SYNTAX  INTEGER
        ACCESS  read-only
        STATUS  mandatory
        DESCRIPTION
                "Indicates the line rate per port for this ANIM in
                 Mbps."
        ::= { sfcsANIMConfigEntry 6 }


sfcsANIMConfigToMB          OBJECT-TYPE
        SYNTAX          INTEGER {
                            local-anim-clock(1),
                            port-one-clock(2),
                            port-two-clock(3),
                            port-three-clock(4),
                            port-four-clock(5)
                        }
        ACCESS  read-write
        STATUS  mandatory
        DESCRIPTION
                "This is the ANIM clock source to board."
        ::= { sfcsANIMConfigEntry 7 }

sfcsANIMConfigMBClockSelect          OBJECT-TYPE
        SYNTAX  INTEGER {
                    master-clk-one(1),
                    master-clk-two(2)
                    }
        ACCESS  read-write
        STATUS  mandatory
        DESCRIPTION
                "This indicates the ANIM clock source."
        ::= { sfcsANIMConfigEntry 8 }




--  SFCS ANIM Stats Tables
--  This table contains the managed objects used to keep track of transmit
--  and receive counts and bandwidth for each SFCS ANIM.


sfcsANIMStatsTable     OBJECT-TYPE
        SYNTAX  SEQUENCE OF SfcsANIMStatsEntry
        ACCESS  not-accessible
        STATUS  mandatory
        DESCRIPTION
                "This table contains the statistics information for
                 each SFCS ANIM instance."
        ::= { sfcsANIMStatistics 1 }

sfcsANIMStatsEntry    OBJECT-TYPE
        SYNTAX  SfcsANIMStatsEntry
        ACCESS  not-accessible
        STATUS  mandatory
        DESCRIPTION
                "Each entry contains the SFCS statistics for the SFCS
                instance."
        INDEX   { sfcsANIMStatsANIMIndex }
        ::= { sfcsANIMStatsTable 1 }

SfcsANIMStatsEntry ::=
        SEQUENCE {
                sfcsANIMStatsANIMIndex          INTEGER,
                sfcsANIMStatsRxCells            OCTET STRING,
                sfcsANIMStatsTxCells            OCTET STRING
        }
        
sfcsANIMStatsANIMIndex          OBJECT-TYPE
        SYNTAX  INTEGER
        ACCESS  read-only
        STATUS  mandatory
        DESCRIPTION
                "The primary index which specifies which ANIM instance
                 we are dealing with.  This index is formatted like
                 MIB II's Interface Index."
        ::= { sfcsANIMStatsEntry 1 }

sfcsANIMStatsRxCells            OBJECT-TYPE
        SYNTAX  OCTET STRING
        ACCESS  read-only
        STATUS  mandatory
        DESCRIPTION
                "Indicates the number of cells received from this
                 ANIM's interfaces."
        ::= { sfcsANIMStatsEntry 2 }

sfcsANIMStatsTxCells            OBJECT-TYPE
        SYNTAX  OCTET STRING
        ACCESS  read-only
        STATUS  mandatory
        DESCRIPTION
                "Indicates the number of cells transmitted from
                 this ANIM's interfaces."
        ::= { sfcsANIMStatsEntry 3 }

--  SFCS ANIM Pic Table
--  This table contains the managed objects used to keep track of
--  the PIC info for each SFCS ANIM.
 
 
sfcsANIMPicTable     OBJECT-TYPE
        SYNTAX  SEQUENCE OF SfcsANIMPicEntry
        ACCESS  not-accessible
        STATUS  mandatory 
        DESCRIPTION
                "This table contains the PIC information for
                 each SFCS ANIM instance."
        ::= { sfcsANIMPic 1 }
 
sfcsANIMPicEntry    OBJECT-TYPE
        SYNTAX  SfcsANIMPicEntry
        ACCESS  not-accessible
        STATUS  mandatory 
        DESCRIPTION
                "Each entry contains the SFCS PIC info for the SFCS
                instance."
        INDEX   { sfcsANIMPicIndex }
        ::= { sfcsANIMPicTable 1 }
 
SfcsANIMPicEntry ::=
        SEQUENCE {
                sfcsANIMPicSlot				INTEGER,
                sfcsANIMPicIndex       			INTEGER,
                sfcsANIMPicLocation             	OBJECT IDENTIFIER,
                sfcsANIMPicStatus			INTEGER,
                sfcsANIMPicVersion			DisplayString,
                sfcsANIMPicModuleType           	OBJECT IDENTIFIER,
                sfcsANIMPicMfgPN                	DisplayString,
                sfcsANIMPicMfgSN                	DisplayString,
                sfcsANIMPicMfgPartNumb          	DisplayString,
                sfcsANIMPicMfgSerialNumb        	DisplayString,
                sfcsANIMPicMfgReworkLocation    	DisplayString,
                sfcsANIMPicMfgMfgLocation       	DisplayString,
                sfcsANIMPicMfgDateCode          	DisplayString,
                sfcsANIMPicMfgRevisionCode      	DisplayString,
                sfcsANIMPicTLPN                 	DisplayString,
                sfcsANIMPicTLSN                 	DisplayString,
                sfcsANIMPicTLPartNumb           	DisplayString,
                sfcsANIMPicTLSerialNumb         	DisplayString,
                sfcsANIMPicTLReworkLocation             DisplayString,	
                sfcsANIMPicTLMfgLocation        	DisplayString,
                sfcsANIMPicTLDateCode           	DisplayString,
                sfcsANIMPicTLRevisionCode       	DisplayString,
                sfcsANIMPicTLPcbRevision        	DisplayString,
                sfcsANIMPicMacAddr              	OCTET STRING,
                sfcsANIMPicNumbRsvdAddrs        	INTEGER,
                sfcsANIMPicBoardLevelRevision   	DisplayString,
                sfcsANIMPicModuleTypeString     	DisplayString,
                sfcsANIMPicDcDcConverterType    	DisplayString,
                sfcsANIMPicDcDcConverterInputPower      DisplayString,
                sfcsANIMPicSmb1PromVersion      	DisplayString
        }
      
sfcsANIMPicSlot		  	OBJECT-TYPE
        SYNTAX  INTEGER
        ACCESS  read-only
        STATUS  mandatory
        DESCRIPTION
                "Specific slot which the module that realizes this PIC
                resides.  If the PIC is associated with the chassis
                and not a specific module then this value will be 0."
        ::= { sfcsANIMPicEntry 1 }
 
sfcsANIMPicIndex               OBJECT-TYPE
        SYNTAX  INTEGER
        ACCESS  read-only
        STATUS  mandatory
        DESCRIPTION
                "Uniquely identifies the instance of a PIC in a particular
                 slot."
        ::= { sfcsANIMPicEntry 2 }
 
sfcsANIMPicLocation           OBJECT-TYPE
        SYNTAX  OBJECT IDENTIFIER
        ACCESS  read-only
        STATUS  mandatory
        DESCRIPTION
                "Defines location of the PIC chip.  This takes on any of
                the encoding values defined below for backplane, module,
                daughter board, brim."
        ::= { sfcsANIMPicEntry 3 }
 
sfcsANIMPicStatus             OBJECT-TYPE
        SYNTAX  INTEGER {
                        other(1),
                        present(2),
                        notPresent(3),
                        checkSum(4),
                        error(5),
                        limited(6)
                }
        ACCESS  read-only
        STATUS  mandatory
        DESCRIPTION
                "Provides the status of the specific PIC chip.  the values
                are defined as follows:
                        other(1) - firmware can not determine status
                        present(2) - PIC seems to be functional
                        notPresent(3) - PIC not found but expected
                        checkSum(4) - A check sum error occured
                        error(5) - An undefined error condition exists.
                        limited(6) - A limited PIC implementation only
                                type code information is present."
        ::= { sfcsANIMPicEntry 4 }
 
sfcsANIMPicVersion            OBJECT-TYPE
        SYNTAX  DisplayString (SIZE(2))
        ACCESS  read-only
        STATUS  mandatory
        DESCRIPTION
                "Reflects the version of the PIC implementation that this
                PIC conforms to.  This has the format x.yy . If non-existent,
                this object will be set to all blanks(ascii 32)."
        ::= { sfcsANIMPicEntry 5 }
 
sfcsANIMPicModuleType		 OBJECT-TYPE
        SYNTAX  OBJECT IDENTIFIER
        ACCESS  read-only
        STATUS  mandatory
        DESCRIPTION
                "Defines the standard module type value as defined in
                ctron-oids."
        ::= { sfcsANIMPicEntry 6 }
 
sfcsANIMPicMfgPN      OBJECT-TYPE
        SYNTAX  DisplayString   (SIZE(9))
        ACCESS  read-only
        STATUS  mandatory
        DESCRIPTION
                "Describes the manufacturing level part number of the module
                associated with this PIC.  This information is encoded as
                follows:
                        7 Characters    Part Number
                        2 Characters    Rework Location.
                If any field of this object is non-existent, it will be set
                to all blanks(ascii 32)."
        ::= { sfcsANIMPicEntry 7 }
 
sfcsANIMPicMfgSN      OBJECT-TYPE
        SYNTAX  DisplayString (SIZE(12))
        ACCESS  read-only
        STATUS  mandatory
        DESCRIPTION
                "Describes the manufacturing level serial number of the module
                associated with this PIC.  This information is encoded as
                follows:
                        3 bytes - Date code (year/week)
                        4 bytes - Serial number
                        2 bytes - Manufacture location
                        3 bytes - Board level revision
                If any field of this object is non-existent, it will be
                set to all blanks(ascii 32)."
        ::= { sfcsANIMPicEntry 8 }
 
sfcsANIMPicMfgPartNumb        OBJECT-TYPE
        SYNTAX  DisplayString (SIZE(7))
        ACCESS  read-only
        STATUS  mandatory
        DESCRIPTION
                "This object presents the part number portion of the
                ctPicMfgPN object.  This object contains the same information
                however in a more human readable format.  If non-existent,
                this object will be set to all blanks(ascii 32)."
        ::= { sfcsANIMPicEntry 9 }
 
sfcsANIMPicMfgSerialNumb      OBJECT-TYPE
        SYNTAX  DisplayString (SIZE(4))
        ACCESS  read-only
        STATUS  mandatory
        DESCRIPTION
                "This object presents the serial number portion of the
                ctPicMfgSN object.  This object contains the same information
                however in a more human readable format.  If non-existent,
                this object will be set to all blanks(ascii 32)."
        ::= { sfcsANIMPicEntry 10 }
 
sfcsANIMPicMfgReworkLocation  OBJECT-TYPE
        SYNTAX  DisplayString (SIZE(2))
        ACCESS  read-only
        STATUS  mandatory
        DESCRIPTION
                "The 2 character code that defines the location this
                module was last reworked. This object contains the same
                information as presented in ctPicMfgPN object however
                in a more human readable format.  If non-existent, this
                object will be set to all blanks(ascii 32)."
        ::= { sfcsANIMPicEntry 11 }
 
sfcsANIMPicMfgMfgLocation  OBJECT-TYPE
        SYNTAX  DisplayString (SIZE(2))
        ACCESS  read-only
        STATUS  mandatory
        DESCRIPTION
                "The two character code that defines the location
                this module was manufactured at. This object contains the same
                information as presented in ctPicMfgSN object however
                in a more human readable format.  If non-existent, this object
                will be set to all blanks(ascii 32)."
        ::= { sfcsANIMPicEntry 12 }
 
sfcsANIMPicMfgDateCode OBJECT-TYPE
        SYNTAX  DisplayString (SIZE(3))
        ACCESS  read-only
        STATUS  mandatory
        DESCRIPTION
                "The 3 byte date code field when this module was last
                reworked.  This is in year/week format. This object
                contains the same information as presented in ctPicMfgSN
                object however in a more human readable format.  If
                non-existent, this object will be set to all blanks(ascii 32)."
        ::= { sfcsANIMPicEntry 13 }
 
sfcsANIMPicMfgRevisionCode  OBJECT-TYPE
        SYNTAX  DisplayString (SIZE(3))
        ACCESS  read-only
        STATUS  mandatory
        DESCRIPTION
                "The 3 character board level revision code field of this
                module.  This object contains the same information as
                presented in ctPicMfgSN object however in a more human
                readable format.  If non-existent, this object will be set
                to all blanks (ascii 32)."
        ::= { sfcsANIMPicEntry 14 }
 
sfcsANIMPicTLPN               OBJECT-TYPE
        SYNTAX  DisplayString   (SIZE(9))
        ACCESS  read-only
        STATUS  mandatory
        DESCRIPTION
                "Describes the top level part number of the module associated
                with this PIC.  This information is encoded as follows:
                        7 Characters    Part Number
                        2 Characters    Rework Location.
                If any field of this object is non-existent, it will be set
                to all blanks(ascii 32)."
        ::= { sfcsANIMPicEntry 15 }
 
sfcsANIMPicTLSN       OBJECT-TYPE
        SYNTAX  DisplayString (SIZE(12))
        ACCESS  read-only
        STATUS  mandatory
        DESCRIPTION
                "Describes the top level serial number of the module
                associated with this PIC.  This information is encoded
                as follows:
                        3 bytes - Date code (year/week)
                        4 bytes - Serial number
                        2 bytes - Manufacture location
                        3 bytes - Top level revision
                If any field of this object is non-existent, it will be
                set to all blanks(ascii 32)."
        ::= { sfcsANIMPicEntry 16 }
 
sfcsANIMPicTLPartNumb OBJECT-TYPE
        SYNTAX  DisplayString (SIZE(7))
        ACCESS  read-only
        STATUS  mandatory
        DESCRIPTION
                "This object presents the part number portion of the
                ctPicTLPN object.  This object contains the same information
                however in a more human readable format.  If non-existent,
                this object will be set to all blanks(ascii 32)."
        ::= { sfcsANIMPicEntry 17 }
 
sfcsANIMPicTLSerialNumb       OBJECT-TYPE
        SYNTAX  DisplayString (SIZE(4))
        ACCESS  read-only
        STATUS  mandatory
        DESCRIPTION
                "This object presents the serial number portion of the
                ctPicTLSN object.  This object contains the same information
                however in a more human readable format.  If non-existent,
                this object will be set to all blanks(ascii 32)."
        ::= { sfcsANIMPicEntry 18 }
 
sfcsANIMPicTLReworkLocation  OBJECT-TYPE
        SYNTAX  DisplayString (SIZE(2))
        ACCESS  read-only
        STATUS  mandatory
        DESCRIPTION
                "The 2 character code that defines the location this
                module was last reworked. This object contains the same
                information as presented in ctPicTLPN object however
                in a more human readable format.  If non-existent, this
                object will be set to all blanks(ascii 32)."
        ::= { sfcsANIMPicEntry 19 }
 
sfcsANIMPicTLMfgLocation  OBJECT-TYPE
        SYNTAX  DisplayString (SIZE(2))
        ACCESS  read-only
        STATUS  mandatory
        DESCRIPTION
                "The two character code that defines the location
                this module was manufactured at. This object contains the same
                information as presented in ctPicTLSN object however
                in a more human readable format.  If non-existent, this object
                will be set to all blanks(ascii 32)."
        ::= { sfcsANIMPicEntry 20 }
 
sfcsANIMPicTLDateCode OBJECT-TYPE
        SYNTAX  DisplayString (SIZE(3))
        ACCESS  read-only
        STATUS  mandatory
        DESCRIPTION
                "The 3 byte date code field when this module was last
                reworked.  This is in year/week format. This object
                contains the same information as presented in ctPicTLSN
                object however in a more human readable format.  If
                non-existent, this object will be set to all blanks(ascii 32)."
        ::= { sfcsANIMPicEntry 21 }
 
sfcsANIMPicTLRevisionCode  OBJECT-TYPE
        SYNTAX  DisplayString (SIZE(3))
        ACCESS  read-only
        STATUS  mandatory
        DESCRIPTION
                "The 3 character top level revision code field of this module.
                This object contains the same information as presented in
                ctPicTLSN object however in a more human readable format.
                If non-existent, this object will be set to all blanks
                (ascii 32)."
        ::= { sfcsANIMPicEntry 22 }
 
sfcsANIMPicTLPcbRevision        OBJECT-TYPE
        SYNTAX  DisplayString (SIZE(8))
        ACCESS  read-only
        STATUS  mandatory
        DESCRIPTION
                "Defines the Cabletron revision of the art work for this
                module. If non-existent, this object will be set to all
                blanks(ascii 32)."
        ::= { sfcsANIMPicEntry 23 }
 
sfcsANIMPicMacAddr    OBJECT-TYPE
        SYNTAX  OCTET STRING (SIZE(0..6))
        ACCESS  read-only
        STATUS  mandatory
        DESCRIPTION
                "The base MAC address(ethernet format)assigned to the module.
                If this field is not used then it should have a value of a
                zero length string. If non-existent, this object will be set
                to all blanks(ascii 32)."
        ::= { sfcsANIMPicEntry 24 }
 
sfcsANIMPicNumbRsvdAddrs  OBJECT-TYPE
        SYNTAX  INTEGER
        ACCESS  read-only
        STATUS  mandatory
        DESCRIPTION
                "The number of reserved MAC addresses starting at the
                address as defined in ctPicMacAddr.  If no MAC addresses
                are reserved this object should have a value of 0."
        ::= { sfcsANIMPicEntry 25 }
 
sfcsANIMPicBoardLevelRevision      OBJECT-TYPE
        SYNTAX  DisplayString (SIZE(3))
        ACCESS  read-only
        STATUS  mandatory
        DESCRIPTION
                "Defines the Cabletron board level revision level code for
                this module.  If non-existent, this object will be set to
                blanks (ascii 32)."
        ::= { sfcsANIMPicEntry 26 }
 
sfcsANIMPicModuleTypeString   OBJECT-TYPE
        SYNTAX  DisplayString (SIZE(16))
        ACCESS  read-only
        STATUS  mandatory
        DESCRIPTION
                "Describes the module associated with this PIC in a
                human readable format.  If non-existent, this object
                will be set to blanks (ascii 32)."
        ::= { sfcsANIMPicEntry 27 }
 
sfcsANIMPicDcDcConverterType  OBJECT-TYPE
        SYNTAX  DisplayString (SIZE(12))
        ACCESS  read-only
        STATUS  mandatory
        DESCRIPTION
                "Describes the voltage of the installed DCDC Converter
                input and output lines.
                If the Module does not contain a DCDC Converter
                this object will be set to blanks (ascii 32)."
        ::= { sfcsANIMPicEntry 28 }
 
sfcsANIMPicDcDcConverterInputPower OBJECT-TYPE
        SYNTAX  DisplayString (SIZE(3))
        ACCESS  read-only
        STATUS  mandatory
        DESCRIPTION
                "Describes the maximum allowed input power
                for the DCDC input line.
                If the Module does not contain a DCDC Converter
                this object will be set to blanks (ascii 32)."
        ::= { sfcsANIMPicEntry 29 }

sfcsANIMPicSmb1PromVersion    OBJECT-TYPE
        SYNTAX  DisplayString (SIZE(8))
        ACCESS  read-only
        STATUS  mandatory
        DESCRIPTION
                "Describes the current version of the SMB1 prom.
                If the Module does not contain an SMB1 prom
                this object will be set to blanks (ascii 32)."
        ::= { sfcsANIMPicEntry 30 }
 

--  SFCS Switching Interface Group
--  This group contains the managed objects used to setup and
--  configure the SFCS interfaces for cell switching and statisics
--  monitoring.  This group contains two sub-groups:  configuration
--  and statistics.


--  SFCS Interface Configuration Table
--  This table contains the managed objects used to set-up and configure
--  each SFCS switching interface.

sfcsInterfaceConfigTable     OBJECT-TYPE
        SYNTAX  SEQUENCE OF SfcsInterfaceConfigEntry
        ACCESS  not-accessible
        STATUS  mandatory
        DESCRIPTION
                "This table contains the configuration information of each
                 configured SFCS switch interface.  If SFCS is not configured
                 on a port, than an entry will not exist."
        ::= { sfcsInterfaceConfig 1 }

sfcsInterfaceConfigEntry    OBJECT-TYPE
        SYNTAX  SfcsInterfaceConfigEntry
        ACCESS  not-accessible
        STATUS  mandatory
        DESCRIPTION
                "Each entry specifies the SFCS configuration for the SFCS
                 switch interface for which the entry exists."
        INDEX   { sfcsInterfaceConfigInterfaceIndex }
        ::= { sfcsInterfaceConfigTable 1 }

SfcsInterfaceConfigEntry ::=
        SEQUENCE {
                sfcsInterfaceConfigInterfaceIndex       INTEGER,
                sfcsInterfaceConfigType                 INTEGER,
                sfcsInterfacePeakBufferUseage           INTEGER,
                sfcsInterfaceConfigNumberOfQueues       INTEGER,
                sfcsInterfaceConfigSigStackID           INTEGER,
                sfcsInterfaceConfigClockingSource       INTEGER
        }

sfcsInterfaceConfigInterfaceIndex               OBJECT-TYPE
        SYNTAX  INTEGER
        ACCESS  read-only
        STATUS  mandatory
        DESCRIPTION
                "The index which specifies which interface we are
                 dealing with."
        ::= { sfcsInterfaceConfigEntry 1 }

sfcsInterfaceConfigType                         OBJECT-TYPE
        SYNTAX          INTEGER {
                            other(1),
                            access-port(2),
                            network-port(3),
                            host-mgmt-port(4),
                            host-ctl-port(5)
                        }
        ACCESS          read-only
        STATUS          deprecated
        DESCRIPTION
                "Sets the type of interface access attribute for the SFCS
                 interfaces.  Access ports allow single user or shared
                 access and perform statisics and control; network ports
                 are equivalent to trunk ports with no access control;
                 host management port indicates the (virtual) port to which
                 the (internal) management agent is attached; host control
                 port indicates the port to redirect non-management packets.
                            other(1)
                            access-port(2)
                            network-port(3)
                            host-mgmt-port(4)
                            host-ctl-port(5)"
        ::= { sfcsInterfaceConfigEntry 2 }

sfcsInterfacePeakBufferUseage                   OBJECT-TYPE
        SYNTAX          INTEGER (0..100)
        ACCESS          read-only
        STATUS          mandatory
        DESCRIPTION
                "An accumulated snap shot of the current peak queue depth
		 for the configured buffer queues.  This information is 
		 obtained from a read/reset register."
        ::= { sfcsInterfaceConfigEntry 3 }

sfcsInterfaceConfigNumberOfQueues               OBJECT-TYPE
        SYNTAX          INTEGER
        ACCESS          read-only
        STATUS          mandatory
        DESCRIPTION
                "Indicates the number of priority queues configured on this
                 interface."
        ::= { sfcsInterfaceConfigEntry 4 }

sfcsInterfaceConfigSigStackID                   OBJECT-TYPE
        SYNTAX          INTEGER
        ACCESS          read-only
        STATUS          mandatory
        DESCRIPTION
                "Indicates the user signalling stack ID for this interface."
        ::= { sfcsInterfaceConfigEntry 5 }

sfcsInterfaceConfigClockingSource       OBJECT-TYPE
        SYNTAX          INTEGER {
                            local-anim-clock(1),
                            mother-board-master-clock(2)
                        }
        ACCESS          read-write
        STATUS          mandatory
        DESCRIPTION
                "The interface clocking source."
        ::= { sfcsInterfaceConfigEntry 6 }


-- SFCS Switching Interface Statistics Tables
-- This table contains the objects that specify the packet and byte counters
-- for each configured SFCS switching interface.


sfcsInterfaceStatsTable                 OBJECT-TYPE
        SYNTAX          SEQUENCE OF SfcsInterfaceStatsEntry
        ACCESS          not-accessible
        STATUS          mandatory
        DESCRIPTION
                "This table contains the cell counts for each
                 SFCS switch interface."
        ::= { sfcsInterfaceStatistics 1 }

sfcsInterfaceStatsEntry                 OBJECT-TYPE
        SYNTAX          SfcsInterfaceStatsEntry
        ACCESS          not-accessible
        STATUS          mandatory
        DESCRIPTION
                "Specifies the SFCS cell counts for the SFCS
                 interface for which this entry exists."
        INDEX    { sfcsInterfaceStatsInterfaceIndex }
        ::= { sfcsInterfaceStatsTable 1 }

SfcsInterfaceStatsEntry ::=
        SEQUENCE {
                sfcsInterfaceStatsInterfaceIndex                INTEGER,
                sfcsInterfaceStatsRxErrors                      OCTET STRING,
                sfcsInterfaceStatsVPILookupInvalidErrors        OCTET STRING,
                sfcsInterfaceStatsRxCnxLookupInvalidErrors      OCTET STRING,
                sfcsInterfaceStatsRxCellCnt                     OCTET STRING,
                sfcsInterfaceStatsTxCellCnt                     OCTET STRING,
                sfcsInterfaceStatsOverflowDropCellCnt           OCTET STRING
        }

sfcsInterfaceStatsInterfaceIndex        OBJECT-TYPE
        SYNTAX  INTEGER
        ACCESS  read-only
        STATUS  mandatory
        DESCRIPTION
                "The index which specifies which interface we are
                 dealing with."
        ::= { sfcsInterfaceStatsEntry 1 }

sfcsInterfaceStatsRxErrors              OBJECT-TYPE
        SYNTAX          OCTET STRING
        ACCESS          read-only
        STATUS          mandatory
        DESCRIPTION
                "Indicates the number of receive path lookup
                 invalid and out of range errors."
        ::= { sfcsInterfaceStatsEntry 2 }

sfcsInterfaceStatsVPILookupInvalidErrors        OBJECT-TYPE
        SYNTAX          OCTET STRING
        ACCESS          read-only
        STATUS          mandatory
        DESCRIPTION
                "Indicates the number of VPI lookup invalid and out of
                 range errors."
        ::= { sfcsInterfaceStatsEntry 3 }

sfcsInterfaceStatsRxCnxLookupInvalidErrors      OBJECT-TYPE
        SYNTAX          OCTET STRING
        ACCESS          read-only
        STATUS          mandatory
        DESCRIPTION
                "Indicates the number of receive connection lookup
                 invalid errors."
        ::= { sfcsInterfaceStatsEntry 4 }

sfcsInterfaceStatsRxCellCnt              OBJECT-TYPE
        SYNTAX          OCTET STRING
        ACCESS          read-only
        STATUS          mandatory
        DESCRIPTION
                "Indicates the number of receive cells on
                 this interface."
        ::= { sfcsInterfaceStatsEntry 5 }
 

sfcsInterfaceStatsTxCellCnt              OBJECT-TYPE
        SYNTAX          OCTET STRING
        ACCESS          read-only
        STATUS          mandatory
        DESCRIPTION
                "Indicates the number of transmit cells
                 on this interface."
        ::= { sfcsInterfaceStatsEntry 6 }
 

sfcsInterfaceStatsOverflowDropCellCnt    OBJECT-TYPE
        SYNTAX          OCTET STRING
        ACCESS          read-only
        STATUS          mandatory
        DESCRIPTION
                "Indicates the number of cells that were
                 dropped due to queue overflows."
        ::= { sfcsInterfaceStatsEntry 7 }
 


-- SFCS Switch Queue Group
-- This group contains the managed objects for maintaining SFCS Queues.

--  SFCS Queue Configuration Table

sfcsQueueConfigTable     OBJECT-TYPE
        SYNTAX  SEQUENCE OF SfcsQueueConfigEntry
        ACCESS  not-accessible
        STATUS  mandatory
        DESCRIPTION
                "This table contains the configuration information for
                 all queues on the SFCS."
        ::= { sfcsQueueConfig 1 }

sfcsQueueConfigEntry    OBJECT-TYPE
        SYNTAX  SfcsQueueConfigEntry
        ACCESS  not-accessible
        STATUS  mandatory
        DESCRIPTION
                "Each entry specifies the queue information for the
                 SFCS switch for which the entry exists."
        INDEX   { sfcsQueueConfigInterfaceIndex, sfcsQueueConfigQueueIndex }
        ::= { sfcsQueueConfigTable 1 }

SfcsQueueConfigEntry ::=
        SEQUENCE {
                sfcsQueueConfigInterfaceIndex           INTEGER,
                sfcsQueueConfigQueueIndex               INTEGER,
                sfcsQueueConfigQueueSize                INTEGER,
                sfcsQueueConfigQueueBandwidth           INTEGER,
                sfcsQueueConfigClpDropThreshold         INTEGER,
                sfcsQueueConfigCongestionThreshold      INTEGER,
                sfcsQueueConfigEFCILowThreshold         INTEGER,
                sfcsQueueConfigRMThreshold              INTEGER,
                sfcsQueueConfigEPDThreshold             INTEGER
        }

sfcsQueueConfigInterfaceIndex           OBJECT-TYPE
        SYNTAX  INTEGER
        ACCESS  read-only
        STATUS  mandatory
        DESCRIPTION
                "The index which specifies which interface we are
                 dealing with."
        ::= { sfcsQueueConfigEntry 1 }

sfcsQueueConfigQueueIndex               OBJECT-TYPE
        SYNTAX  INTEGER
        ACCESS  read-only
        STATUS  mandatory
        DESCRIPTION
                "The index which specifies which transmit queue we
                 are dealing with."
        ::= { sfcsQueueConfigEntry 2 }

sfcsQueueConfigQueueSize                OBJECT-TYPE
        SYNTAX  INTEGER
        ACCESS  read-only
        STATUS  mandatory
        DESCRIPTION
                "Indicates the size of the transmit queue for this
                 queue instance."
        ::= { sfcsQueueConfigEntry 3 }

sfcsQueueConfigQueueBandwidth           OBJECT-TYPE
        SYNTAX  INTEGER (0..100)
        ACCESS  read-only
        STATUS  mandatory
        DESCRIPTION
                "Indicates the percentage of this interface's bandwidth
                 utilized by this particular queue."
        ::= { sfcsQueueConfigEntry 4 }

sfcsQueueConfigClpDropThreshold         OBJECT-TYPE
        SYNTAX  INTEGER (0..100)
        ACCESS  read-write
        STATUS  mandatory
        DESCRIPTION
                "Indicates the queue level to start dropping CLP=1
                 cells for this queue.  This level is expressed as
                 the percentage of this queue's size."
        ::= { sfcsQueueConfigEntry 5 }

sfcsQueueConfigCongestionThreshold      OBJECT-TYPE
        SYNTAX  INTEGER (0..100)
        ACCESS  read-write
        STATUS  mandatory
        DESCRIPTION
                "Indicates the level to consider this queue congested.
                 This level is expressed as the percentage of this
                 queue's size."
        ::= { sfcsQueueConfigEntry 6 }

sfcsQueueConfigEFCILowThreshold         OBJECT-TYPE
        SYNTAX  INTEGER (0..100)
        ACCESS  read-write
        STATUS  mandatory
        DESCRIPTION
                "Indicates the lower threshold used for EFCI for
                 this queue instance.  This level is expressed as
                 the percentage of this queue's size."
        ::= { sfcsQueueConfigEntry 7 }

sfcsQueueConfigRMThreshold              OBJECT-TYPE
        SYNTAX  INTEGER (0..100)
        ACCESS  read-write
        STATUS  mandatory
        DESCRIPTION
                "Indicates the remote management queue threshold expressed
                 as a percentage of the queue's size.  When this level is
                 hit, a management message is sent to the sender notifying it
                 to slow down."
        ::= { sfcsQueueConfigEntry 8 }

sfcsQueueConfigEPDThreshold              OBJECT-TYPE
        SYNTAX  INTEGER (0..100)
        ACCESS  read-write
        STATUS  mandatory
        DESCRIPTION
                "Indicates the Early Packet Discard threshold expressed
                 as a percentage of the queue's size.  When this level is
                 exceeded the Transmit ASIC starts to drop all cells entering
                 this queue."
        ::= { sfcsQueueConfigEntry 9 }


--  SFCS Queue Stats Table

sfcsQueueStatsTable     OBJECT-TYPE
        SYNTAX  SEQUENCE OF SfcsQueueStatsEntry
        ACCESS  not-accessible
        STATUS  mandatory
        DESCRIPTION
                "This table contains the statistics information for all
                 queues on the SFCS."
        ::= { sfcsQueueStatistics 1 }

sfcsQueueStatsEntry    OBJECT-TYPE
        SYNTAX  SfcsQueueStatsEntry
        ACCESS  not-accessible
        STATUS  mandatory
        DESCRIPTION
                "Each entry specifies the queue information for the
                 SFCS switch for which the entry exists."
        INDEX   { sfcsQueueStatsInterfaceIndex, sfcsQueueStatsQueue }
        ::= { sfcsQueueStatsTable 1 }

SfcsQueueStatsEntry ::=
        SEQUENCE {
                sfcsQueueStatsInterfaceIndex            INTEGER,
                sfcsQueueStatsQueue                     INTEGER,
                sfcsQueueStatsTxClpCellsDiscarded       OCTET STRING,
                sfcsQueueStatsTxCellsDropped            OCTET STRING,
                sfcsQueueStatsQueuePeakLevel            INTEGER,
                sfcsQueueStatsTxCellCnt                 OCTET STRING
        }

sfcsQueueStatsInterfaceIndex    OBJECT-TYPE
        SYNTAX  INTEGER
        ACCESS  read-only
        STATUS  mandatory
        DESCRIPTION
                "The index which specifies which interface we are
                 dealing with."
        ::= { sfcsQueueStatsEntry 1 }

sfcsQueueStatsQueue    OBJECT-TYPE
        SYNTAX  INTEGER
        ACCESS  read-only
        STATUS  mandatory
        DESCRIPTION
                "The index which specifies which queue we are
                 dealing with."
        ::= { sfcsQueueStatsEntry 2 }

sfcsQueueStatsTxClpCellsDiscarded    OBJECT-TYPE
        SYNTAX  OCTET STRING
        ACCESS  read-only
        STATUS  mandatory
        DESCRIPTION
                "Indicates the number of cells with CLP=1 that were
                 discarded for this queue instance."
        ::= { sfcsQueueStatsEntry 3 }

sfcsQueueStatsTxCellsDropped    OBJECT-TYPE
        SYNTAX  OCTET STRING
        ACCESS  read-only
        STATUS  mandatory
        DESCRIPTION
                "Indicates the number of cells that overflowed the
                 buffer for this queue instance."
        ::= { sfcsQueueStatsEntry 4 }

sfcsQueueStatsQueuePeakLevel    OBJECT-TYPE
        SYNTAX  INTEGER
        ACCESS  read-only
        STATUS  mandatory
        DESCRIPTION
                "Indicates the peak level since last read for this
                 queue instance."
        ::= { sfcsQueueStatsEntry 5 }

sfcsQueueStatsTxCellCnt         OBJECT-TYPE
        SYNTAX  OCTET STRING
        ACCESS  read-only
        STATUS  mandatory
        DESCRIPTION
                "Indicates the transmit cell count on a per queue basis.
                A value of zero indicates not available"
        ::= { sfcsQueueStatsEntry 6 }
 

-- The SFCS Connection Group

--  SFCS Switch Connection Config Table

sfcsCnxCfgTable     OBJECT-TYPE
        SYNTAX  SEQUENCE OF SfcsCnxCfgEntry
        ACCESS  not-accessible
        STATUS  mandatory
        DESCRIPTION
                "This table contains the connection configuration
                 information."
        ::= { sfcsConnectionConfig 1 }

sfcsCnxCfgEntry    OBJECT-TYPE
        SYNTAX  SfcsCnxCfgEntry
        ACCESS  not-accessible
        STATUS  mandatory
        DESCRIPTION
                "Each entry specifies the connection configuration
                 information for the SFCS switch connection instance."
        INDEX   { sfcsCnxCfgCrossConnectIndex,
                  sfcsCnxCfgCrossConnectLowIfIndex,
                  sfcsCnxCfgCrossConnectLowVpi,
                  sfcsCnxCfgCrossConnectLowVci,
                  sfcsCnxCfgCrossConnectHighIfIndex,
                  sfcsCnxCfgCrossConnectHighVpi,
                  sfcsCnxCfgCrossConnectHighVci }
        ::= { sfcsCnxCfgTable 1 }

SfcsCnxCfgEntry ::=
        SEQUENCE {
                sfcsCnxCfgCrossConnectIndex             INTEGER,
                sfcsCnxCfgCrossConnectLowIfIndex        INTEGER,
                sfcsCnxCfgCrossConnectLowVpi            INTEGER,
                sfcsCnxCfgCrossConnectLowVci            INTEGER,
                sfcsCnxCfgCrossConnectHighIfIndex       INTEGER,
                sfcsCnxCfgCrossConnectHighVpi           INTEGER,
                sfcsCnxCfgCrossConnectHighVci           INTEGER,
                sfcsCnxCfgType                          INTEGER,
                sfcsCnxCfgTmType                        INTEGER,
                sfcsCnxCfgUPCEnable                     INTEGER,
                sfcsCnxCfgStatsEnable                   INTEGER,
                sfcsCnxCfgStatsTableCounterSizes        INTEGER,
                sfcsCnxCfgOwner                          INTEGER
        }

sfcsCnxCfgCrossConnectIndex             OBJECT-TYPE
        SYNTAX  INTEGER
        ACCESS  read-only
        STATUS  mandatory
        DESCRIPTION
                "A unique value to identify this cross-connect."
        ::= { sfcsCnxCfgEntry 1 }

sfcsCnxCfgCrossConnectLowIfIndex        OBJECT-TYPE
        SYNTAX  INTEGER
        ACCESS  read-only
        STATUS  mandatory
        DESCRIPTION
                "The value of this object is equal to the low
                 MIB II IfIndex value of the ATM interface port
                 for this cross-connect."
        ::= { sfcsCnxCfgEntry 2 }

sfcsCnxCfgCrossConnectLowVpi            OBJECT-TYPE
        SYNTAX  INTEGER  (0..4095)
        ACCESS  read-only
        STATUS  mandatory
        DESCRIPTION
                "The value of this object is equal to the low VPI
                 value at the ATM interface associated with the
                 cross-connect that is identified by
                 sfcsCnxCfgCrossConnectIndex."
        ::= { sfcsCnxCfgEntry 3 }

sfcsCnxCfgCrossConnectLowVci            OBJECT-TYPE
        SYNTAX  INTEGER  (0..65535)
        ACCESS  read-only
        STATUS  mandatory
        DESCRIPTION
                "The value of this object is equal to the low VCI
                 value at the ATM interface associated with this
                 cross-connect that is identified by
                 sfcsCnxCfgCrossConnectIndex."
        ::= { sfcsCnxCfgEntry 4 }

sfcsCnxCfgCrossConnectHighIfIndex       OBJECT-TYPE
        SYNTAX  INTEGER
        ACCESS  read-only
        STATUS  mandatory
        DESCRIPTION
                "The value of this object is equal to the high
                 MIB II IfIndex value of the ATM interface port
                 for this cross-connect."
        ::= { sfcsCnxCfgEntry 5 }

sfcsCnxCfgCrossConnectHighVpi           OBJECT-TYPE
        SYNTAX  INTEGER  (0..4095)
        ACCESS  read-only
        STATUS  mandatory
        DESCRIPTION
                "The value of this object is equal to the high VPI
                 value at the ATM interface associated with the
                 cross-connect that is identified by
                 sfcsCnxCfgCrossConnectIndex."
        ::= { sfcsCnxCfgEntry 6 }

sfcsCnxCfgCrossConnectHighVci           OBJECT-TYPE
        SYNTAX  INTEGER  (0..65535)
        ACCESS  read-only
        STATUS  mandatory
        DESCRIPTION
                "The value of this object is equal to the high VCI
                 value at the ATM interface associated with this
                 cross-connect that is identified by
                 sfcsCnxCfgCrossConnectIndex."
        ::= { sfcsCnxCfgEntry 7 }

sfcsCnxCfgType          OBJECT-TYPE
        SYNTAX  INTEGER {
                        point-to-point-vpl          (1),
                        point-to-mpoint-vpl         (2),
                        mpoint-to-mpoint-vpl        (3),
                        point-to-point-vcl          (4),
                        point-to-mpoint-vcl         (5),
                        mpoint-to-mpoint-vcl        (6)
                }
        ACCESS  read-only
        STATUS  mandatory
        DESCRIPTION
                "Indicates the connection type for this VC.
                        point-to-point-vpl(1)
                        point-to-mpoint-vpl(2)
                        mpoint-to-mpoint-vpl(3)
                        point-to-point-vcl(4)
                        point-to-mpoint-vcl(5)
                        mpoint-to-mpoint-vcl(6)"
        ::= { sfcsCnxCfgEntry 8 }

sfcsCnxCfgTmType                OBJECT-TYPE
        SYNTAX  INTEGER  {
                        other   (1),
                        efci    (2),
                        er      (3)
                }
        ACCESS  read-only
        STATUS  mandatory
        DESCRIPTION
                "Indicates the type of traffic management used on this VC.
                        other   (1)
                        efci    (2)
                        er      (3)"
        ::= { sfcsCnxCfgEntry 9 }

sfcsCnxCfgUPCEnable             OBJECT-TYPE
        SYNTAX  INTEGER  {
                        l-h-upc-enabled 			(1),
                        l-h-tag-enabled 			(2),
                        l-h-upc-tag-enabled			(3),
                        h-l-upc-enabled				(4),
                        l-h-upc-and-h-l-upc-enabled		(5), 
                        l-h-Tag-and-h-l-upc-enabled		(6),
                        l-h-upc-tag-and-h-l-upc-enabled		(7),
                        h-l-tag-enabled				(8),
                        l-h-upc-and-h-l-tag-enabled		(9),
                        l-h-tag-and-h-l-tag-enabled		(10),
                        l-h-upc-tag-and-h-l-tag-enabled		(11),
                        h-l-upc-tag-enabled			(12),
                        l-h-upc-and-h-l-upc-tag-enabled		(13),
                        l-h-tag-and-h-l-upc-tag-enabled		(14),
                        l-h-upc-tag-and-h-l-upc-tag-enabled	(15)
                }
        ACCESS  read-only
        STATUS  mandatory
        DESCRIPTION
                "Indicates whether or not UPC policing is enabled on
                 this VC. A VC can be bi-directional or uni-directional.
                 Due to this, the UPC bit is a masking based on directionality.
                 Where direction is in terms of high interface (H) and low
                 interface (L). (Where not specified, assume disabled.)
                        L to H UPC enabled(1)
                        L to H Tagging enabled(2)
                        L to H UPC/Tagging enabled(3)
                        H to L UPC enabled(4)
                        L to H UPC enabled & H to L UPC enabled(5)
                        L to H Tagging enabled & H to L UPC enabled(6)
                        L to H UPC/Tagging enabled & H to L UPC enabled(7)
                        H to L Tagging enabled(8)
                        L to H UPC enabled & H to L Tagging enabled(9)
                        L to H Tagging enabled & H to L Tagging enabled(10)
                        L to H UPC/Tagging enabled & H to L Tagging enabled(11)
                        H to L UPC/Tagging enabled(12)
                        L to H UPC enabled & H to L UPC/Tagging enabled(13)
                        L to H Tagging enabled and H to L UPC/Tagging enabled(14)
                        L to H UPC/Tagging enabled & H to L UPC/Tagging enabled(15)"
        ::= { sfcsCnxCfgEntry 10 }

sfcsCnxCfgStatsEnable   OBJECT-TYPE
        SYNTAX  INTEGER  {
                        enabled (1),
                        disabled (2),
                        other (3)
                }
        ACCESS  read-only
        STATUS  mandatory
        DESCRIPTION
                "Indicates whether statistics will be kept on this VC.
                        enabled(1)
                        disabled(2)
                        other(3)"
        ::= { sfcsCnxCfgEntry 11 }

sfcsCnxCfgStatsTableCounterSizes        OBJECT-TYPE
        SYNTAX  INTEGER  {
                        thirtytwobittagcounter  (1),
                        thirtytwobitdropcounter (2),
                        sixteenbiteachcounter   (3)
                }
        ACCESS  read-only
        STATUS  mandatory
        DESCRIPTION
                "Indicates the size of the drop counter for this VC.
                        thirtytwobittagcounter  (1)
                        thirtytwobitdropcounter (2)
                        sixteenbiteachcounter   (3)"
        ::= { sfcsCnxCfgEntry 12 }

sfcsCnxCfgOwner        OBJECT-TYPE
        SYNTAX  INTEGER  {
                        other   (1),
                        own   (2),
                        dontown (3)
                }
        ACCESS  read-only
        STATUS  mandatory
        DESCRIPTION
                "Indicates the owner of this cross connect.
                        other(1)
                        own(2)
                        dontown(3)"
        ::= { sfcsCnxCfgEntry 13 }





--  SFCS Switch Connection Stats Table

sfcsCnxStatsTable    OBJECT-TYPE
        SYNTAX  SEQUENCE OF SfcsCnxStatsEntry
        ACCESS  not-accessible
        STATUS  mandatory
        DESCRIPTION
                "This table contains the connection configuration
                 information."
        ::= { sfcsConnectionStatistics 1 }

sfcsCnxStatsEntry    OBJECT-TYPE
        SYNTAX  SfcsCnxStatsEntry
        ACCESS  not-accessible
        STATUS  mandatory
        DESCRIPTION
                "Each entry specifies the connection statistics
                 information for the SFCS switch connection instance."
        INDEX   { sfcsCnxStatsCrossConnectIndex,
                  sfcsCnxStatsCrossConnectLowIfIndex,
                  sfcsCnxStatsCrossConnectLowVpi,
                  sfcsCnxStatsCrossConnectLowVci,
                  sfcsCnxStatsCrossConnectHighIfIndex,
                  sfcsCnxStatsCrossConnectHighVpi,
                  sfcsCnxStatsCrossConnectHighVci }
        ::= { sfcsCnxStatsTable 1 }

SfcsCnxStatsEntry ::=
        SEQUENCE {
                sfcsCnxStatsCrossConnectIndex   INTEGER,
                sfcsCnxStatsCrossConnectLowIfIndex      INTEGER,
                sfcsCnxStatsCrossConnectLowVpi          INTEGER,
                sfcsCnxStatsCrossConnectLowVci          INTEGER,
                sfcsCnxStatsCrossConnectHighIfIndex     INTEGER,
                sfcsCnxStatsCrossConnectHighVpi         INTEGER,
                sfcsCnxStatsCrossConnectHighVci         INTEGER,
                sfcsCnxStatsLoToHiHTxCells              OCTET STRING,
                sfcsCnxStatsLoToHiDroppedCells          OCTET STRING,
                sfcsCnxStatsLoToHiTaggedCells           OCTET STRING,
                sfcsCnxStatsHiToLoHTxCells              OCTET STRING,
                sfcsCnxStatsHiToLoDroppedCells          OCTET STRING,
                sfcsCnxStatsHiToLoTaggedCells           OCTET STRING
        }

sfcsCnxStatsCrossConnectIndex           OBJECT-TYPE
        SYNTAX  INTEGER
        ACCESS  read-only
        STATUS  mandatory
        DESCRIPTION
                "A unique value to identify this cross-connect."
        ::= { sfcsCnxStatsEntry 1 }

sfcsCnxStatsCrossConnectLowIfIndex      OBJECT-TYPE
        SYNTAX  INTEGER
        ACCESS  read-only
        STATUS  mandatory
        DESCRIPTION
                "The value of this object is equal to the low
                 MIB II IfIndex value of the ATM interface port
                 for this cross-connect."
        ::= { sfcsCnxStatsEntry 2 }

sfcsCnxStatsCrossConnectLowVpi          OBJECT-TYPE
        SYNTAX  INTEGER  (0..4095)
        ACCESS  read-only
        STATUS  mandatory
        DESCRIPTION
                "The value of this object is equal to the low VPI
                 value at the ATM interface associated with the
                 cross-connect that is identified by
                 sfcsCnxStatsCrossConnectIndex."
        ::= { sfcsCnxStatsEntry 3 }

sfcsCnxStatsCrossConnectLowVci          OBJECT-TYPE
        SYNTAX  INTEGER  (0..65535)
        ACCESS  read-only
        STATUS  mandatory
        DESCRIPTION
                "The value of this object is equal to the low VCI
                 value at the ATM interface associated with this
                 cross-connect that is identified by
                 sfcsCnxStatsCrossConnectIndex."
        ::= { sfcsCnxStatsEntry 4 }

sfcsCnxStatsCrossConnectHighIfIndex     OBJECT-TYPE
        SYNTAX  INTEGER
        ACCESS  read-only
        STATUS  mandatory
        DESCRIPTION
                "The value of this object is equal to the high
                 MIB II IfIndex value of the ATM interface port
                 for this cross-connect."
        ::= { sfcsCnxStatsEntry 5 }

sfcsCnxStatsCrossConnectHighVpi                 OBJECT-TYPE
        SYNTAX  INTEGER  (0..4095)
        ACCESS  read-only
        STATUS  mandatory
        DESCRIPTION
                "The value of this object is equal to the high VPI
                 value at the ATM interface associated with the
                 cross-connect that is identified by
                 sfcsCnxStatsCrossConnectIndex."
        ::= { sfcsCnxStatsEntry 6 }

sfcsCnxStatsCrossConnectHighVci                 OBJECT-TYPE
        SYNTAX  INTEGER  (0..65535)
        ACCESS  read-only
        STATUS  mandatory
        DESCRIPTION
                "The value of this object is equal to the high VCI
                 value at the ATM interface associated with this
                 cross-connect that is identified by
                 sfcsCnxStatsCrossConnectIndex."
        ::= { sfcsCnxStatsEntry 7 }

sfcsCnxStatsLoToHiHTxCells      OBJECT-TYPE
        SYNTAX  OCTET STRING
        ACCESS  read-only
        STATUS  mandatory
        DESCRIPTION
                "Indicates the transmitted cell count for this connection.
                 This entry specifies the count from the low port/vpi/vci
                 to the high port/vpi/vci"
        ::= { sfcsCnxStatsEntry 8 }

sfcsCnxStatsLoToHiDroppedCells  OBJECT-TYPE
        SYNTAX  OCTET STRING
        ACCESS  read-only
        STATUS  mandatory
        DESCRIPTION
                "Indicates the dropped cell count for this connection
                 instance. This entry specifies the count from the low
                 port/vpi/vci to the high port/vpi/vci."
        ::= { sfcsCnxStatsEntry 9 }

sfcsCnxStatsLoToHiTaggedCells   OBJECT-TYPE
        SYNTAX  OCTET STRING
        ACCESS  read-only
        STATUS  mandatory
        DESCRIPTION
                "Indicates the tagged cell count for this connection
                 instance. This entry specifies the count from the low
                 port/vpi/vci to the high port/vpi/vci."
        ::= { sfcsCnxStatsEntry 10 }

sfcsCnxStatsHiToLoHTxCells      OBJECT-TYPE
        SYNTAX  OCTET STRING
        ACCESS  read-only
        STATUS  mandatory
        DESCRIPTION
                "Indicates the transmitted cell count for this connection.
                 This entry specifies the count from the high port/vpi/vci
                 to the low port/vpi/vci"
        ::= { sfcsCnxStatsEntry 11 }

sfcsCnxStatsHiToLoDroppedCells  OBJECT-TYPE
        SYNTAX  OCTET STRING
        ACCESS  read-only
        STATUS  mandatory
        DESCRIPTION
                "Indicates the dropped cell count for this connection
                 instance. This entry specifies the count from the high
                 port/vpi/vci to the low port/vpi/vci."
        ::= { sfcsCnxStatsEntry 12 }

sfcsCnxStatsHiToLoTaggedCells   OBJECT-TYPE
        SYNTAX  OCTET STRING
        ACCESS  read-only
        STATUS  mandatory
        DESCRIPTION
                "Indicates the tagged cell count for this connection
                 instance. This entry specifies the count from the high
                 port/vpi/vci to the low port/vpi/vci."
        ::= { sfcsCnxStatsEntry 13 }




--  SFCS Switch Connection Error Table

sfcsCnxErrorTable    OBJECT-TYPE
        SYNTAX  SEQUENCE OF SfcsCnxErrorEntry
        ACCESS  not-accessible
        STATUS  mandatory
        DESCRIPTION
                "This table contains the connection error information
                 supplied by the atmAPI mib."
        ::= { sfcsConnectionError 1 }

sfcsCnxErrorEntry    OBJECT-TYPE
        SYNTAX  SfcsCnxErrorEntry
        ACCESS  not-accessible
        STATUS  mandatory
        DESCRIPTION
                "A list of VCC connection request failures. This table
                 is indexed the same way as the atmVcCrossConnectTable
                 in the AToM mib."
        INDEX   { atmVcCrossConnectIndex, atmVcCrossConnectLowIfIndex, atmVcCrossConnectLowVpi, atmVcCrossConnectLowVci, atmVcCrossConnectHighIfIndex, atmVcCrossConnectHighVpi, atmVcCrossConnectHighVci }
--          AUGMENTS { sfcsCnxCfgEntry }
        ::= { sfcsCnxErrorTable 1 }
    

SfcsCnxErrorEntry ::=
        SEQUENCE {
                sfcsCnxErrorCode         OCTET STRING,
                sfcsCnxErrorTimeStamp    TimeTicks,
                sfcsCnxErrorRowStatus    INTEGER
        }

sfcsCnxErrorCode        OBJECT-TYPE
        SYNTAX  OCTET STRING
        ACCESS  read-only
        STATUS  mandatory
        DESCRIPTION
                "Specifies the error reason for failure of the
                 connection setup.
                
                
                01 fatal_error
                02 moe_table_out_of_range
                03 moe_mem_not_allocated
                04 mem_fetch_double_reqst
                05 lo_port_invalid
                06 lo_port_locked
                07 lo_vpi_invalid
                08 lo_vci_invalid
                09 hi_port_invalid
                10 hi_port_locked
                11 hi_vpi_invalid
                12 hi_vci_invalid
                13 trfc_desc_l2h_invalid
                14 trfc_desc_h2l_invalid
                15 ccid_invalid
                16 ccid_not_assigned
                17 atm_api_type_invalid
                18 atm_api_verb_invalid
                19 pt_to_pt_over_write_reqst
                20 pt_reqst_over_mpt_conn
                21 mask_table_full
                22 duplicate_request
                23 moe_table_out_of_memory
                24 vpi0_non_term_reqst
                25 hardware_out_of_heap
                26 tx_conn_table_out_of_mem
                27 tx_conn_table_time_out
                28 ctm_communication_error
                29 connection_table_out_of_sync
                30 invalid_connection_entry
                31 ctm_resource_alloc_error
                32 front_panel_bandwidth_alloc_error
                33 ccid_in_use"

        ::= { sfcsCnxErrorEntry 1 }

sfcsCnxErrorTimeStamp   OBJECT-TYPE
        SYNTAX  TimeTicks
        ACCESS  read-only
        STATUS  mandatory
        DESCRIPTION
                "Indicates the value of the sysUpTime when this
                 connection request failed. We will support this
                 field only if the element management uses this
                 table."
        ::= { sfcsCnxErrorEntry 2 }


sfcsCnxErrorRowStatus   OBJECT-TYPE
        SYNTAX  INTEGER {
                other (1),
                inactive (2),
                active (3),
                delete (4)
        }
        ACCESS  read-write
        STATUS  mandatory
        DESCRIPTION
                "The administrative control of this entry. The owner
                 could delete this entry after reading it, to prevent
                 this table from growing too big.
                	other (1)
                	inactive (2)
                	active (3)
                	delete (4)"
        ::= { sfcsCnxErrorEntry 3 }




--  The SFCS connection API Group

sfcsCnxAPIEntry                 OBJECT-TYPE
        SYNTAX  INTEGER     (1)
        ACCESS  read-only
        STATUS  mandatory
        DESCRIPTION
        "
        The connection API leaf provides a method for contool for creating
        PVCs. This always returns a value of 0.
        "

        ::= { sfcsConnectionAPI 1 }




--  The SFCS Switch CTM Group

sfcsCTMInterfaceConfigTable     OBJECT-TYPE
        SYNTAX  SEQUENCE OF SfcsCTMInterfaceConfigEntry
        ACCESS  not-accessible
        STATUS  mandatory
        DESCRIPTION
                "This table contains the configuration information of each
                 configured SHEMP interface.  If SFCS is not configured
                 on a port, than an entry will not exist."
        ::= { sfcsCTMInterfaceConfig 1 }
 
sfcsCTMInterfaceConfigEntry    OBJECT-TYPE
        SYNTAX  SfcsCTMInterfaceConfigEntry
        ACCESS  not-accessible
        STATUS  mandatory
        DESCRIPTION
                "Each entry specifies the SFCS configuration for the SFCS
                 switch interface for which the entry exists."
        INDEX   { sfcsCTMInterfaceConfigInterfaceIndex }
        ::= { sfcsCTMInterfaceConfigTable 1 }
 
SfcsCTMInterfaceConfigEntry ::=
        SEQUENCE {
                sfcsCTMInterfaceConfigInterfaceIndex       INTEGER,
                sfcsCTMInterfaceConfigType                 INTEGER,
                sfcsCTMInterfacePeakBufferUseage           INTEGER,
                sfcsCTMInterfaceConfigNumberOfQueues       INTEGER,
                sfcsCTMInterfaceConfigSigStackID           INTEGER,
                sfcsCTMInterfaceConfigClocking             INTEGER,
                sfcsCTMInterfaceConfigNextVPI              INTEGER,
                sfcsCTMInterfaceConfigNextVCI              INTEGER
        }
 
sfcsCTMInterfaceConfigInterfaceIndex               OBJECT-TYPE
        SYNTAX  INTEGER
        ACCESS  read-only
        STATUS  mandatory
        DESCRIPTION
                "The index which specifies which interface we are
                 dealing with."
        ::= { sfcsCTMInterfaceConfigEntry 1 }
 
sfcsCTMInterfaceConfigType                         OBJECT-TYPE
        SYNTAX          INTEGER {
                            other(1),
                            access-port(2),
                            network-port(3),
                            host-mgmt-port(4),
                            host-ctl-port(5)
                        }
        ACCESS          read-only
        STATUS          mandatory
        DESCRIPTION
                "Sets the type of interface access attribute for the SFCS
                 interfaces.  Access ports allow single user or shared
                 access and perform statisics and control; network ports
                 are equivalent to trunk ports with no access control;
                 host management port indicates the (virtual) port to which
                 the (internal) management agent is attached; host control
                 port indicates the port to redirect non-management packets.
                            other(1),
                            access-port(2),
                            network-port(3),
                            host-mgmt-port(4),
                            host-ctl-port(5)

"
        ::= { sfcsCTMInterfaceConfigEntry 2 }
 
sfcsCTMInterfacePeakBufferUseage                   OBJECT-TYPE
        SYNTAX          INTEGER (0..100)
        ACCESS          read-only
        STATUS          mandatory
        DESCRIPTION
                "Indicates the number of cells in transmit buffer memory."
        ::= { sfcsCTMInterfaceConfigEntry 3 }
 
sfcsCTMInterfaceConfigNumberOfQueues               OBJECT-TYPE
        SYNTAX          INTEGER
        ACCESS          read-only
        STATUS          mandatory
        DESCRIPTION
                "Indicates the number of priority queues configured on this
                 interface."
        ::= { sfcsCTMInterfaceConfigEntry 4 }
 
sfcsCTMInterfaceConfigSigStackID                   OBJECT-TYPE
        SYNTAX          INTEGER
        ACCESS          read-only
        STATUS          mandatory
        DESCRIPTION
                "Indicates the user signalling stack ID for this interface."
        ::= { sfcsCTMInterfaceConfigEntry 5 }
 
sfcsCTMInterfaceConfigClocking       OBJECT-TYPE
        SYNTAX          INTEGER {
                            generated-transmit-clock(1),
                            channel-recovered-clock(2),
                            system-master-clock(3),
             not-supported(4)
                        }
        ACCESS          read-write
        STATUS          mandatory
        DESCRIPTION
                "The anim clocking source.
                one - use the generated-transmit-clock
                two - use the channel-recovered-clock
                three - use the system-master-clock
      four - option not supported by this interface"
        ::= { sfcsCTMInterfaceConfigEntry 6 }
 
sfcsCTMInterfaceConfigNextVPI                   OBJECT-TYPE
        SYNTAX          INTEGER
        ACCESS          read-only
        STATUS          mandatory
        DESCRIPTION
                "Indicates the next vpi for this interface."
        ::= { sfcsCTMInterfaceConfigEntry 7 }
 
sfcsCTMInterfaceConfigNextVCI                   OBJECT-TYPE
        SYNTAX          INTEGER
        ACCESS          read-only
        STATUS          mandatory
        DESCRIPTION
                "Indicates the next vci for this interface."
        ::= { sfcsCTMInterfaceConfigEntry 8 }
 
 
-- SFCS SHEMP Interface Statistics Tables
-- This table contains the objects that specify the packet and byte counters
-- for each configured SFCS switching interface.
 
 
sfcsCTMInterfaceStatsTable                 OBJECT-TYPE
        SYNTAX          SEQUENCE OF SfcsCTMInterfaceStatsEntry
        ACCESS          not-accessible
        STATUS          mandatory
        DESCRIPTION
                "This table contains the cell counts for each
                 SFCS switch interface."
        ::= { sfcsCTMInterfaceStatistics 1 }
 
sfcsCTMInterfaceStatsEntry                 OBJECT-TYPE
        SYNTAX          SfcsCTMInterfaceStatsEntry
        ACCESS          not-accessible
        STATUS          mandatory
        DESCRIPTION
                "Specifies the SFCS cell counts for the SFCS
                 interface for which this entry exists."
        INDEX    { sfcsCTMInterfaceStatsInterfaceIndex }
        ::= { sfcsCTMInterfaceStatsTable 1 }
 
SfcsCTMInterfaceStatsEntry ::=
        SEQUENCE {
                sfcsCTMInterfaceStatsInterfaceIndex                INTEGER,
                sfcsCTMInterfaceStatsRxErrors                      OCTET STRING,
                sfcsCTMInterfaceStatsVPILookupInvalidErrors        OCTET STRING,
                sfcsCTMInterfaceStatsRxCnxLookupInvalidErrors      OCTET STRING,
                sfcsCTMInterfaceStatsRxCellCnt                     OCTET STRING,
                sfcsCTMInterfaceStatsTxCellCnt                     OCTET STRING,
                sfcsCTMInterfaceStatsOverflowDropCellCnt           OCTET STRING
        }
 
sfcsCTMInterfaceStatsInterfaceIndex        OBJECT-TYPE
        SYNTAX  INTEGER
        ACCESS  read-only
        STATUS  mandatory
        DESCRIPTION
                "The index which specifies which interface we are
                 dealing with."
        ::= { sfcsCTMInterfaceStatsEntry 1 }
 
sfcsCTMInterfaceStatsRxErrors              OBJECT-TYPE
        SYNTAX          OCTET STRING
        ACCESS          read-only
        STATUS          mandatory
        DESCRIPTION
                "Indicates the number of receive path lookup
                 invalid and out of range errors."
        ::= { sfcsCTMInterfaceStatsEntry 2 }
 
sfcsCTMInterfaceStatsVPILookupInvalidErrors        OBJECT-TYPE
        SYNTAX          OCTET STRING
        ACCESS          read-only
        STATUS          mandatory
        DESCRIPTION
                "Indicates the number of VPI lookup invalid and out of
                 range errors."
        ::= { sfcsCTMInterfaceStatsEntry 3 }
 
sfcsCTMInterfaceStatsRxCnxLookupInvalidErrors      OBJECT-TYPE
        SYNTAX          OCTET STRING
        ACCESS          read-only
        STATUS          mandatory
        DESCRIPTION
                "Indicates the number of receive connection lookup
                 invalid errors."
        ::= { sfcsCTMInterfaceStatsEntry 4 }
 
sfcsCTMInterfaceStatsRxCellCnt              OBJECT-TYPE
        SYNTAX          OCTET STRING
        ACCESS          read-only
        STATUS          mandatory
        DESCRIPTION
                "Indicates the number of receive cells on
                 this interface."
        ::= { sfcsCTMInterfaceStatsEntry 7 }
 
 
sfcsCTMInterfaceStatsTxCellCnt              OBJECT-TYPE
        SYNTAX          OCTET STRING
        ACCESS          read-only
        STATUS          mandatory
        DESCRIPTION
                "Indicates the number of transmit cells
                 on this interface."
        ::= { sfcsCTMInterfaceStatsEntry 8 }
 
 
sfcsCTMInterfaceStatsOverflowDropCellCnt    OBJECT-TYPE
        SYNTAX          OCTET STRING
        ACCESS          read-only
        STATUS          mandatory
        DESCRIPTION
                "Indicates the number of cells that were
                 dropped due to queue overflows."
        ::= { sfcsCTMInterfaceStatsEntry 9 }
 

-- SFCS SHEMP Queue Group
-- This group contains the managed objects for maintaining SFCS Shemp Queues.
 
--  SFCS Shemp Queue Configuration Table
 
sfcsCTMQueueConfigTable     OBJECT-TYPE
        SYNTAX  SEQUENCE OF SfcsCTMQueueConfigEntry
        ACCESS  not-accessible
        STATUS  mandatory
        DESCRIPTION
                "This table contains the configuration information for
                 all queues on the SFCS."
        ::= { sfcsCTMQueueConfig 1 }
 
sfcsCTMQueueConfigEntry    OBJECT-TYPE
        SYNTAX  SfcsCTMQueueConfigEntry
        ACCESS  not-accessible
        STATUS  mandatory
        DESCRIPTION
                "Each entry specifies the queue information for the
                 SFCS switch for which the entry exists."
        INDEX   { sfcsCTMQueueConfigInterfaceIndex, sfcsQueueConfigQueueIndex }
        ::= { sfcsCTMQueueConfigTable 1 }
 
SfcsCTMQueueConfigEntry ::=
        SEQUENCE {
                sfcsCTMQueueConfigInterfaceIndex           INTEGER,
                sfcsCTMQueueConfigQueueIndex               INTEGER,
                sfcsCTMQueueConfigQueueSize                INTEGER,
                sfcsCTMQueueConfigQueueBandwidth           INTEGER,
                sfcsCTMQueueConfigClpDropThreshold         INTEGER,
                sfcsCTMQueueConfigCongestionThreshold      INTEGER,
                sfcsCTMQueueConfigEFCILowThreshold         INTEGER,
                sfcsCTMQueueConfigRMThreshold              INTEGER
        }
 
sfcsCTMQueueConfigInterfaceIndex           OBJECT-TYPE
        SYNTAX  INTEGER
        ACCESS  read-only
        STATUS  mandatory
        DESCRIPTION
                "The index which specifies which interface we are
                 dealing with."
        ::= { sfcsCTMQueueConfigEntry 1 }
 
sfcsCTMQueueConfigQueueIndex               OBJECT-TYPE
        SYNTAX  INTEGER
        ACCESS  read-only
        STATUS  mandatory
        DESCRIPTION
                "The index which specifies which transmit queue we
                 are dealing with."
        ::= { sfcsCTMQueueConfigEntry 2 }
 
sfcsCTMQueueConfigQueueSize                OBJECT-TYPE
        SYNTAX  INTEGER
        ACCESS  read-write
        STATUS  mandatory
        DESCRIPTION
                "Indicates the size of the transmit queue for this
                 queue instance."
        ::= { sfcsCTMQueueConfigEntry 3 }
 
sfcsCTMQueueConfigQueueBandwidth           OBJECT-TYPE
        SYNTAX  INTEGER (0..100)
        ACCESS  read-write
        STATUS  mandatory
        DESCRIPTION
                "Indicates the percentage of this interface's bandwidth
                 utilized by this particular queue."
        ::= { sfcsCTMQueueConfigEntry 4 }
 
sfcsCTMQueueConfigClpDropThreshold         OBJECT-TYPE
        SYNTAX  INTEGER (0..100)
        ACCESS  read-write
        STATUS  mandatory
        DESCRIPTION
                "Indicates the queue level to start dropping CLP=1
                 cells for this queue.  This level is expressed as
                 the percentage of this queue's size."
        ::= { sfcsCTMQueueConfigEntry 5 }
 
sfcsCTMQueueConfigCongestionThreshold      OBJECT-TYPE
        SYNTAX  INTEGER (0..100)
        ACCESS  read-write
        STATUS  mandatory
        DESCRIPTION
                "Indicates the level to consider this queue congested.
                 This level is expressed as the percentage of this
                 queue's size."
        ::= { sfcsCTMQueueConfigEntry 6 }
 
sfcsCTMQueueConfigEFCILowThreshold         OBJECT-TYPE
        SYNTAX  INTEGER (0..100)
        ACCESS  read-write
        STATUS  mandatory
        DESCRIPTION
                "Indicates the lower threshold used for EFCI for
                 this queue instance.  This level is expressed as
                 the percentage of this queue's size."
        ::= { sfcsCTMQueueConfigEntry 7 }
 
sfcsCTMQueueConfigRMThreshold              OBJECT-TYPE
        SYNTAX  INTEGER (0..100)
        ACCESS  read-write
        STATUS  mandatory
        DESCRIPTION
                "Indicates the remote management queue threshold expressed
                 as a percentage of the queue's size.  When this level is
                 hit, a management message is sent to the sender notifying it
                 to slow down."
        ::= { sfcsCTMQueueConfigEntry 8 }
 
 
 
 
--  SFCS Shemp Queue Stats Table
 
sfcsCTMQueueStatsTable     OBJECT-TYPE
        SYNTAX  SEQUENCE OF SfcsCTMQueueStatsEntry
        ACCESS  not-accessible
        STATUS  mandatory
        DESCRIPTION
                "This table contains the statistics information for all
                 queues on the SFCS."
        ::= { sfcsCTMQueueStatistics 1 }
 
sfcsCTMQueueStatsEntry    OBJECT-TYPE
        SYNTAX  SfcsCTMQueueStatsEntry
        ACCESS  not-accessible
        STATUS  mandatory
        DESCRIPTION
                "Each entry specifies the queue information for the
                 SFCS switch for which the entry exists."
        INDEX   { sfcsCTMQueueStatsInterfaceIndex, sfcsQueueStatsQueue }
        ::= { sfcsCTMQueueStatsTable 1 }
 
SfcsCTMQueueStatsEntry ::=
        SEQUENCE {
                sfcsCTMQueueStatsInterfaceIndex            INTEGER,
                sfcsCTMQueueStatsQueue                     INTEGER,
                sfcsCTMQueueStatsTxClpCellsDiscarded       OCTET STRING,
                sfcsCTMQueueStatsTxCellsDropped            OCTET STRING,
                sfcsCTMQueueStatsQueuePeakLevel            INTEGER,
                sfcsCTMQueueStatsTxCellCnt                 OCTET STRING
        }
 
sfcsCTMQueueStatsInterfaceIndex    OBJECT-TYPE
        SYNTAX  INTEGER
        ACCESS  read-only
        STATUS  mandatory
        DESCRIPTION
                "The index which specifies which interface we are
                 dealing with."
        ::= { sfcsCTMQueueStatsEntry 1 }
 
sfcsCTMQueueStatsQueue    OBJECT-TYPE
        SYNTAX  INTEGER
        ACCESS  read-only
        STATUS  mandatory
        DESCRIPTION
                "The index which specifies which queue we are
                 dealing with."
        ::= { sfcsCTMQueueStatsEntry 2 }
 
sfcsCTMQueueStatsTxClpCellsDiscarded    OBJECT-TYPE
        SYNTAX  OCTET STRING
        ACCESS  read-only
        STATUS  mandatory
        DESCRIPTION
                "Indicates the number of cells with CLP=1 that were
                 discarded for this queue instance."
        ::= { sfcsCTMQueueStatsEntry 3 }
 
sfcsCTMQueueStatsTxCellsDropped    OBJECT-TYPE
        SYNTAX  OCTET STRING
        ACCESS  read-only
        STATUS  mandatory
        DESCRIPTION
                "Indicates the number of cells that overflowed the
                 buffer for this queue instance."
        ::= { sfcsCTMQueueStatsEntry 4 }
 
sfcsCTMQueueStatsQueuePeakLevel    OBJECT-TYPE
        SYNTAX  INTEGER
        ACCESS  read-only
        STATUS  mandatory
        DESCRIPTION
                "Indicates the peak level since last read for this
                 queue instance."
        ::= { sfcsCTMQueueStatsEntry 5 }
 
sfcsCTMQueueStatsTxCellCnt         OBJECT-TYPE
        SYNTAX  OCTET STRING
        ACCESS  read-only
        STATUS  mandatory
        DESCRIPTION
                "Indicates the transmit cell count on a per queue basis.
                A value of zero indicates not available"
        ::= { sfcsCTMQueueStatsEntry 6 }
 
 

--  The SFCS Switch Host Group

--  The SFCS Switch UniMux Group

-- SFCS Switch Bandwidth Management Group
-- This group contains the managed objects and functions used to setup and
-- configure the SFCS Bandwidth Manager.  This group contains four sub-groups
-- Nim Tables, Port Tables, Bandwidth Pool elements and Buffer Tables. 

-- SFCS ANIM Bandwidth Management Nim Table
-- This table contains contains information about the administration status of the Nim.
--  %%%%%%%%%%%%%%%%%%%%%%%%%%%%%%%%%%%%%%%%%%%%%%%%%%%%%%%%%%%%%%%%%%%%%%%%%%%%%%%%%%%%%%%%
--  ### Nim Information

sfcsBwNimsTable   OBJECT-TYPE
   SYNTAX   SEQUENCE OF SfcsBwNimsEntry
   ACCESS   not-accessible
   STATUS   mandatory
   DESCRIPTION
      "This table contains the Nim Oid and the Nim Administrative Status
       reading functions."
   ::= { sfcsBwNims 1 }

sfcsBwNimsEntry   OBJECT-TYPE
   SYNTAX   SfcsBwNimsEntry
   ACCESS   not-accessible
   STATUS   mandatory
   DESCRIPTION
      "Each entry contains a Nim Oid and the Nim Administrative Status."
   INDEX   { sfcsBwNimsIndex }
   ::= { sfcsBwNimsTable 1 }

SfcsBwNimsEntry ::=
   SEQUENCE {
      sfcsBwNimsIndex          INTEGER,
      sfcsBwNimsAdminStatus    INTEGER,
      sfcsBWNimsBuffCount      INTEGER,
      sfcsBWNimsPortCount      INTEGER,
      sfcsBWNimsPrioCount      INTEGER
   }

--  ### Nim Defs
sfcsBwNimsIndex   OBJECT-TYPE
   SYNTAX   INTEGER
   ACCESS   read-only
   STATUS   mandatory
   DESCRIPTION
      "This index specifies which NIM we are dealing
       with.  This reference is in the same format as MIB II's
       Interface index."
   ::= { sfcsBwNimsEntry 1 }

sfcsBwNimsAdminStatus      OBJECT-TYPE
   SYNTAX   INTEGER
   ACCESS   read-write
   STATUS   mandatory
   DESCRIPTION
      "Indicates the administrative status of this Nim.
                  10 - Active
                  20 - Inactive "
   ::= { sfcsBwNimsEntry 2 }

sfcsBWNimsBuffCount OBJECT-TYPE
   SYNTAX   INTEGER
   ACCESS   read-only
   STATUS   mandatory
   DESCRIPTION
      "The number of transmit buffers for this NIM"
   ::= { sfcsBwNimsEntry 3 }

sfcsBWNimsPortCount OBJECT-TYPE
   SYNTAX   INTEGER
   ACCESS   read-only
   STATUS   mandatory
   DESCRIPTION
      "The number of ports for this NIM"
   ::= { sfcsBwNimsEntry 4 }

sfcsBWNimsPrioCount OBJECT-TYPE
   SYNTAX   INTEGER
   ACCESS   read-only
   STATUS   mandatory
   DESCRIPTION
      "The number of priority queues for this NIM"
   ::= { sfcsBwNimsEntry 5 }

--  %%%%%%%%%%%%%%%%%%%%%%%%%%%%%%%%%%%%%%%%%%%%%%%%%%%%%%%%%%%%%%%%%%%%%%%%%%%%%%%%%%%%%
--  ### Port Information

sfcsBwPortsTable   OBJECT-TYPE
   SYNTAX   SEQUENCE OF SfcsBwPortsEntry
   ACCESS   not-accessible
   STATUS   mandatory
   DESCRIPTION
      "This table contains the Port Oid, Port Administrative Status and
       the forward/reverse physical bandwidth reading functions."
   ::= { sfcsBwPorts 1 }

sfcsBwPortsEntry   OBJECT-TYPE
   SYNTAX   SfcsBwPortsEntry
   ACCESS   not-accessible
   STATUS   mandatory
   DESCRIPTION
      "Each entry contains the Port Oid, Port Administrative Status and
       the forward/reverse physical bandwidth."
   INDEX   { sfcsBwPortsIndex }
   ::= { sfcsBwPortsTable 1 }

SfcsBwPortsEntry ::=
   SEQUENCE
   {
      sfcsBwPortsIndex          INTEGER,
      sfcsBwPortsAdminStatus    INTEGER,
      sfcsBwPortsPhysBwFwd      INTEGER,
      sfcsBwPortsPhysBwRev      INTEGER,
      sfcsBwPortsZone           INTEGER,
      sfcsBwPortsMetric         INTEGER
   }

--   #Ports Defs
sfcsBwPortsIndex   OBJECT-TYPE
   SYNTAX   INTEGER
   ACCESS   read-only
   STATUS   mandatory
   DESCRIPTION
      "This index specifies which Port we are dealing
       with.  This reference is in the same format as MIB II's
       Interface index."
   ::= { sfcsBwPortsEntry 1 }

sfcsBwPortsAdminStatus      OBJECT-TYPE
   SYNTAX   INTEGER
   ACCESS   read-write
   STATUS   mandatory
   DESCRIPTION
      "Indicates the administrative status of this Port.
                  10 - Active
                  20 - Inactive "
   ::= { sfcsBwPortsEntry 2 }

sfcsBwPortsPhysBwFwd      OBJECT-TYPE
   SYNTAX   INTEGER
   ACCESS   read-only
   STATUS   mandatory
   DESCRIPTION
      "This is the forward physical bandwidth of the port in cells/sec."
   ::= { sfcsBwPortsEntry 3 }

sfcsBwPortsPhysBwRev      OBJECT-TYPE
   SYNTAX   INTEGER
   ACCESS   read-only
   STATUS   mandatory
   DESCRIPTION
      "This is the reverse physical bandwidth of the port in cells/sec."
   ::= { sfcsBwPortsEntry 4 }

sfcsBwPortsZone           OBJECT-TYPE
   SYNTAX   INTEGER
   ACCESS   read-only
   STATUS   mandatory
   DESCRIPTION
      "The range of the current bw operational point for this port. If a value has never been set the value will be -1."
   ::= { sfcsBwPortsEntry 5 }

sfcsBwPortsMetric         OBJECT-TYPE
   SYNTAX   INTEGER
   ACCESS   read-only
   STATUS   mandatory
   DESCRIPTION
      "The current bw operational point for this port.  If a value has never been set the value will be -1."
   ::= { sfcsBwPortsEntry 6 }


--  %%%%%%%%%%%%%%%%%%%%%%%%%%%%%%%%%%%%%%%%%%%%%%%%%%%%%%%%%%%%%%%%%%%%%%%%%%%%%%%%%%%%%
--  ### Bandwidth Pool Limits Information

sfcsBwPortPoolLimitsTable   OBJECT-TYPE
   SYNTAX   SEQUENCE OF SfcsBwPortPoolLimitsEntry
   ACCESS   not-accessible
   STATUS   mandatory
   DESCRIPTION
      "This table contains "
   ::= { sfcsBwPortPools 1 }

sfcsBwPortPoolLimitsEntry   OBJECT-TYPE
   SYNTAX   SfcsBwPortPoolLimitsEntry
   ACCESS   not-accessible
   STATUS   mandatory
   DESCRIPTION
      "Each entry contains "
   INDEX   { sfcsBwPortPoolLimitsIndex, sfcsBwPortPoolLimitsPoolIndex }
   ::= { sfcsBwPortPoolLimitsTable 1 }

SfcsBwPortPoolLimitsEntry ::=
   SEQUENCE
   {
      sfcsBwPortPoolLimitsIndex              INTEGER,
      sfcsBwPortPoolLimitsPoolIndex          INTEGER,
      sfcsBwPortPoolLimitsMaxAllocBwFwd      INTEGER,
      sfcsBwPortPoolLimitsMaxAllocBwRev      INTEGER,
      sfcsBwPortPoolLimitsBwAllocStrat       INTEGER,
      sfcsBwPortPoolLimitsBwConstant         INTEGER,
      sfcsBwPortPoolLimitsCBRLimitFwd        INTEGER,
      sfcsBwPortPoolLimitsCBRLimitRev        INTEGER,
      sfcsBwPortPoolLimitsABRLimitFwd        INTEGER,
      sfcsBwPortPoolLimitsABRLimitRev        INTEGER,
      sfcsBwPortPoolLimitsVBRLimitFwd        INTEGER,
      sfcsBwPortPoolLimitsVBRLimitRev        INTEGER,
      sfcsBwPortPoolLimitsUBRLimitFwd        INTEGER,
      sfcsBwPortPoolLimitsUBRLimitRev        INTEGER,
      sfcsBwPortPoolLimitsUBRConnLimitFwd    INTEGER,
      sfcsBwPortPoolLimitsUBRConnLimitRev    INTEGER
   }

--   # Limit Definitions
sfcsBwPortPoolLimitsIndex   OBJECT-TYPE
   SYNTAX   INTEGER
   ACCESS   read-only
   STATUS   mandatory
   DESCRIPTION
      "This index specifies which Port we are dealing
       with.  This reference is in the same format as MIB II's
       Interface index."
   ::= { sfcsBwPortPoolLimitsEntry 1 }

sfcsBwPortPoolLimitsPoolIndex   OBJECT-TYPE
   SYNTAX   INTEGER
   ACCESS   read-only
   STATUS   mandatory
   DESCRIPTION
      "This index specifies which Pool within Port we are dealing
       with.  This reference is in the same format as MIB II's
       Interface index."
   ::= { sfcsBwPortPoolLimitsEntry 2 }

sfcsBwPortPoolLimitsMaxAllocBwFwd      OBJECT-TYPE
   SYNTAX   INTEGER
   ACCESS   read-write
   STATUS   mandatory
   DESCRIPTION
      " Upper Limit for BW to be allocated forward direction. It is defaulted to
        the physical BW and is set by administrative action. Can't be set to
        a value greater than physical BW"
   ::= { sfcsBwPortPoolLimitsEntry 3 }

sfcsBwPortPoolLimitsMaxAllocBwRev      OBJECT-TYPE
   SYNTAX   INTEGER
   ACCESS   read-write
   STATUS   mandatory
   DESCRIPTION
      " Upper Limit for BW to be allocated reverse direction. It is defaulted to
        the physical BW and is set by administrative action. Can't be set to
        a value greater than physical BW"

   ::= { sfcsBwPortPoolLimitsEntry 4 }

sfcsBwPortPoolLimitsBwAllocStrat      OBJECT-TYPE
   SYNTAX   INTEGER
   ACCESS   read-write
   STATUS   mandatory
   DESCRIPTION
      "  Determines which of 3 sets of formulas will be used for computing
         the amount of variable bandwidth to be allocated. 
         Conservative allocates the full amount of variable bandwidth,
         Moderate allocates approximately half of the variable bandwidth,
         Liberal supports very aggressive allocation and should only be
         used with caution. Conservative is the default."
   ::= { sfcsBwPortPoolLimitsEntry 5 }

sfcsBwPortPoolLimitsBwConstant      OBJECT-TYPE
   SYNTAX   INTEGER
   ACCESS   read-write
   STATUS   mandatory
   DESCRIPTION
      " A ratio used in formulas for computing the amount of variable 
        bandwidth to be allocated. Valid values are 1-255 which is the
        numerator of a fraction whose fixed denominator is 256. Thus
        the value 255 is really 255/256 the most conservative value;
        the value 1 is really 1/256 the most liberal value; the value
        128 is really 128/256 or 50%. The default is 50%."
   ::= { sfcsBwPortPoolLimitsEntry 6 }

sfcsBwPortPoolLimitsCBRLimitFwd      OBJECT-TYPE
   SYNTAX   INTEGER
   ACCESS   read-write
   STATUS   mandatory
   DESCRIPTION
      " A ratio used in allocating the allocatable bandwidth among the 
        various Service classes. This value is the amount of the overall
        allocatable bw that can be allocated to CBR. The values are 1-255.
        For a more detailed description of value useage see
        sfcsBwPortPoolLimitsBwConstant. Total of all service classes for a
        given direction should not exceed 256. (If it has never been set,
        the value will be -1.)"
   ::= { sfcsBwPortPoolLimitsEntry 7 }

sfcsBwPortPoolLimitsCBRLimitRev      OBJECT-TYPE
   SYNTAX   INTEGER
   ACCESS   read-write
   STATUS   mandatory
   DESCRIPTION
      " A ratio used in allocating the allocatable bandwidth among the 
        various Service classes. This value is the amount of the overall
        allocatable bw that can be allocated to CBR. The values are 1-255.
        For a more detailed description of value useage see
        sfcsBwPortPoolLimitsBwConstant. Total of all service classes for a
        given direction should not exceed 256. (If it has never been set,
        the value will be -1.)"
   ::= { sfcsBwPortPoolLimitsEntry 8 }

sfcsBwPortPoolLimitsABRLimitFwd      OBJECT-TYPE
   SYNTAX   INTEGER
   ACCESS   read-write
   STATUS   mandatory
   DESCRIPTION
      " A ratio used in allocating the allocatable bandwidth among the 
        various Service classes. This value is the amount of the overall
        allocatable bw that can be allocated to ABR. The values are 1-255.
        For a more detailed description of value useage see
        sfcsBwPortPoolLimitsBwConstant. Total of all service classes for a
        given direction should not exceed 256. (If it has never been set,
        the value will be -1.)"
   ::= { sfcsBwPortPoolLimitsEntry 9 }

sfcsBwPortPoolLimitsABRLimitRev      OBJECT-TYPE
   SYNTAX   INTEGER
   ACCESS   read-write
   STATUS   mandatory
   DESCRIPTION
      " A ratio used in allocating the allocatable bandwidth among the 
        various Service classes. This value is the amount of the overall
        allocatable bw that can be allocated to ABR. The values are 1-255.
        For a more detailed description of value useage see
        sfcsBwPortPoolLimitsBwConstant. Total of all service classes for a
        given direction should not exceed 256. (If it has never been set,
        the value will be -1.)"
   ::= { sfcsBwPortPoolLimitsEntry 10 }

sfcsBwPortPoolLimitsVBRLimitFwd      OBJECT-TYPE
   SYNTAX   INTEGER
   ACCESS   read-write
   STATUS   mandatory
   DESCRIPTION
      " A ratio used in allocating the allocatable bandwidth among the 
        various Service classes. This value is the amount of the overall
        allocatable bw that can be allocated to VBR. The values are 1-255.
        For a more detailed description of value useage see
        sfcsBwPortPoolLimitsBwConstant. Total of all service classes for a
        given direction should not exceed 256. (If it has never been set,
        the value will be -1.)
        WARNING - Setting this limit to an arbitrarily low value may 
        cause the switch to become inoperable as an SVC switch. PNNI
        establishes VBR connections for switch to switch communications.
        If an arbitrarily low limit is established, it may preclude
        PNNI inter-switch operability." 
   ::= { sfcsBwPortPoolLimitsEntry 11 }

sfcsBwPortPoolLimitsVBRLimitRev      OBJECT-TYPE
   SYNTAX   INTEGER
   ACCESS   read-write
   STATUS   mandatory
   DESCRIPTION
      " A ratio used in allocating the allocatable bandwidth among the 
        various Service classes. This value is the amount of the overall
        allocatable bw that can be allocated to VBR. The values are 1-255.
        For a more detailed description of value useage see
        sfcsBwPortPoolLimitsBwConstant. Total of all service classes for a
        given direction should not exceed 256. (If it has never been set,
        the value will be -1.)
        WARNING - Setting this limit to an arbitrarily low value may 
        cause the switch to become inoperable as an SVC switch. PNNI 
        establishes VBR connections for switch to switch communications.
        If an arbitrarily low limit is established, it may preclude 
        PNNI inter-switch operability."
   ::= { sfcsBwPortPoolLimitsEntry 12 }

sfcsBwPortPoolLimitsUBRLimitFwd      OBJECT-TYPE
   SYNTAX   INTEGER
   ACCESS   read-write
   STATUS   mandatory
   DESCRIPTION
      " A ratio used in allocating the allocatable bandwidth among the 
        various Service classes. This value is the amount of the overall
        allocatable bw that can be allocated to UBR. The values are 1-255.
        For a more detailed description of value useage see
        sfcsBwPortPoolLimitsBwConstant. Total of all service classes for a
        given direction should not exceed 256. (If it has never been set,
        the value will be -1.)
        WARNING - Setting this limit to an arbitrarily low value may 
        cause the switch to become inoperable as an SVC switch. Many
        internal management functions use UBR connections to establish
        connections with neighboring switches for keep alive and 
        discovery functions.  
        If an arbitrarily low limit is established, it may preclude 
        SVC inter-switch operability."
   ::= { sfcsBwPortPoolLimitsEntry 13 }

sfcsBwPortPoolLimitsUBRLimitRev      OBJECT-TYPE
   SYNTAX   INTEGER
   ACCESS   read-write
   STATUS   mandatory
   DESCRIPTION
      " A ratio used in allocating the allocatable bandwidth among the 
        various Service classes. This value is the amount of the overall
        allocatable bw that can be allocated to UBR. The values are 1-255.
        For a more detailed description of value useage see
        sfcsBwPortPoolLimitsBwConstant. Total of all service classes for a
        given direction should not exceed 256. (If it has never been set,
        the value will be -1.)
        WARNING - Setting this limit to an arbitrarily low value may 
        cause the switch to become inoperable as an SVC switch. Many 
        internal management functions use UBR connections to establish
        connections with neighboring switches for keep alive and 
        discovery functions. 
        If an arbitrarily low limit is established, it may preclude 
        SVC inter-switch operability."
   ::= { sfcsBwPortPoolLimitsEntry 14 }

sfcsBwPortPoolLimitsUBRConnLimitFwd      OBJECT-TYPE
   SYNTAX   INTEGER
   ACCESS   read-write
   STATUS   mandatory
   DESCRIPTION
      " A Limit to the number of UBR connections which can be established
        through this port. The limit applies to both user connections and
        management connections. The default is no limit. (If it has never
        been set, the value will be -1.)"
   ::= { sfcsBwPortPoolLimitsEntry 15 }

sfcsBwPortPoolLimitsUBRConnLimitRev      OBJECT-TYPE
   SYNTAX   INTEGER
   ACCESS   read-write
   STATUS   mandatory
   DESCRIPTION
      " A Limit to the number of UBR connections which can be established
        through this port. The limit applies to both user connections and
        management connections. The default is no limit.  (If it has never
        been set, the value will be -1.)"
   ::= { sfcsBwPortPoolLimitsEntry 16 }

--  %%%%%%%%%%%%%%%%%%%%%%%%%%%%%%%%%%%%%%%%%%%%%%%%%%%%%%%%%%%%%%%%%%%%%%%%%%%%%%%%%%%%%
--  ### Bandwidth Pool Statistical Information

sfcsBwPortPoolStatTable   OBJECT-TYPE
   SYNTAX   SEQUENCE OF SfcsBwPortPoolStatEntry
   ACCESS   not-accessible
   STATUS   mandatory
   DESCRIPTION
      "This table contains "
   ::= { sfcsBwPortPools 2 }

sfcsBwPortPoolStatEntry   OBJECT-TYPE
   SYNTAX   SfcsBwPortPoolStatEntry
   ACCESS   not-accessible 
   STATUS   mandatory
   DESCRIPTION
      "Each entry contains "
   INDEX   { sfcsBwPortPoolStatsIndex, sfcsBwPortPoolStatsPoolIndex }
   ::= { sfcsBwPortPoolStatTable 1 }

SfcsBwPortPoolStatEntry ::=
   SEQUENCE
   {
      sfcsBwPortPoolStatsIndex                 INTEGER,
      sfcsBwPortPoolStatsPoolIndex             INTEGER,
      sfcsBwPortPoolStatConnCntFwd             INTEGER,
      sfcsBwPortPoolStatConnCntRev             INTEGER,
      sfcsBwPortPoolStatAllocBwFwd             INTEGER,
      sfcsBwPortPoolStatAllocBwRev             INTEGER,
      sfcsBwPortPoolStatAvailBwFwd             INTEGER,
      sfcsBwPortPoolStatAvailBwRev             INTEGER,
      sfcsBwPortPoolStatPeakBwFwd              INTEGER,
      sfcsBwPortPoolStatPeakBwRev              INTEGER,
      sfcsBwPortPoolStatRejConnFwd             INTEGER,
      sfcsBwPortPoolStatRejConnRev             INTEGER,
      sfcsBwPortPoolStatPrevAdverMAXCRFwd      INTEGER,
      sfcsBwPortPoolStatPrevAdverMAXCRRev      INTEGER,
      sfcsBwPortPoolStatPrevAdverAvailCRFwd    INTEGER,
      sfcsBwPortPoolStatPrevAdverAvailCRRev    INTEGER,

      sfcsBwPortPoolStatCBRConnCntFwd          INTEGER,
      sfcsBwPortPoolStatCBRConnCntRev          INTEGER,
      sfcsBwPortPoolStatCBRConnRejFwd          INTEGER,
      sfcsBwPortPoolStatCBRConnRejRev          INTEGER,
      sfcsBwPortPoolStatCBRAllocBwFwd          INTEGER,
      sfcsBwPortPoolStatCBRAllocBwRev          INTEGER,
      sfcsBwPortPoolStatCBRAggPCRFwd           INTEGER,
      sfcsBwPortPoolStatCBRAggPCRRev           INTEGER,
      sfcsBwPortPoolStatCBRPrevAdverMAXCTD     INTEGER,
      sfcsBwPortPoolStatCBRPrevAdverCDV        INTEGER,

      sfcsBwPortPoolStatABRConnCntFwd          INTEGER,
      sfcsBwPortPoolStatABRConnCntRev          INTEGER,
      sfcsBwPortPoolStatABRConnRejFwd          INTEGER,
      sfcsBwPortPoolStatABRConnRejRev          INTEGER,
      sfcsBwPortPoolStatABRAllocBwFwd          INTEGER,
      sfcsBwPortPoolStatABRAllocBwRev          INTEGER,
      sfcsBwPortPoolStatABRAggPCRFwd           INTEGER,
      sfcsBwPortPoolStatABRAggPCRRev           INTEGER,
      sfcsBwPortPoolStatABRPrevAdverMAXCTD     INTEGER,
      sfcsBwPortPoolStatABRPrevAdverCDV        INTEGER,

      sfcsBwPortPoolStatVBRConnCntFwd          INTEGER,
      sfcsBwPortPoolStatVBRConnCntRev          INTEGER,
      sfcsBwPortPoolStatVBRConnRejFwd          INTEGER,
      sfcsBwPortPoolStatVBRConnRejRev          INTEGER,
      sfcsBwPortPoolStatVBRAllocBwFwd          INTEGER,
      sfcsBwPortPoolStatVBRAllocBwRev          INTEGER,
      sfcsBwPortPoolStatVBRAggPCRFwd           INTEGER,
      sfcsBwPortPoolStatVBRAggPCRRev           INTEGER,
      sfcsBwPortPoolStatVBRPrevAdverMAXCTD     INTEGER,
      sfcsBwPortPoolStatVBRPrevAdverCDV        INTEGER,

      sfcsBwPortPoolStatUBRConnCntFwd          INTEGER,
      sfcsBwPortPoolStatUBRConnCntRev          INTEGER,
      sfcsBwPortPoolStatUBRConnRejFwd          INTEGER,
      sfcsBwPortPoolStatUBRConnRejRev          INTEGER,
      sfcsBwPortPoolStatUBRAllocBwFwd          INTEGER,
      sfcsBwPortPoolStatUBRAllocBwRev          INTEGER,
      sfcsBwPortPoolStatUBRAggPCRFwd           INTEGER,
      sfcsBwPortPoolStatUBRAggPCRRev           INTEGER,
      sfcsBwPortPoolStatUBRPrevAdverMAXCTD     INTEGER,
      sfcsBwPortPoolStatUBRPrevAdverCDV        INTEGER
}

sfcsBwPortPoolStatsIndex   OBJECT-TYPE
   SYNTAX   INTEGER
   ACCESS   read-only
   STATUS   mandatory
   DESCRIPTION
      "This index specifies which Port we are dealing
       with.  This reference is in the same format as MIB II's
       Interface index."
   ::= { sfcsBwPortPoolStatEntry 1 }

sfcsBwPortPoolStatsPoolIndex   OBJECT-TYPE
   SYNTAX   INTEGER
   ACCESS   read-only
   STATUS   mandatory
   DESCRIPTION
      "This index specifies which Pool within Port we are dealing
       with.  This reference is in the same format as MIB II's
       Interface index."
   ::= { sfcsBwPortPoolStatEntry 2 }

sfcsBwPortPoolStatConnCntFwd   OBJECT-TYPE
   SYNTAX   INTEGER
   ACCESS   read-only
   STATUS   mandatory
   DESCRIPTION
	" The current total number of calls in the forward direction."
   ::= { sfcsBwPortPoolStatEntry 3 }

sfcsBwPortPoolStatConnCntRev   OBJECT-TYPE
   SYNTAX   INTEGER
   ACCESS   read-only
   STATUS   mandatory
   DESCRIPTION
	" The current total number of calls in the reverse direction."
   ::= { sfcsBwPortPoolStatEntry 4 }

sfcsBwPortPoolStatAllocBwFwd   OBJECT-TYPE
   SYNTAX   INTEGER
   ACCESS   read-only
   STATUS   mandatory
   DESCRIPTION
	" The current amount of allocated Bw in the forward direction."
   ::= { sfcsBwPortPoolStatEntry 5 }

sfcsBwPortPoolStatAllocBwRev   OBJECT-TYPE
   SYNTAX   INTEGER
   ACCESS   read-only
   STATUS   mandatory
   DESCRIPTION
	" The current amount of allocated Bw in the reverse direction."
   ::= { sfcsBwPortPoolStatEntry 6 }

sfcsBwPortPoolStatAvailBwFwd   OBJECT-TYPE
   SYNTAX   INTEGER
   ACCESS   read-only
   STATUS   mandatory
   DESCRIPTION
	" The current amount of available Bw in the forward direction."
   ::= { sfcsBwPortPoolStatEntry 7 }

sfcsBwPortPoolStatAvailBwRev   OBJECT-TYPE
   SYNTAX   INTEGER
   ACCESS   read-only
   STATUS   mandatory
   DESCRIPTION
	" The current amount of available Bw in the reverse direction."
   ::= { sfcsBwPortPoolStatEntry 8 }

sfcsBwPortPoolStatPeakBwFwd   OBJECT-TYPE
   SYNTAX   INTEGER
   ACCESS   read-only
   STATUS   mandatory
   DESCRIPTION
	" The peak amount of allocated Bw in the forward direction since the 
      port was initialized OR the switch was reset."
   ::= { sfcsBwPortPoolStatEntry 9 }

sfcsBwPortPoolStatPeakBwRev   OBJECT-TYPE
   SYNTAX   INTEGER
   ACCESS   read-only
   STATUS   mandatory
   DESCRIPTION
    " The peak amount of allocated Bw in the reverse direction since the 
      port was initialized OR the switch was reset."
   ::= { sfcsBwPortPoolStatEntry 10 }

sfcsBwPortPoolStatRejConnFwd   OBJECT-TYPE
   SYNTAX   INTEGER
   ACCESS   read-only
   STATUS   mandatory
   DESCRIPTION
	" The number of connections which were rejected because of 
      insufficient forward bandwidth since the port was initialized or
      the switch was reset last."
   ::= { sfcsBwPortPoolStatEntry 11 }

sfcsBwPortPoolStatRejConnRev   OBJECT-TYPE
   SYNTAX   INTEGER
   ACCESS   read-only
   STATUS   mandatory
   DESCRIPTION
    " The number of connections which were rejected because of 
      insufficient reverse bandwidth since the port was initialized or
      the switch was reset last."
   ::= { sfcsBwPortPoolStatEntry 12 }

sfcsBwPortPoolStatPrevAdverMAXCRFwd   OBJECT-TYPE
   SYNTAX   INTEGER
   ACCESS   read-only
   STATUS   mandatory
   DESCRIPTION
	" The amount of physical forward BW reported to PNNI in the latest
      reporting period."
   ::= { sfcsBwPortPoolStatEntry 13 }

sfcsBwPortPoolStatPrevAdverMAXCRRev   OBJECT-TYPE
   SYNTAX   INTEGER
   ACCESS   read-only
   STATUS   mandatory
   DESCRIPTION
    " The amount of physical reverse BW reported to PNNI in the latest
      reporting period."
   ::= { sfcsBwPortPoolStatEntry 14 }

sfcsBwPortPoolStatPrevAdverAvailCRFwd   OBJECT-TYPE
   SYNTAX   INTEGER
   ACCESS   read-only
   STATUS   mandatory
   DESCRIPTION
    " The amount of avail forward BW reported to PNNI in the latest
      reporting period."
   ::= { sfcsBwPortPoolStatEntry 15 }

sfcsBwPortPoolStatPrevAdverAvailCRRev   OBJECT-TYPE
   SYNTAX   INTEGER
   ACCESS   read-only
   STATUS   mandatory
   DESCRIPTION
    " The amount of avail reverse BW reported to PNNI in the latest
      reporting period."
   ::= { sfcsBwPortPoolStatEntry 16 }

--  # CBR Info

sfcsBwPortPoolStatCBRConnCntFwd   OBJECT-TYPE
   SYNTAX   INTEGER
   ACCESS   read-only
   STATUS   mandatory
   DESCRIPTION
	" The number of currently established CBR connections for the forward
      direction."
   ::= { sfcsBwPortPoolStatEntry 17 }

sfcsBwPortPoolStatCBRConnCntRev   OBJECT-TYPE
   SYNTAX   INTEGER
   ACCESS   read-only
   STATUS   mandatory
   DESCRIPTION
    " The number of currently established CBR connections for the reverse
      direction."
   ::= { sfcsBwPortPoolStatEntry 18 }

sfcsBwPortPoolStatCBRConnRejFwd   OBJECT-TYPE
   SYNTAX   INTEGER
   ACCESS   read-only
   STATUS   mandatory
   DESCRIPTION
	" The number of CBR forward connections rejected since the port was 
      initialized or the switch was reset last."
   ::= { sfcsBwPortPoolStatEntry 19 }

sfcsBwPortPoolStatCBRConnRejRev   OBJECT-TYPE
   SYNTAX   INTEGER
   ACCESS   read-only
   STATUS   mandatory
   DESCRIPTION
    " The number of CBR reverse connections rejected since the port was
      initialized or the switch was reset last."
   ::= { sfcsBwPortPoolStatEntry 20 }

sfcsBwPortPoolStatCBRAllocBwFwd   OBJECT-TYPE
   SYNTAX   INTEGER
   ACCESS   read-only
   STATUS   mandatory
   DESCRIPTION
	" The amount of forward allocated Bw that is CBR service class."
   ::= { sfcsBwPortPoolStatEntry 21 }

sfcsBwPortPoolStatCBRAllocBwRev   OBJECT-TYPE
   SYNTAX   INTEGER
   ACCESS   read-only
   STATUS   mandatory
   DESCRIPTION
	" The amount of reverse allocated Bw that is CBR service class."
   ::= { sfcsBwPortPoolStatEntry 22 }

sfcsBwPortPoolStatCBRAggPCRFwd   OBJECT-TYPE
   SYNTAX   INTEGER
   ACCESS   read-only
   STATUS   mandatory
   DESCRIPTION
	" The aggregated forward PCR for all established CBR connections."
   ::= { sfcsBwPortPoolStatEntry 23 }

sfcsBwPortPoolStatCBRAggPCRRev   OBJECT-TYPE
   SYNTAX   INTEGER
   ACCESS   read-only
   STATUS   mandatory
   DESCRIPTION
    " The aggregated reverse PCR for all established CBR connections."
   ::= { sfcsBwPortPoolStatEntry 24 }

sfcsBwPortPoolStatCBRPrevAdverMAXCTD   OBJECT-TYPE
   SYNTAX   INTEGER
   ACCESS   read-only
   STATUS   mandatory
   DESCRIPTION
	" The maxCTD for the forward direction reported to PNNI for the last
      update period for CBR service class."
   ::= { sfcsBwPortPoolStatEntry 25 }

sfcsBwPortPoolStatCBRPrevAdverCDV   OBJECT-TYPE
   SYNTAX   INTEGER
   ACCESS   read-only
   STATUS   mandatory
   DESCRIPTION
    " The CDV for the forward direction reported to PNNI for the last
      update period for CBR service class."
   ::= { sfcsBwPortPoolStatEntry 26 }

--  # ABR Information

sfcsBwPortPoolStatABRConnCntFwd   OBJECT-TYPE
   SYNTAX   INTEGER
   ACCESS   read-only
   STATUS   mandatory
   DESCRIPTION
    " The number of currently established ABR connections for the forward
      direction."
   ::= { sfcsBwPortPoolStatEntry 27 }

sfcsBwPortPoolStatABRConnCntRev   OBJECT-TYPE
   SYNTAX   INTEGER
   ACCESS   read-only
   STATUS   mandatory
   DESCRIPTION
    " The number of currently established ABR connections for the reverse
      direction."
   ::= { sfcsBwPortPoolStatEntry 28 }

sfcsBwPortPoolStatABRConnRejFwd   OBJECT-TYPE
   SYNTAX   INTEGER
   ACCESS   read-only
   STATUS   mandatory
   DESCRIPTION
    " The number of ABR forward connections rejected since the port was
      initialized or the switch was reset last."
   ::= { sfcsBwPortPoolStatEntry 29 }

sfcsBwPortPoolStatABRConnRejRev   OBJECT-TYPE
   SYNTAX   INTEGER
   ACCESS   read-only
   STATUS   mandatory
   DESCRIPTION
    " The number of ABR reverse connections rejected since the port was
      initialized or the switch was reset last."
   ::= { sfcsBwPortPoolStatEntry 30 }

sfcsBwPortPoolStatABRAllocBwFwd   OBJECT-TYPE
   SYNTAX   INTEGER
   ACCESS   read-only
   STATUS   mandatory
   DESCRIPTION
    " The amount of forward allocated Bw that is ABR service class."
   ::= { sfcsBwPortPoolStatEntry 31 }

sfcsBwPortPoolStatABRAllocBwRev   OBJECT-TYPE
   SYNTAX   INTEGER
   ACCESS   read-only
   STATUS   mandatory
   DESCRIPTION
    " The amount of reverse allocated Bw that is ABR service class."
   ::= { sfcsBwPortPoolStatEntry 32 }

sfcsBwPortPoolStatABRAggPCRFwd   OBJECT-TYPE
   SYNTAX   INTEGER
   ACCESS   read-only
   STATUS   mandatory
   DESCRIPTION
    " The aggregated forward PCR for all established ABR connections."
   ::= { sfcsBwPortPoolStatEntry 33 }

sfcsBwPortPoolStatABRAggPCRRev   OBJECT-TYPE
   SYNTAX   INTEGER
   ACCESS   read-only
   STATUS   mandatory
   DESCRIPTION
    " The aggregated reverse PCR for all established ABR connections."
   ::= { sfcsBwPortPoolStatEntry 34 }

sfcsBwPortPoolStatABRPrevAdverMAXCTD   OBJECT-TYPE
   SYNTAX   INTEGER
   ACCESS   read-only
   STATUS   mandatory
   DESCRIPTION
    " The maxCTD for the forward direction reported to PNNI for the last
      update period for ABR service class."
   ::= { sfcsBwPortPoolStatEntry 35 }

sfcsBwPortPoolStatABRPrevAdverCDV   OBJECT-TYPE
   SYNTAX   INTEGER
   ACCESS   read-only
   STATUS   mandatory
   DESCRIPTION
    " The CDV for the forward direction reported to PNNI for the last
      update period for ABR service class."
   ::= { sfcsBwPortPoolStatEntry 36 }

--  # VBR Information

sfcsBwPortPoolStatVBRConnCntFwd   OBJECT-TYPE
   SYNTAX   INTEGER
   ACCESS   read-only
   STATUS   mandatory
   DESCRIPTION
    " The number of currently established VBR connections for the forward
      direction."
   ::= { sfcsBwPortPoolStatEntry 37 }

sfcsBwPortPoolStatVBRConnCntRev   OBJECT-TYPE
   SYNTAX   INTEGER
   ACCESS   read-only
   STATUS   mandatory
   DESCRIPTION
    " The number of currently established VBR connections for the reverse
      direction."
   ::= { sfcsBwPortPoolStatEntry 38 }

sfcsBwPortPoolStatVBRConnRejFwd   OBJECT-TYPE
   SYNTAX   INTEGER
   ACCESS   read-only
   STATUS   mandatory
   DESCRIPTION
    " The number of VBR forward connections rejected since the port was
      initialized or the switch was reset last."
   ::= { sfcsBwPortPoolStatEntry 39 }

sfcsBwPortPoolStatVBRConnRejRev   OBJECT-TYPE
   SYNTAX   INTEGER
   ACCESS   read-only
   STATUS   mandatory
   DESCRIPTION
    " The number of VBR reverse connections rejected since the port was
      initialized or the switch was reset last."
   ::= { sfcsBwPortPoolStatEntry 40 }

sfcsBwPortPoolStatVBRAllocBwFwd   OBJECT-TYPE
   SYNTAX   INTEGER
   ACCESS   read-only
   STATUS   mandatory
   DESCRIPTION
    " The amount of forward allocated Bw that is VBR service class."
   ::= { sfcsBwPortPoolStatEntry 41 }

sfcsBwPortPoolStatVBRAllocBwRev   OBJECT-TYPE
   SYNTAX   INTEGER
   ACCESS   read-only
   STATUS   mandatory
   DESCRIPTION
    " The amount of reverse allocated Bw that is VBR service class."
   ::= { sfcsBwPortPoolStatEntry 42 }

sfcsBwPortPoolStatVBRAggPCRFwd   OBJECT-TYPE
   SYNTAX   INTEGER
   ACCESS   read-only
   STATUS   mandatory
   DESCRIPTION
    " The aggregated forward PCR for all established VBR connections."
   ::= { sfcsBwPortPoolStatEntry 43 }

sfcsBwPortPoolStatVBRAggPCRRev   OBJECT-TYPE
   SYNTAX   INTEGER
   ACCESS   read-only
   STATUS   mandatory
   DESCRIPTION
    " The aggregated reverse PCR for all established VBR connections."
   ::= { sfcsBwPortPoolStatEntry 44 }

sfcsBwPortPoolStatVBRPrevAdverMAXCTD   OBJECT-TYPE
   SYNTAX   INTEGER
   ACCESS   read-only
   STATUS   mandatory
   DESCRIPTION
    " The maxCTD for the forward direction reported to PNNI for the last
      update period for VBR service class."
   ::= { sfcsBwPortPoolStatEntry 45 }

sfcsBwPortPoolStatVBRPrevAdverCDV   OBJECT-TYPE
   SYNTAX   INTEGER
   ACCESS   read-only
   STATUS   mandatory
   DESCRIPTION
    " The CDV for the forward direction reported to PNNI for the last
      update period for VBR service class."
   ::= { sfcsBwPortPoolStatEntry 46 }

--  # UBR Information

sfcsBwPortPoolStatUBRConnCntFwd   OBJECT-TYPE
   SYNTAX   INTEGER
   ACCESS   read-only
   STATUS   mandatory
   DESCRIPTION
    " The number of currently established UBR connections for the forward
      direction."
   ::= { sfcsBwPortPoolStatEntry 47 }

sfcsBwPortPoolStatUBRConnCntRev   OBJECT-TYPE
   SYNTAX   INTEGER
   ACCESS   read-only
   STATUS   mandatory
   DESCRIPTION
    " The number of currently established UBR connections for the reverse
      direction."
   ::= { sfcsBwPortPoolStatEntry 48 }

sfcsBwPortPoolStatUBRConnRejFwd   OBJECT-TYPE
   SYNTAX   INTEGER
   ACCESS   read-only
   STATUS   mandatory
   DESCRIPTION
    " The number of UBR forward connections rejected since the port was
      initialized or the switch was reset last."
   ::= { sfcsBwPortPoolStatEntry 49 }

sfcsBwPortPoolStatUBRConnRejRev   OBJECT-TYPE
   SYNTAX   INTEGER
   ACCESS   read-only
   STATUS   mandatory
   DESCRIPTION
    " The number of UBR reverse connections rejected since the port was
      initialized or the switch was reset last."
   ::= { sfcsBwPortPoolStatEntry 50 }

sfcsBwPortPoolStatUBRAllocBwFwd   OBJECT-TYPE
   SYNTAX   INTEGER
   ACCESS   read-only
   STATUS   mandatory
   DESCRIPTION
    " The amount of forward allocated Bw that is UBR service class."
   ::= { sfcsBwPortPoolStatEntry 51 }

sfcsBwPortPoolStatUBRAllocBwRev   OBJECT-TYPE
   SYNTAX   INTEGER
   ACCESS   read-only
   STATUS   mandatory
   DESCRIPTION
    " The amount of reverse allocated Bw that is UBR service class."
   ::= { sfcsBwPortPoolStatEntry 52 }

sfcsBwPortPoolStatUBRAggPCRFwd   OBJECT-TYPE
   SYNTAX   INTEGER
   ACCESS   read-only
   STATUS   mandatory
   DESCRIPTION
    " The aggregated forward PCR for all established UBR connections."
   ::= { sfcsBwPortPoolStatEntry 53 }

sfcsBwPortPoolStatUBRAggPCRRev   OBJECT-TYPE
   SYNTAX   INTEGER
   ACCESS   read-only
   STATUS   mandatory
   DESCRIPTION
    " The aggregated reverse PCR for all established UBR connections."
   ::= { sfcsBwPortPoolStatEntry 54 }

sfcsBwPortPoolStatUBRPrevAdverMAXCTD   OBJECT-TYPE
   SYNTAX   INTEGER
   ACCESS   read-only
   STATUS   mandatory
   DESCRIPTION
    " The maxCTD for the forward direction reported to PNNI for the last
      update period for UBR service class."
   ::= { sfcsBwPortPoolStatEntry 55 }

sfcsBwPortPoolStatUBRPrevAdverCDV   OBJECT-TYPE
   SYNTAX   INTEGER
   ACCESS   read-only
   STATUS   mandatory
   DESCRIPTION
    " The CDV for the forward direction reported to PNNI for the last
      update period for UBR service class."
   ::= { sfcsBwPortPoolStatEntry 56 }

--  %%%%%%%%%%%%%%%%%%%%%%%%%%%%%%%%%%%%%%%%%%%%%%%%%%%%%%%%%%%%%%%%%%%%%%%%%%%%%%%%%%%%%
--  ### Bandwidth Pool Trap Management Information

sfcsBwPortPoolTrapMgmtTable   OBJECT-TYPE
   SYNTAX   SEQUENCE OF SfcsBwPortPoolTrapMgmtEntry
   ACCESS   not-accessible
   STATUS   mandatory
   DESCRIPTION
      "This table contains "
   ::= { sfcsBwPortPools 3 }

sfcsBwPortPoolTrapMgmtEntry   OBJECT-TYPE
   SYNTAX   SfcsBwPortPoolTrapMgmtEntry
   ACCESS   not-accessible
   STATUS   mandatory
   DESCRIPTION
      "Each entry contains "
   INDEX   { sfcsBwPortPoolTrapMgmtIndex, sfcsBwPortPoolTrapMgmtPoolIndex }
   ::= { sfcsBwPortPoolTrapMgmtTable 1 }

SfcsBwPortPoolTrapMgmtEntry ::=
   SEQUENCE
   {
      sfcsBwPortPoolTrapMgmtIndex                 INTEGER,
      sfcsBwPortPoolTrapMgmtPoolIndex             INTEGER,
      sfcsBwPortPoolTrapMgmtAllocBwTholdHiFwd     INTEGER,
      sfcsBwPortPoolTrapMgmtAllocBwTholdHiRev     INTEGER,
      sfcsBwPortPoolTrapMgmtAllocBwTholdLoFwd     INTEGER,
      sfcsBwPortPoolTrapMgmtAllocBwTholdLoRev     INTEGER,
      sfcsBwPortPoolTrapMgmtPeakBwTholdFwd        INTEGER,
      sfcsBwPortPoolTrapMgmtPeakBwTholdRev        INTEGER,
      sfcsBwPortPoolTrapMgmtHoldDownTime          INTEGER,

      sfcsBwPortPoolTrapMgmtCBRConnCntTholdHiFwd  INTEGER,
      sfcsBwPortPoolTrapMgmtCBRConnCntTholdHiRev  INTEGER,
      sfcsBwPortPoolTrapMgmtCBRConnCntTholdLoFwd  INTEGER,
      sfcsBwPortPoolTrapMgmtCBRConnCntTholdLoRev  INTEGER,
      sfcsBwPortPoolTrapMgmtCBRAllocBwTholdHiFwd  INTEGER,
      sfcsBwPortPoolTrapMgmtCBRAllocBwTholdHiRev  INTEGER,
      sfcsBwPortPoolTrapMgmtCBRAllocBwTholdLoFwd  INTEGER,
      sfcsBwPortPoolTrapMgmtCBRAllocBwTholdLoRev  INTEGER,

      sfcsBwPortPoolTrapMgmtABRConnCntTholdHiFwd  INTEGER,
      sfcsBwPortPoolTrapMgmtABRConnCntTholdHiRev  INTEGER,
      sfcsBwPortPoolTrapMgmtABRConnCntTholdLoFwd  INTEGER,
      sfcsBwPortPoolTrapMgmtABRConnCntTholdLoRev  INTEGER,
      sfcsBwPortPoolTrapMgmtABRAllocBwTholdHiFwd  INTEGER,
      sfcsBwPortPoolTrapMgmtABRAllocBwTholdHiRev  INTEGER,
      sfcsBwPortPoolTrapMgmtABRAllocBwTholdLoFwd  INTEGER,
      sfcsBwPortPoolTrapMgmtABRAllocBwTholdLoRev  INTEGER,

      sfcsBwPortPoolTrapMgmtVBRConnCntTholdHiFwd  INTEGER,
      sfcsBwPortPoolTrapMgmtVBRConnCntTholdHiRev  INTEGER,
      sfcsBwPortPoolTrapMgmtVBRConnCntTholdLoFwd  INTEGER,
      sfcsBwPortPoolTrapMgmtVBRConnCntTholdLoRev  INTEGER,
      sfcsBwPortPoolTrapMgmtVBRAllocBwTholdHiFwd  INTEGER,
      sfcsBwPortPoolTrapMgmtVBRAllocBwTholdHiRev  INTEGER,
      sfcsBwPortPoolTrapMgmtVBRAllocBwTholdLoFwd  INTEGER,
      sfcsBwPortPoolTrapMgmtVBRAllocBwTholdLoRev  INTEGER,

      sfcsBwPortPoolTrapMgmtUBRConnCntTholdHiFwd  INTEGER,
      sfcsBwPortPoolTrapMgmtUBRConnCntTholdHiRev  INTEGER,
      sfcsBwPortPoolTrapMgmtUBRConnCntTholdLoFwd  INTEGER,
      sfcsBwPortPoolTrapMgmtUBRConnCntTholdLoRev  INTEGER,
      sfcsBwPortPoolTrapMgmtUBRAllocBwTholdHiFwd  INTEGER,
      sfcsBwPortPoolTrapMgmtUBRAllocBwTholdHiRev  INTEGER,
      sfcsBwPortPoolTrapMgmtUBRAllocBwTholdLoFwd  INTEGER,
      sfcsBwPortPoolTrapMgmtUBRAllocBwTholdLoRev  INTEGER,
      sfcsBWPortPoolTrapMgmtBuffUpThold           INTEGER,
      sfcsBWPortPoolTrapMgmtBuffLoThold           INTEGER,
      sfcsBWPortPoolTrapMgmtConnRejThold          INTEGER
   }

sfcsBwPortPoolTrapMgmtIndex   OBJECT-TYPE
   SYNTAX   INTEGER
   ACCESS   read-only
   STATUS   mandatory
   DESCRIPTION
      "This index specifies which Port we are dealing
       with.  This reference is in the same format as MIB II's
       Interface index."
   ::= { sfcsBwPortPoolTrapMgmtEntry 1 }

sfcsBwPortPoolTrapMgmtPoolIndex   OBJECT-TYPE
   SYNTAX   INTEGER
   ACCESS   read-only
   STATUS   mandatory
   DESCRIPTION
      "This index specifies which Pool within Port we are dealing
       with.  This reference is in the same format as MIB II's
       Interface index. (If it has never been set, the value will 
       be -1.)"
   ::= { sfcsBwPortPoolTrapMgmtEntry 2 }

sfcsBwPortPoolTrapMgmtAllocBwTholdHiFwd   OBJECT-TYPE
   SYNTAX   INTEGER
   ACCESS   read-write
   STATUS   mandatory
   DESCRIPTION
      "The upper threshold for the Alloc BW fwd trap. When an allocation
       causes the currently allocated bw to exceed this value the trap 
       is generated. (If it has never been set, the value will 
       be -1.)"
   ::= { sfcsBwPortPoolTrapMgmtEntry 3 }

sfcsBwPortPoolTrapMgmtAllocBwTholdHiRev   OBJECT-TYPE
   SYNTAX   INTEGER
   ACCESS   read-write
   STATUS   mandatory
   DESCRIPTION
    " The upper threshold for the Alloc BW rev trap. When an allocation
      causes the currently allocated bw to exceed this value the trap 
      is generated. (If it has never been set, the value will
      be -1.)"
   ::= { sfcsBwPortPoolTrapMgmtEntry 4 }

sfcsBwPortPoolTrapMgmtAllocBwTholdLoFwd   OBJECT-TYPE
   SYNTAX   INTEGER
   ACCESS   read-write
   STATUS   mandatory
   DESCRIPTION
    " The lower threshold for the Alloc BW fwd trap. When an allocation
      causes the currently allocated bw be below this value the trap 
      is generated. (If it has never been set, the value will
      be -1.)"
   ::= { sfcsBwPortPoolTrapMgmtEntry 5 }

sfcsBwPortPoolTrapMgmtAllocBwTholdLoRev   OBJECT-TYPE
   SYNTAX   INTEGER
   ACCESS   read-write
   STATUS   mandatory
   DESCRIPTION
    " The lower threshold for the Alloc BW rev trap. When an allocation
      causes the currently allocated bw be below this value the trap 
      is generated. (If it has never been set, the value will
      be -1.)"
   ::= { sfcsBwPortPoolTrapMgmtEntry 6 }

sfcsBwPortPoolTrapMgmtPeakBwTholdFwd   OBJECT-TYPE
   SYNTAX   INTEGER
   ACCESS   read-write
   STATUS   mandatory
   DESCRIPTION
     "The upper threshold for the Peak BW fwd trap. When an allocation
      causes the allocated BW to exceed this value the trap is generated.
      (If it has never been set, the value will be -1.)"
   ::= { sfcsBwPortPoolTrapMgmtEntry 7 }

sfcsBwPortPoolTrapMgmtPeakBwTholdRev   OBJECT-TYPE
   SYNTAX   INTEGER
   ACCESS   read-write
   STATUS   mandatory
   DESCRIPTION
     "The upper threshold for the Peak BW rev trap. When an allocation
      causes the allocated BW to exceed this value the trap is generated.
      (If it has never been set, the value will be -1.)"
   ::= { sfcsBwPortPoolTrapMgmtEntry 8 }

sfcsBwPortPoolTrapMgmtHoldDownTime   OBJECT-TYPE
   SYNTAX   INTEGER
   ACCESS   read-write
   STATUS   mandatory
   DESCRIPTION
    " The time between traps of the same type. If a trap of a particular
      type is generated for a particular port, another of that type for that
      port will not be generated until the hold down time has expired.
      (If it has never been set, the value will be -1.)"
   ::= { sfcsBwPortPoolTrapMgmtEntry 9 }

--  # CBR Information

sfcsBwPortPoolTrapMgmtCBRConnCntTholdHiFwd   OBJECT-TYPE
   SYNTAX   INTEGER
   ACCESS   read-write
   STATUS   mandatory
   DESCRIPTION
    " The upper threshold for the CBR connection count Fwd trap. When an
      allocation causes the CBR connection count to exceed this value,
      the trap is generated. (If it has never been set, the value will be -1.)"
   ::= { sfcsBwPortPoolTrapMgmtEntry 10 }

sfcsBwPortPoolTrapMgmtCBRConnCntTholdHiRev   OBJECT-TYPE
   SYNTAX   INTEGER
   ACCESS   read-write
   STATUS   mandatory
   DESCRIPTION
    " The upper threshold for the CBR connection count Rev trap. When an
      allocation causes the CBR connection count to exceed this value,
      the trap is generated. (If it has never been set, the value will be -1.)"
   ::= { sfcsBwPortPoolTrapMgmtEntry 11 }

sfcsBwPortPoolTrapMgmtCBRConnCntTholdLoFwd   OBJECT-TYPE
   SYNTAX   INTEGER
   ACCESS   read-write
   STATUS   mandatory
   DESCRIPTION
    " The lower threshold for the CBR connection count Fwd trap. When an
      allocation causes the CBR connection count to fall below this value,
      the trap is generated. (If it has never been set, the value will be -1.)"
   ::= { sfcsBwPortPoolTrapMgmtEntry 12 }

sfcsBwPortPoolTrapMgmtCBRConnCntTholdLoRev   OBJECT-TYPE
   SYNTAX   INTEGER
   ACCESS   read-write
   STATUS   mandatory
   DESCRIPTION
    " The lower threshold for the CBR connection count Rev trap. When an
      allocation causes the CBR connection count to fall below this value,
      the trap is generated. (If it has never been set, the value will be -1.)"
   ::= { sfcsBwPortPoolTrapMgmtEntry 13 }

sfcsBwPortPoolTrapMgmtCBRAllocBwTholdHiFwd   OBJECT-TYPE
   SYNTAX   INTEGER
   ACCESS   read-write
   STATUS   mandatory
   DESCRIPTION
    " The upper threshold for the CBR Allocated Bw Fwd trap. When an
      allocation causes the CBR Allocated Bw to exceed this value,
      the trap is generated. (If it has never been set, the value will be -1.)"
   ::= { sfcsBwPortPoolTrapMgmtEntry 14 }

sfcsBwPortPoolTrapMgmtCBRAllocBwTholdHiRev   OBJECT-TYPE
   SYNTAX   INTEGER
   ACCESS   read-write
   STATUS   mandatory
   DESCRIPTION
    " The upper threshold for the CBR connection count Rev trap. When an
      allocation causes the CBR connection count to exceed this value,
      the trap is generated. (If it has never been set, the value will be -1.)"
   ::= { sfcsBwPortPoolTrapMgmtEntry 15 }

sfcsBwPortPoolTrapMgmtCBRAllocBwTholdLoFwd   OBJECT-TYPE
   SYNTAX   INTEGER
   ACCESS   read-write
   STATUS   mandatory
   DESCRIPTION
    " The lower threshold for the CBR Allocated Bw Fwd trap. When an
      allocation causes the CBR Allocated Bw to fall below this value,
      the trap is generated. (If it has never been set, the value will be -1.)"
   ::= { sfcsBwPortPoolTrapMgmtEntry 16 }

sfcsBwPortPoolTrapMgmtCBRAllocBwTholdLoRev   OBJECT-TYPE
   SYNTAX   INTEGER
   ACCESS   read-write
   STATUS   mandatory
   DESCRIPTION
    " The lower threshold for the CBR Allocated Bw Rev trap. When an
      allocation causes the CBR Allocated Bw to fall below this value,
      the trap is generated. (If it has never been set, the value will be -1.)"
   ::= { sfcsBwPortPoolTrapMgmtEntry 17 }

--  # ABR Information

sfcsBwPortPoolTrapMgmtABRConnCntTholdHiFwd   OBJECT-TYPE
   SYNTAX   INTEGER
   ACCESS   read-write
   STATUS   mandatory
   DESCRIPTION
    " The upper threshold for the ABR connection count Fwd trap. When an
      allocation causes the ABR connection count to exceed this value,
      the trap is generated. (If it has never been set, the value will be -1.)"
   ::= { sfcsBwPortPoolTrapMgmtEntry 18 }

sfcsBwPortPoolTrapMgmtABRConnCntTholdHiRev   OBJECT-TYPE
   SYNTAX   INTEGER
   ACCESS   read-write
   STATUS   mandatory
   DESCRIPTION
    " The upper threshold for the ABR connection count Rev trap. When an
      allocation causes the ABR connection count to exceed this value,
      the trap is generated. (If it has never been set, the value will be -1.)"
   ::= { sfcsBwPortPoolTrapMgmtEntry 19 }

sfcsBwPortPoolTrapMgmtABRConnCntTholdLoFwd   OBJECT-TYPE
   SYNTAX   INTEGER
   ACCESS   read-write
   STATUS   mandatory
   DESCRIPTION
    " The lower threshold for the ABR connection count Fwd trap. When an
      allocation causes the ABR connection count to fall below this value,
      the trap is generated. (If it has never been set, the value will be -1.)"
   ::= { sfcsBwPortPoolTrapMgmtEntry 20 }

sfcsBwPortPoolTrapMgmtABRConnCntTholdLoRev   OBJECT-TYPE
   SYNTAX   INTEGER
   ACCESS   read-write
   STATUS   mandatory
   DESCRIPTION
    " The lower threshold for the ABR connection count Rev trap. When an
      allocation causes the ABR connection count to fall below this value,
      the trap is generated. (If it has never been set, the value will be -1.)"
   ::= { sfcsBwPortPoolTrapMgmtEntry 21 }

sfcsBwPortPoolTrapMgmtABRAllocBwTholdHiFwd   OBJECT-TYPE
   SYNTAX   INTEGER
   ACCESS   read-write
   STATUS   mandatory
   DESCRIPTION
    " The upper threshold for the ABR Allocated Bw Fwd trap. When an
      allocation causes the ABR Allocated Bw to exceed this value,
      the trap is generated. (If it has never been set, the value will be -1.)"
   ::= { sfcsBwPortPoolTrapMgmtEntry 22 }

sfcsBwPortPoolTrapMgmtABRAllocBwTholdHiRev   OBJECT-TYPE
   SYNTAX   INTEGER
   ACCESS   read-write
   STATUS   mandatory
   DESCRIPTION
    " The upper threshold for the ABR Allocated Bw Rev trap. When an
      allocation causes the ABR Allocated Bw to exceed this value,
      the trap is generated. (If it has never been set, the value will be -1.)"
   ::= { sfcsBwPortPoolTrapMgmtEntry 23 }

sfcsBwPortPoolTrapMgmtABRAllocBwTholdLoFwd   OBJECT-TYPE
   SYNTAX   INTEGER
   ACCESS   read-write
   STATUS   mandatory
   DESCRIPTION
    " The lower threshold for the ABR Allocated Bw Fwd trap. When an
      allocation causes the ABR Allocated Bw to fall below this value,
      the trap is generated. (If it has never been set, the value will be -1.)"
   ::= { sfcsBwPortPoolTrapMgmtEntry 24 }

sfcsBwPortPoolTrapMgmtABRAllocBwTholdLoRev   OBJECT-TYPE
   SYNTAX   INTEGER
   ACCESS   read-write
   STATUS   mandatory
   DESCRIPTION
    " The lower threshold for the ABR Allocated Bw Rev trap. When an
      allocation causes the ABR Allocated Bw to fall below this value,
      the trap is generated. (If it has never been set, the value will be -1.)"
   ::= { sfcsBwPortPoolTrapMgmtEntry 25 }

-- # VBR Information

sfcsBwPortPoolTrapMgmtVBRConnCntTholdHiFwd   OBJECT-TYPE
   SYNTAX   INTEGER
   ACCESS   read-write
   STATUS   mandatory
   DESCRIPTION
    " The upper threshold for the VBR connection count Fwd trap. When an
      allocation causes the VBR connection count to exceed this value,
      the trap is generated. (If it has never been set, the value will be -1.)"
   ::= { sfcsBwPortPoolTrapMgmtEntry 26 }

sfcsBwPortPoolTrapMgmtVBRConnCntTholdHiRev   OBJECT-TYPE
   SYNTAX   INTEGER
   ACCESS   read-write
   STATUS   mandatory
   DESCRIPTION
    " The upper threshold for the VBR connection count Rev trap. When an
      allocation causes the VBR connection count to exceed this value,
      the trap is generated. (If it has never been set, the value will be -1.)"
   ::= { sfcsBwPortPoolTrapMgmtEntry 27 }

sfcsBwPortPoolTrapMgmtVBRConnCntTholdLoFwd   OBJECT-TYPE
   SYNTAX   INTEGER
   ACCESS   read-write
   STATUS   mandatory
   DESCRIPTION
    " The lower threshold for the VBR connection count Fwd trap. When an
      allocation causes the VBR connection count to fall below this value,
      the trap is generated. (If it has never been set, the value will be -1.)"
   ::= { sfcsBwPortPoolTrapMgmtEntry 28 }

sfcsBwPortPoolTrapMgmtVBRConnCntTholdLoRev   OBJECT-TYPE
   SYNTAX   INTEGER
   ACCESS   read-write
   STATUS   mandatory
   DESCRIPTION
    " The lower threshold for the VBR connection count Rev trap. When an
      allocation causes the VBR connection count to fall below this value,
      the trap is generated. (If it has never been set, the value will be -1.)"
   ::= { sfcsBwPortPoolTrapMgmtEntry 29 }

sfcsBwPortPoolTrapMgmtVBRAllocBwTholdHiFwd   OBJECT-TYPE
   SYNTAX   INTEGER
   ACCESS   read-write
   STATUS   mandatory
   DESCRIPTION
    " The upper threshold for the VBR Allocated Bw Fwd trap. When an
      allocation causes the VBR Allocated Bw to exceed this value,
      the trap is generated. (If it has never been set, the value will be -1.)"
   ::= { sfcsBwPortPoolTrapMgmtEntry 30 }

sfcsBwPortPoolTrapMgmtVBRAllocBwTholdHiRev   OBJECT-TYPE
   SYNTAX   INTEGER
   ACCESS   read-write
   STATUS   mandatory
   DESCRIPTION
    " The upper threshold for the VBR Allocated Bw Rev trap. When an
      allocation causes the VBR Allocated Bw to exceed this value,
      the trap is generated. (If it has never been set, the value will be -1.)"
   ::= { sfcsBwPortPoolTrapMgmtEntry 31 }

sfcsBwPortPoolTrapMgmtVBRAllocBwTholdLoFwd   OBJECT-TYPE
   SYNTAX   INTEGER
   ACCESS   read-write
   STATUS   mandatory
   DESCRIPTION
    " The lower threshold for the VBR Allocated Bw Fwd trap. When an
      allocation causes the VBR Allocated Bw to fall below this value,
      the trap is generated. (If it has never been set, the value will be -1.)"
   ::= { sfcsBwPortPoolTrapMgmtEntry 32 }

sfcsBwPortPoolTrapMgmtVBRAllocBwTholdLoRev   OBJECT-TYPE
   SYNTAX   INTEGER
   ACCESS   read-write
   STATUS   mandatory
   DESCRIPTION
    " The lower threshold for the VBR Allocated Bw Rev trap. When an
      allocation causes the VBR Allocated Bw to fall below this value,
      the trap is generated. (If it has never been set, the value will be -1.)"
   ::= { sfcsBwPortPoolTrapMgmtEntry 33 }

--  # UBR Information

sfcsBwPortPoolTrapMgmtUBRConnCntTholdHiFwd   OBJECT-TYPE
   SYNTAX   INTEGER
   ACCESS   read-write
   STATUS   mandatory
   DESCRIPTION
    " The upper threshold for the UBR connection count Fwd trap. When an
      allocation causes the UBR connection count to exceed this value,
      the trap is generated. (If it has never been set, the value will be -1.)"
   ::= { sfcsBwPortPoolTrapMgmtEntry 34 }

sfcsBwPortPoolTrapMgmtUBRConnCntTholdHiRev   OBJECT-TYPE
   SYNTAX   INTEGER
   ACCESS   read-write
   STATUS   mandatory
   DESCRIPTION
    " The upper threshold for the UBR connection count Rev trap. When an
      allocation causes the UBR connection count to exceed this value,
      the trap is generated. (If it has never been set, the value will be -1.)"
   ::= { sfcsBwPortPoolTrapMgmtEntry 35 }

sfcsBwPortPoolTrapMgmtUBRConnCntTholdLoFwd   OBJECT-TYPE
   SYNTAX   INTEGER
   ACCESS   read-write
   STATUS   mandatory
   DESCRIPTION
    " The lower threshold for the UBR connection count Fwd trap. When an
      allocation causes the UBR connection count to fall below this value,
      the trap is generated. (If it has never been set, the value will be -1.)"
   ::= { sfcsBwPortPoolTrapMgmtEntry 36 }

sfcsBwPortPoolTrapMgmtUBRConnCntTholdLoRev   OBJECT-TYPE
   SYNTAX   INTEGER
   ACCESS   read-write
   STATUS   mandatory
   DESCRIPTION
    " The lower threshold for the UBR connection count Rev trap. When an
      allocation causes the UBR connection count to fall below this value,
      the trap is generated. (If it has never been set, the value will be -1.)"
   ::= { sfcsBwPortPoolTrapMgmtEntry 37 }

sfcsBwPortPoolTrapMgmtUBRAllocBwTholdHiFwd   OBJECT-TYPE
   SYNTAX   INTEGER
   ACCESS   read-write
   STATUS   mandatory
   DESCRIPTION
    " The upper threshold for the UBR Allocated Bw Fwd trap. When an
      allocation causes the UBR Allocated Bw to exceed this value,
      the trap is generated. (If it has never been set, the value will be -1.)"
   ::= { sfcsBwPortPoolTrapMgmtEntry 38 }

sfcsBwPortPoolTrapMgmtUBRAllocBwTholdHiRev   OBJECT-TYPE
   SYNTAX   INTEGER
   ACCESS   read-write
   STATUS   mandatory
   DESCRIPTION
    " The upper threshold for the UBR Allocated Bw Rev trap. When an
      allocation causes the UBR Allocated Bw to exceed this value,
      the trap is generated. (If it has never been set, the value will be -1.)"
   ::= { sfcsBwPortPoolTrapMgmtEntry 39 }

sfcsBwPortPoolTrapMgmtUBRAllocBwTholdLoFwd   OBJECT-TYPE
   SYNTAX   INTEGER
   ACCESS   read-write
   STATUS   mandatory
   DESCRIPTION
    " The lower threshold for the UBR Allocated Bw Fwd trap. When an
      allocation causes the UBR Allocated Bw to fall below this value,
      the trap is generated. (If it has never been set, the value will be -1.)"
   ::= { sfcsBwPortPoolTrapMgmtEntry 40 }

sfcsBwPortPoolTrapMgmtUBRAllocBwTholdLoRev   OBJECT-TYPE
   SYNTAX   INTEGER
   ACCESS   read-write
   STATUS   mandatory
   DESCRIPTION
    " The lower threshold for the UBR Allocated Bw Rev trap. When an
      allocation causes the UBR Allocated Bw to fall below this value,
      the trap is generated. (If it has never been set, the value will be -1.)"
   ::= { sfcsBwPortPoolTrapMgmtEntry 41 }

sfcsBWPortPoolTrapMgmtBuffUpThold            OBJECT-TYPE
   SYNTAX   INTEGER
   ACCESS   read-write
   STATUS   mandatory
   DESCRIPTION
      " The upper threshold for buffer allocation trap ."
   ::= { sfcsBwPortPoolTrapMgmtEntry 42 }

sfcsBWPortPoolTrapMgmtBuffLoThold            OBJECT-TYPE 
   SYNTAX   INTEGER
   ACCESS   read-write
   STATUS   mandatory
   DESCRIPTION
      " The lower threshold for buffer allocation trap ."
   ::= { sfcsBwPortPoolTrapMgmtEntry 43 }

sfcsBWPortPoolTrapMgmtConnRejThold           OBJECT-TYPE
   SYNTAX   INTEGER
   ACCESS   read-write
   STATUS   mandatory
   DESCRIPTION
      " The lower threshold for conn rejects trap ."
   ::= { sfcsBwPortPoolTrapMgmtEntry 44 }


-- %%%%%%%%%%%%%%%%%%%%%%%%%%%%%%%%%%%%%%%%%%%%%%%%%%%%%%%%%%%%%%%%%%%%%%%%%%%%%%%%%%%%%%
--  ### Buffer Pool Information

--  Each Buffer Pool consists of a number of rows- one for each priority
--  The primary index is the ifindex of the port that owns these row entries
--  The secondary index is the priority number for the row

--  
sfcsBuffPrioTable   OBJECT-TYPE
   SYNTAX   SEQUENCE OF SfcsBuffPrioEntry
   ACCESS   not-accessible
   STATUS   mandatory
   DESCRIPTION
      "This table contains the rows of all the buffer pools." 
   ::= { sfcsBuffPools 1 }

sfcsBuffPrioEntry   OBJECT-TYPE
   SYNTAX   SfcsBuffPrioEntry
   ACCESS   not-accessible
   STATUS   mandatory
   DESCRIPTION
      "Each entry contains the rows of all the buffer pools."
   INDEX   { sfcsBuffPrioPortIndex, sfcsBuffPrioPriority }
   ::= { sfcsBuffPrioTable 1 }
 
SfcsBuffPrioEntry ::=
   SEQUENCE {
      sfcsBuffPrioPortIndex    INTEGER,
      sfcsBuffPrioPriority     INTEGER,
      sfcsBuffPrioAssignCtl    INTEGER,
      sfcsBuffPrioMinCtl       INTEGER,
      sfcsBuffPrioAssigned     INTEGER,
      sfcsBuffPrioAllocated    INTEGER,
      sfcsBuffPrioAvailable    INTEGER,
      sfcsBuffPrioPeakAlloc    INTEGER,
      sfcsBuffPrioConnRejs     INTEGER,
      sfcsBuffPrioUpTholdTrap  INTEGER,
      sfcsBuffPrioLoTholdTrap  INTEGER,
      sfcsBuffPrioConnRejThold INTEGER
   }

--  ### Entry Defs
sfcsBuffPrioPortIndex    OBJECT-TYPE
   SYNTAX   INTEGER
   ACCESS   read-only
   STATUS   mandatory
   DESCRIPTION
      "This index specifies which port we are dealing
       with.  This reference is in the same format as MIB II's
       Interface index."
   ::= { sfcsBuffPrioEntry 1 }
 
sfcsBuffPrioPriority     OBJECT-TYPE
   SYNTAX   INTEGER
   ACCESS   read-only
   STATUS   mandatory
   DESCRIPTION
      "This index specifies which priority we are dealing
       with."
   ::= { sfcsBuffPrioEntry 2 }


sfcsBuffPrioAssignCtl    OBJECT-TYPE
   SYNTAX   INTEGER
   ACCESS   read-only
   STATUS   mandatory
   DESCRIPTION
      " The status of how assignment is controlled. Static,Manual,Adaptive.  "
   ::= { sfcsBuffPrioEntry 3}

sfcsBuffPrioMinCtl       OBJECT-TYPE
   SYNTAX   INTEGER
   ACCESS   read-write
   STATUS   mandatory
   DESCRIPTION
      " The minimum number of cells which can be assigned to this
      port/prioity."
   ::= { sfcsBuffPrioEntry 4}

sfcsBuffPrioAssigned     OBJECT-TYPE
   SYNTAX   INTEGER
   ACCESS   read-write
   STATUS   mandatory
   DESCRIPTION
      " The number of cells which are currently assigned to this
      port/priority."
   ::= { sfcsBuffPrioEntry 5}

sfcsBuffPrioAllocated    OBJECT-TYPE
   SYNTAX   INTEGER
   ACCESS   read-only
   STATUS   mandatory
   DESCRIPTION
      " The number of assigned cells which are currently allocated to
      VCs for this port/priority."
   ::= { sfcsBuffPrioEntry 6}

sfcsBuffPrioAvailable    OBJECT-TYPE
   SYNTAX   INTEGER
   ACCESS   read-only
   STATUS   mandatory
   DESCRIPTION
      " The number of assigned cells which are free to be allocated."
   ::= { sfcsBuffPrioEntry 7}

sfcsBuffPrioPeakAlloc    OBJECT-TYPE
   SYNTAX   INTEGER
   ACCESS   read-only
   STATUS   mandatory
   DESCRIPTION
      " The peak number of cells which have been allocated to this
      port/priority."
   ::= { sfcsBuffPrioEntry 8}

sfcsBuffPrioConnRejs     OBJECT-TYPE
   SYNTAX   INTEGER
   ACCESS   read-write
   STATUS   mandatory
   DESCRIPTION
      " The number of connections rejected because of a lack of buffers."
   ::= { sfcsBuffPrioEntry 9}

sfcsBuffPrioUpTholdTrap  OBJECT-TYPE
   SYNTAX   INTEGER
   ACCESS   read-write
   STATUS   mandatory
   DESCRIPTION
      " The upper threshold of allocations to trigger an upper thold trap."
   ::= { sfcsBuffPrioEntry 10}

sfcsBuffPrioLoTholdTrap  OBJECT-TYPE
   SYNTAX   INTEGER
   ACCESS   read-write
   STATUS   mandatory
   DESCRIPTION
      " The lower threshold of allocations to trigger a lower thold trap."
   ::= { sfcsBuffPrioEntry 11}

sfcsBuffPrioConnRejThold OBJECT-TYPE
   SYNTAX   INTEGER
   ACCESS   read-write
   STATUS   mandatory
   DESCRIPTION
      " The lower threshold of conn rejects trap  because of inadequate buffers."
   ::= { sfcsBuffPrioEntry 12}

--  %%%%%%%%%%%%%%%%%%%%%%%%%%%%%%%%%%%%%%%%%%%%%%%%%%%%%%%%%%%%%%%%%%%%%%%%%%%%%%%%%%%%%
--  The SFCS ANIM Proxy Group

-- SFCS ANIM Proxy Group
-- This group contains the managed objects and functions used to setup and
-- configure the SFCS ANIM Proxies.  This group contains three sub-groups:
-- configuration status, Transmit function setup, and Port Read

-- SFCS ANIM Proxy Configuration Status Table
-- This table contains contains information about the status of the Port or Proxy
-- as a whole, as opposed to the receive and Transmit table which contain information
-- about cells.

sfcsProxyConfigTable   OBJECT-TYPE
   SYNTAX   SEQUENCE OF SfcsProxyConfigEntry
   ACCESS   not-accessible
   STATUS   mandatory
   DESCRIPTION
      "This table contains the config info and a port
      reading function."
   ::= { sfcsProxyConfig 1 }

sfcsProxyConfigEntry   OBJECT-TYPE
   SYNTAX   SfcsProxyConfigEntry
   ACCESS   not-accessible
   STATUS  mandatory
   DESCRIPTION
      "Each entry contains ANIM Proxy config info or a function."
   INDEX   { sfcsProxyConfigANIMIndex }
   ::= { sfcsProxyConfigTable 1 }

SfcsProxyConfigEntry ::=
   SEQUENCE {
      sfcsProxyConfigANIMIndex      INTEGER,
      sfcsProxyConfigNUMPORTS         INTEGER,
      sfcsProxyConfigTxMemSize      INTEGER,
      sfcsProxyConfigRxMaxPduSize      INTEGER,
      sfcsProxyConfigBandWidth      INTEGER,
      sfcsProxyConfigTransmitDone      INTEGER,
      sfcsProxyConfigReceiveFifoState      INTEGER,
      sfcsProxyConfigPortTransmitMode      INTEGER,
      sfcsProxyConfigReceiveFifoReset      INTEGER,
      sfcsProxyConfigTxFifoReset      INTEGER,
      sfcsProxyConfigReceiveMode      INTEGER,
      sfcsProxyConfigCaptureMode      INTEGER,
      sfcsProxyConfigInitPort         INTEGER,
      sfcsProxyConfigLoad         INTEGER,
      sfcsProxyConfigGumbo         OCTET STRING
   }

sfcsProxyConfigANIMIndex   OBJECT-TYPE
   SYNTAX   INTEGER
   ACCESS   read-only
   STATUS   mandatory
   DESCRIPTION
      "This index specifies which ANIM Proxy we are dealing
      with.  This reference is in the same format as MIB II's
      Interface index."
   ::= { sfcsProxyConfigEntry 1 }

sfcsProxyConfigNUMPORTS      OBJECT-TYPE
   SYNTAX   INTEGER
   ACCESS   read-only
    STATUS   mandatory
   DESCRIPTION
      "Indicates the number of ports per Proxy which is always 4."
   ::= { sfcsProxyConfigEntry 2 }

sfcsProxyConfigTxMemSize   OBJECT-TYPE
   SYNTAX   INTEGER
   ACCESS   read-only
    STATUS   mandatory
   DESCRIPTION
      "Indicates the size of the port's Transmission memory in K.
      The memory size is always 1K."
   ::= { sfcsProxyConfigEntry 3 }

sfcsProxyConfigRxMaxPduSize   OBJECT-TYPE
   SYNTAX   INTEGER
   ACCESS   read-only
    STATUS   mandatory
   DESCRIPTION
      "Indicates the size of the port's Transmission memory in K.
      The memory size is always 1K."
   ::= { sfcsProxyConfigEntry 4 }

sfcsProxyConfigBandWidth   OBJECT-TYPE
   SYNTAX   INTEGER
   ACCESS   read-only
    STATUS   mandatory
   DESCRIPTION
      "Indicates the bandwidth for the port, which is ?????"
   ::= { sfcsProxyConfigEntry 5 }

sfcsProxyConfigTransmitDone   OBJECT-TYPE
   SYNTAX   INTEGER   {
         yes   (1),
         no   (2)
      }
   ACCESS   read-only
   STATUS   mandatory
   DESCRIPTION
      "Checks if the Transmission has finished."
   ::= { sfcsProxyConfigEntry 6 }

sfcsProxyConfigReceiveFifoState   OBJECT-TYPE
   SYNTAX   INTEGER   {
         full(1),
         not-full(2)
      }
   ACCESS   read-only
   STATUS   mandatory
   DESCRIPTION
      "Checks if the port's receive Fifo is full or not."
   ::= { sfcsProxyConfigEntry 7 }

sfcsProxyConfigPortTransmitMode   OBJECT-TYPE
   SYNTAX   INTEGER   {
         stop(1),
         start-stay(2),
         reread(3)
         }
   ACCESS   read-write
   STATUS   mandatory
   DESCRIPTION
      "Controls Transmission of cells in port Transmit memory."
   ::= { sfcsProxyConfigEntry 8 }

sfcsProxyConfigReceiveFifoReset   OBJECT-TYPE
   SYNTAX   INTEGER
   ACCESS   write-only
   STATUS   mandatory
   DESCRIPTION
      "Controls the receive buffer's memory. Reset clears memory."
   ::= { sfcsProxyConfigEntry 9 }

sfcsProxyConfigTxFifoReset   OBJECT-TYPE
   SYNTAX   INTEGER
   ACCESS   write-only
   STATUS   mandatory
   DESCRIPTION
      "Controls the port's transmit memory. Reset clears memory."
   ::= { sfcsProxyConfigEntry 10 }

sfcsProxyConfigReceiveMode   OBJECT-TYPE
   SYNTAX   INTEGER   {
         receiving   (1),
         not-receiving   (2)
      }
   ACCESS   read-write
   STATUS   mandatory
   DESCRIPTION
      "Controls whether or not the port receives cells."
   ::= { sfcsProxyConfigEntry 11 }

sfcsProxyConfigCaptureMode   OBJECT-TYPE
   SYNTAX   INTEGER   {
         all   (1),
         header   (2)
      }
   ACCESS   read-write
   STATUS   mandatory
   DESCRIPTION
      "Controls how much of the cell is received."
   ::= { sfcsProxyConfigEntry 12 }

sfcsProxyConfigInitPort      OBJECT-TYPE
   SYNTAX   INTEGER
   ACCESS   write-only
   STATUS   mandatory
   DESCRIPTION
      "Setting this returns the port to the initial setup."
   ::= { sfcsProxyConfigEntry 13 }

sfcsProxyConfigLoad      OBJECT-TYPE
   SYNTAX   INTEGER
   ACCESS   read-write
   STATUS   mandatory
   DESCRIPTION
      "Transmit load for port."
   ::= { sfcsProxyConfigEntry 14 }

sfcsProxyConfigGumbo      OBJECT-TYPE
   SYNTAX   OCTET STRING
   ACCESS   read-only
   STATUS   mandatory
   DESCRIPTION
      "Unreadable octet string used for control information."
   ::= { sfcsProxyConfigEntry 15 }

-- SFCS ANIM Proxy Transmit function setup Table.
-- This table contains the function to send cells from specific ports and
-- the arguments which this function takes.

sfcsProxyTransTable      OBJECT-TYPE
   SYNTAX   SEQUENCE OF SfcsProxyTransEntry
   ACCESS   not-accessible
   STATUS   mandatory
   DESCRIPTION
      "This table contains the arguments and the function for the
      Transmit function."
   ::= { sfcsProxyTrans 1 }

sfcsProxyTransEntry      OBJECT-TYPE
   SYNTAX   SfcsProxyTransEntry
   ACCESS   not-accessible
   STATUS   mandatory
   DESCRIPTION
      "The entries are the arguments for the Transmit function."
   INDEX   { sfcsProxyTransANIMIndex }
   ::= { sfcsProxyTransTable 1 }

SfcsProxyTransEntry ::=
   SEQUENCE {
      sfcsProxyTransANIMIndex         INTEGER,
      sfcsProxyTransEncodeNewPdu      INTEGER,
      sfcsProxyTransVPI         INTEGER,
      sfcsProxyTransVCI         INTEGER,
      sfcsProxyTransPTI         INTEGER,
      sfcsProxyTransCLP         INTEGER,
      sfcsProxyTransPayloadType      INTEGER,
      sfcsProxyTransPayloadLength      INTEGER,
      sfcsProxyTransPayloadData      OCTET STRING,
      sfcsProxyTransCount         INTEGER,
      sfcsProxyTransPayloadAdaptionLayer   INTEGER,
      sfcsProxyTransMpxMethod         INTEGER,
      sfcsProxyTransControl         INTEGER,
      sfcsProxyTransGumbo         OCTET STRING
   }

sfcsProxyTransANIMIndex   OBJECT-TYPE
   SYNTAX   INTEGER
   ACCESS   read-only
   STATUS   mandatory
   DESCRIPTION
      "This index specifies which ANIM Port we are dealing
      with.  This reference is in the same format as MIB II's
      Interface Index."
   ::= { sfcsProxyTransEntry 1 }

sfcsProxyTransEncodeNewPdu   OBJECT-TYPE
   SYNTAX  INTEGER
   ACCESS  write-only
   STATUS  mandatory
   DESCRIPTION
      "Setting this encodes a new PDU based on the current PDU parameters
      into the port's transmit memory."
   ::= { sfcsProxyTransEntry 2 }

sfcsProxyTransVPI      OBJECT-TYPE
   SYNTAX   INTEGER
   ACCESS   read-write
   STATUS   mandatory
   DESCRIPTION
      "This is the VPI for the PDU."
   ::= { sfcsProxyTransEntry 3 }


sfcsProxyTransVCI      OBJECT-TYPE
   SYNTAX   INTEGER
   ACCESS   read-write
   STATUS   mandatory
   DESCRIPTION
      "This is the VCI for the PDU."
   ::= { sfcsProxyTransEntry 4 }

sfcsProxyTransPTI   OBJECT-TYPE
   SYNTAX   INTEGER (0..7)         
   ACCESS   read-write
   STATUS   mandatory
   DESCRIPTION
      "Payload Type Indicator: the value of the 3 bit Payload Type
      field in the header.  The most signifigant bit indicates user or 
      control data, the next bit indicates congestion, and the
      last bit indicates AAL encoding."
   ::= { sfcsProxyTransEntry 5 }

sfcsProxyTransCLP   OBJECT-TYPE
   SYNTAX   INTEGER
   ACCESS   read-write
   STATUS   mandatory
   DESCRIPTION
      "The cell loss priority: 1 or 0."
   ::= { sfcsProxyTransEntry 6 }

sfcsProxyTransPayloadType   OBJECT-TYPE
   SYNTAX   INTEGER   {
         user-input(1),
         sequential(2),
         uniform(3)
         }
   ACCESS   read-write
   STATUS   mandatory
   DESCRIPTION
      "The payload type for the cell."
   ::= { sfcsProxyTransEntry 7 }

sfcsProxyTransPayloadLength   OBJECT-TYPE
   SYNTAX   INTEGER
   ACCESS   read-write
   STATUS   mandatory
   DESCRIPTION
      "The length of the payload in bytes."
   ::= { sfcsProxyTransEntry 8 }

sfcsProxyTransPayloadData   OBJECT-TYPE
   SYNTAX   OCTET STRING
   ACCESS   read-write
   STATUS   mandatory
   DESCRIPTION
      "If the payload type is user input, this is the payload itself."
   ::= { sfcsProxyTransEntry 9 }

sfcsProxyTransCount      OBJECT-TYPE
   SYNTAX   INTEGER
   ACCESS   read-write
   STATUS   mandatory
   DESCRIPTION
      "Number of copies of the pdu to encode in port transmit memory."
   ::= { sfcsProxyTransEntry 10 }

sfcsProxyTransPayloadAdaptionLayer   OBJECT-TYPE
   SYNTAX   INTEGER   {
         raw(1),
         aal5(2)
      }
   ACCESS   read-write
   STATUS   mandatory
   DESCRIPTION
      "The format of the payload: either raw cells or AAL5."
   ::= { sfcsProxyTransEntry 11 }

sfcsProxyTransMpxMethod   OBJECT-TYPE
   SYNTAX   INTEGER
--{
--   enumerate me!!      
--      }
   ACCESS   read-write
   STATUS   mandatory
   DESCRIPTION
      "The format of the payload: either raw cells or AAL5."
   ::= { sfcsProxyTransEntry 12 }


sfcsProxyTransControl   OBJECT-TYPE
   SYNTAX   INTEGER   {
         send-once(1),
         repeat(2)
      }
   ACCESS   read-write
   STATUS   mandatory
   DESCRIPTION
      "Controls how many times to send what's in the port's
      transmit memory."
   ::= { sfcsProxyTransEntry 13 }

sfcsProxyTransGumbo   OBJECT-TYPE
   SYNTAX   OCTET STRING
   ACCESS   read-only
   STATUS   mandatory
   DESCRIPTION
      "Returns the vpi, vci, pti, clp, payload_type, payload_length, count,
      PAL, mpx method, and control entires for this table in a string where
      the entries are separated by semicolons."
   ::= { sfcsProxyTransEntry 14 }

-- SFCS ANIM Port Read
-- This table contains the information read from cells from a port's receive fifo.

sfcsProxyReadTable      OBJECT-TYPE
   SYNTAX   SEQUENCE OF SfcsProxyReadEntry
   ACCESS   not-accessible
   STATUS   mandatory
   DESCRIPTION
      "This table contains information read from the cells in the receive fifo."
   ::= { sfcsProxyRead 1 }

sfcsProxyReadEntry      OBJECT-TYPE
   SYNTAX   SfcsProxyReadEntry
   ACCESS   not-accessible
   STATUS   mandatory
   DESCRIPTION
      "The entries are the information about the cells or the PDU."
   INDEX   { sfcsProxyReadANIMIndex }
   ::= { sfcsProxyReadTable 1 }

SfcsProxyReadEntry ::=
   SEQUENCE {
      sfcsProxyReadANIMIndex         INTEGER,
      sfcsProxyReadMode         INTEGER,
      sfcsProxyReadNewPdu         INTEGER,
      sfcsProxyReadGumbo         OCTET STRING,
      sfcsProxyReadVPI         INTEGER,
      sfcsProxyReadVCI         INTEGER,
      sfcsProxyReadPTI         INTEGER,
      sfcsProxyReadCLP         INTEGER,
      sfcsProxyReadDataLength         INTEGER,
      sfcsProxyReadData         OCTET STRING,
      sfcsProxyReadPal         INTEGER,
      sfcsProxyReadInbyteslosts         INTEGER,
      sfcsProxyReadInCells         INTEGER,
      sfcsProxyReadInError         INTEGER,
      sfcsProxyReadInCellReadError      INTEGER,
      sfcsProxyReadInHecError      INTEGER,
      sfcsProxyReadInTooBigError      INTEGER,
      sfcsProxyReadInCRCError      INTEGER,
      sfcsProxyReadInLengthMismatchError      INTEGER,
      sfcsProxyReadInTotalCells    INTEGER
   }

sfcsProxyReadANIMIndex   OBJECT-TYPE
   SYNTAX   INTEGER
   ACCESS   read-only
   STATUS   mandatory
   DESCRIPTION
      "This index specifies which ANIM Port we are dealing
      with.  This reference is in the same format as the MIB II
      Interface Index."
   ::= { sfcsProxyReadEntry 1 }


sfcsProxyReadMode      OBJECT-TYPE
   SYNTAX   INTEGER   {
         reassemble-PDU(1),
         cell-by-cell(2),
         all-data(3)
      }
   ACCESS   read-write
   STATUS   mandatory
   DESCRIPTION
      "How the receive fifo is read."
   ::= { sfcsProxyReadEntry 2 }

sfcsProxyReadNewPdu      OBJECT-TYPE
   SYNTAX   INTEGER {
         get-next-pdu(1),
         reread-from-beginning(2)
      }
   ACCESS   write-only
   STATUS   mandatory
   DESCRIPTION
      "Pops a new Pdu from the receive fifo to be examined and read."
   ::= { sfcsProxyReadEntry 3 }

sfcsProxyReadGumbo      OBJECT-TYPE
   SYNTAX   OCTET STRING
   ACCESS   write-only
   STATUS   mandatory
   DESCRIPTION
      "Unreadable control information."
   ::= { sfcsProxyReadEntry 4 }

sfcsProxyReadVPI      OBJECT-TYPE
   SYNTAX   INTEGER
   ACCESS   read-only
   STATUS   mandatory
   DESCRIPTION
      "This is the VPI for the PDU."
   ::= { sfcsProxyReadEntry 5 }

sfcsProxyReadVCI      OBJECT-TYPE
   SYNTAX   INTEGER
   ACCESS   read-only
   STATUS   mandatory
   DESCRIPTION
      "This is the VCI for the PDU."
   ::= { sfcsProxyReadEntry 6 }

sfcsProxyReadPTI   OBJECT-TYPE
   SYNTAX   INTEGER (0..7)         
   ACCESS   read-only
   STATUS   mandatory
   DESCRIPTION
      "Payload Type Indicator: the value of the 3 bit Payload Type
      field in the header.  The most signifigant bit indicates user or 
      control data, the next bit indicates congestion, and the
      last bit indicates AAL encoding."
   ::= { sfcsProxyReadEntry 7 }


sfcsProxyReadCLP   OBJECT-TYPE
   SYNTAX   INTEGER
   ACCESS   read-only
   STATUS   mandatory
   DESCRIPTION
      "The cell loss priority: 1 or 0."
   ::= { sfcsProxyReadEntry 8 }

sfcsProxyReadDataLength      OBJECT-TYPE
   SYNTAX   INTEGER
   ACCESS   read-only
   STATUS   mandatory
   DESCRIPTION
      "The length of the PDU in bytes."
   ::= { sfcsProxyReadEntry 9 }

sfcsProxyReadData      OBJECT-TYPE
   SYNTAX   OCTET STRING
   ACCESS   read-only
   STATUS   mandatory
   DESCRIPTION
      "The actual data of the PDU."
   ::= { sfcsProxyReadEntry 10 }

sfcsProxyReadPal      OBJECT-TYPE
   SYNTAX   INTEGER {
         raw(1),
         aal5(2)
      }
   ACCESS   read-only
   STATUS   mandatory
   DESCRIPTION
      "The format of the payload: either raw cells or AAL5."
   ::= { sfcsProxyReadEntry 11 }

sfcsProxyReadInbyteslosts      OBJECT-TYPE
   SYNTAX   INTEGER
   ACCESS   read-only
   STATUS   mandatory
   DESCRIPTION
      "The number of bytes that were dropped while reading. Usually because
   they occurred before the Start of Cell was discovered."
   ::= { sfcsProxyReadEntry 12 }

sfcsProxyReadInCells      OBJECT-TYPE
   SYNTAX   INTEGER
   ACCESS   read-only
   STATUS   mandatory
   DESCRIPTION
      "The number of cells read since this port was last reset."
   ::= { sfcsProxyReadEntry 13 }

sfcsProxyReadInError      OBJECT-TYPE
   SYNTAX   INTEGER
   ACCESS   read-only
   STATUS   mandatory
   DESCRIPTION
      "The number of pdu's that had to be dropped due to errors."
   ::= { sfcsProxyReadEntry 14 }

sfcsProxyReadInCellReadError   OBJECT-TYPE
   SYNTAX   INTEGER
   ACCESS   read-only
   STATUS   mandatory
   DESCRIPTION
      "The number of cells that had to be dropped due to errors."
   ::= { sfcsProxyReadEntry 15 }

sfcsProxyReadInHecError      OBJECT-TYPE
   SYNTAX   INTEGER
   ACCESS   read-only
   STATUS   mandatory
   DESCRIPTION
      "The number of cell headers that contained errors."
   ::= { sfcsProxyReadEntry 16 }

sfcsProxyReadInTooBigError      OBJECT-TYPE
   SYNTAX   INTEGER
   ACCESS   read-only
   STATUS   mandatory
   DESCRIPTION
      "The number of pdu's that were too large to be received."
   ::= { sfcsProxyReadEntry 17 }

sfcsProxyReadInCRCError   OBJECT-TYPE
   SYNTAX   INTEGER
   ACCESS   read-only
   STATUS   mandatory
   DESCRIPTION
      "The number of pdu's that failed the CRC check."
   ::= { sfcsProxyReadEntry 18 }

sfcsProxyReadInLengthMismatchError   OBJECT-TYPE
   SYNTAX   INTEGER
   ACCESS   read-only
   STATUS   mandatory
   DESCRIPTION
      "The length stored in the pdu did not match the actual
   length of the pdu read in."
   ::= { sfcsProxyReadEntry 19 }

sfcsProxyReadInTotalCells   OBJECT-TYPE
   SYNTAX   INTEGER
   ACCESS   read-only
   STATUS   mandatory
   DESCRIPTION
      "Total number of cells read in by the snapshot."
   ::= { sfcsProxyReadEntry 20 }
END
