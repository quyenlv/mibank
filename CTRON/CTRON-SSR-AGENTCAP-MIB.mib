-- $Id: ssr-agent-capabilities.txt,v 1.1 2000/02/21 00:39:59 mrm Exp $
-- SSR Firmware 3.1 Agent Capabilities macro
-- Cabletron Systems, Inc 2000

CTRON-SSR-AGENTCAP-MIB DEFINITIONS ::= BEGIN

IMPORTS
    MODULE-IDENTITY
       FROM SNMPv2-SMI
    AGENT-CAPABILITIES
       FROM  SNMPv2-CONF
    etherMIB
       FROM EtherLike-MIB
    ifMIB
       FROM IF-MIB
    ipMIB
       FROM IP-MIB
    udpMIB
       FROM UDP-MIB
    tcpMIB
       FROM TCP-MIB
    bgp
       FROM BGP4-MIB
    ospf
       FROM OSPF-MIB
    ospfTrap
       FROM OSPF-TRAP-MIB
    rip2
       FROM RIPv2-MIB
    dot1dBase
       FROM BRIDGE-MIB
    qBridgeMIB
       FROM Q-BRIDGE-MIB       
    pBridgeMIB
       FROM P-BRIDGE-MIB
    frameRelayDTE
       FROM FRAME-RELAY-DTE-MIB
    ppp
       FROM PPP-LCP-MIB
    pppSecurity
       FROM PPP-SEC-MIB
    pppIp
       FROM PPP-IP-NCP-MIB
    ds1
       FROM DS1-MIB
    ds3
       FROM DS3-MIB
    sonetMIB
       FROM SONET-MIB
    atmMIB
       FROM ATM-MIB
    radiusAuthClientMIB
       FROM RADIUS-AUTH-CLIENT-MIB
    rmon
       FROM RMON-MIB   
    rmon
       FROM RMON2-MIB    
    vrrpMIB
       FROM VRRP-MIB
    ctLFAP
       FROM CTRON-LFAP-MIB
    policyMIB
       FROM CTRON-SSR-POLICY-MIB
    ssrConfigMIB
       FROM CTRON-SSR-CONFIG-MIB
    hardwareMIB
       FROM CTRON-SSR-HARDWARE-MIB
    capacityMIB
       FROM CTRON-SSR-CAPACITY-MIB
    ssrMibs 
       FROM CTRON-SSR-SMI-MIB; 

ctronSsrAgentCapabilityMIB MODULE-IDENTITY
   LAST-UPDATED
     "0002190000Z"
   ORGANIZATION
     "Cabletron Systems, Inc."
   CONTACT-INFO
    "Cabletron Systems, Inc.
     35 Industrial Way, P.O. Box 5005
     Rochester, NH 03867-0505
     (603) 332-9400
     support@ctron.com
     http://www.ctron.com"

   DESCRIPTION
     "This module defines agent capabilities for SSR firmware release 3.1"
        ::= { ssrMibs 760 }


-- branch for capability macros

ssrCapability OBJECT IDENTIFIER ::= {  ctronSsrAgentCapabilityMIB 1 }

ssr31 AGENT-CAPABILITIES 
  PRODUCT-RELEASE 
     "3.1"
  STATUS  current
  DESCRIPTION
     "First try at implementing a capabilities mib"
  REFERENCE 
     " some reference"

     SUPPORTS SNMPv2-MIB
     INCLUDES { 
         systemGroup,
         snmpGroup, 
         snmpBasicNotificationsGroup,
         --  snmpSetGroup is not implemented, but is needed for SNMPv2-MIB compliance
         -- non mandatory groups
         snmpCommunityGroup,
         -- deprecated/obsolete support
         snmpObsoleteGroup
     }

     -- ********************* ************ ************ *************** ***

     SUPPORTS EtherLike-MIB
     INCLUDES { 
         etherStats100MbsGroup
     }

     -- ********************* ************ ************ *************** ***

     SUPPORTS IF-MIB
     INCLUDES { 
         ifGeneralInformationGroup, 
         ifStackGroup2,
         ifCounterDiscontinuityGroup,
         -- non mandatory groups
         ifFixedLengthGroup,
         ifHCFixedLengthGroup,
         ifPacketGroup,
         ifHCPacketGroup,
         ifVHCPacketGroup,
         ifRcvAddressGroup,
         -- deprecated/obsolete support
         ifOldObjectsGroup
     }
     VARIATION ifAlias
     ACCESS read-only
     DESCRIPTION "ifAlias is guarenteed to be unique across reboots. It takes the form Type : instance info
      for example: ifAlias.49 = IP interface: to-sc-BGPfeed or ifAlias.42 = VLAN: test1 or 
      ifAlias.35 = Physical port: et.14.5"

     VARIATION ifAdminStatus
     ACCESS read-only
     DESCRIPTION "For ifTypes corresponding to VLANs this object is read only."

     VARIATION ifLinkUpDownTrapEnable
     ACCESS read-only
     DESCRIPTION "For all ifTypes where ifConnectorPresent is not TRUE."

     VARIATION ifStackStatus
     ACCESS read-only
     DESCRIPTION "Command line interface(CLI) is used to change relationships."

     -- ********************* ************ ************ *************** ***

     SUPPORTS IP-MIB
     INCLUDES { 
         ipGroup,
         -- icmpGroup 
     }
     VARIATION ipDefaultTTL
     ACCESS read-only
     DESCRIPTION "Command line interface(CLI) is used to change default ttl."

     -- ********************* ************ ************ *************** ***

     SUPPORTS IP-FORWARD-MIB
     INCLUDES { 
         ipForwardCidrRouteGroup
     }
     VARIATION ipCidrRouteIfIndex
     ACCESS read-only
     DESCRIPTION "Command line interface(CLI) is used to update Forwarding Information Base/FIB."

     VARIATION ipCidrRouteType
     ACCESS read-only
     DESCRIPTION "Command line interface(CLI) is used to update Forwarding Information Base/FIB."

     VARIATION ipCidrRouteInfo
     ACCESS read-only
     DESCRIPTION "Command line interface(CLI) is used to update Forwarding Information Base/FIB."

     VARIATION ipCidrRouteNextHopAS
     ACCESS read-only
     DESCRIPTION "Command line interface(CLI) is used to update Forwarding Information Base/FIB."

     VARIATION ipCidrRouteMetric1
     ACCESS read-only
     DESCRIPTION "Command line interface(CLI) is used to update Forwarding Information Base/FIB."

     VARIATION ipCidrRouteMetric2
     ACCESS read-only
     DESCRIPTION "Command line interface(CLI) is used to update Forwarding Information Base/FIB."

     VARIATION ipCidrRouteMetric3
     ACCESS read-only
     DESCRIPTION "Command line interface(CLI) is used to update Forwarding Information Base/FIB."

     VARIATION ipCidrRouteMetric4
     ACCESS read-only
     DESCRIPTION "Command line interface(CLI) is used to update Forwarding Information Base/FIB."

     VARIATION ipCidrRouteMetric5
     ACCESS read-only
     DESCRIPTION "Command line interface(CLI) is used to update Forwarding Information Base/FIB."

     VARIATION ipCidrRouteStatus
     ACCESS read-only
     DESCRIPTION "Command line interface(CLI) is used to update Forwarding Information Base/FIB."

     -- ********************* ************ ************ *************** ***

     SUPPORTS UDP-MIB
     INCLUDES { 
         udpGroup         
     }

     -- ********************* ************ ************ *************** ***

     SUPPORTS TCP-MIB
     INCLUDES { 
         tcpGroup         
     }
     VARIATION tcpConnState
     ACCESS read-only
     DESCRIPTION "Command line interface(CLI) is used to kill tcp sessions."

     -- ********************* ************ ************ *************** ***

--     SUPPORTS BGP4-MIB
--     INCLUDES { 
--      SMIv1 file, by default mib is disabled
--     }

     -- ********************* ************ ************ *************** ***

     SUPPORTS OSPF-MIB
     INCLUDES { 
         ospfBasicGroup,
         ospfAreaGroup,
         ospfStubAreaGroup,
         ospfIfGroup,
         ospfIfMetricGroup,
         ospfVirtIfGroup,
         ospfNbrGroup,
         ospfVirtNbrGroup,
         ospfAreaAggregateGroup
     }
     VARIATION ospfRouterId
     ACCESS read-only
     DESCRIPTION "Command line interface(CLI) is used to set router id."

     VARIATION ospfAdminStat
     ACCESS read-only
     DESCRIPTION "Command line interface(CLI) is used to set ospf state."

     VARIATION ospfTOSSupport
     ACCESS read-only
     DESCRIPTION "Command line interface(CLI) is used to set ospf TOS support."

     VARIATION ospfExtLsdbLimit
     ACCESS read-only
     DESCRIPTION "Command line interface(CLI) is used to set ospf Lsdb Limit."

     VARIATION ospfMulticastExtensions
     ACCESS read-only
     DESCRIPTION "Command line interface(CLI) is used to set ospf multicast extensions."

     VARIATION ospfExitOverflowInterval
     ACCESS read-only
     DESCRIPTION "Command line interface(CLI) is used to set ospf exit overflow interval."

     VARIATION ospfDemandExtensions
     ACCESS read-only
     DESCRIPTION "Command line interface(CLI) is used to set ospf demand extensions."

     VARIATION ospfAuthType
     ACCESS read-only
     DESCRIPTION "Command line interface(CLI) is used to set ospf authorisation types."

     VARIATION ospfImportAsExtern
     ACCESS read-only
     DESCRIPTION "Command line interface(CLI) is used to set ospf Import AS external routes."

     VARIATION ospfAreaSummary
     ACCESS read-only
     DESCRIPTION "Command line interface(CLI) is used to set ospf area summary importation."

     VARIATION ospfAreaStatus
     ACCESS read-only
     DESCRIPTION "Command line interface(CLI) is used to create & delete ospf areas."

     VARIATION ospfStubMetric
     ACCESS read-only
     DESCRIPTION "Command line interface(CLI) is used to set ospf area stub metric."

     VARIATION ospfStubStatus
     ACCESS read-only
     DESCRIPTION "Command line interface(CLI) is used to create & delete stub areas."

     VARIATION ospfStubMetricType
     ACCESS read-only
     DESCRIPTION "Command line interface(CLI) is used to set ospf stub metric type."

     VARIATION ospfAreaRangeMask
     ACCESS read-only
     DESCRIPTION "Command line interface(CLI) is used to set ospf area range mask."

     VARIATION ospfAreaRangeStatus
     ACCESS read-only
     DESCRIPTION "Command line interface(CLI) is used to create & delete ranges."

     VARIATION ospfAreaRangeEffect
     ACCESS read-only
     DESCRIPTION "Command line interface(CLI) is used to set area range effect."

     VARIATION ospfHostMetric
     ACCESS read-only
     DESCRIPTION "Command line interface(CLI) is used to set host metric."

     VARIATION ospfHostStatus
     ACCESS read-only
     DESCRIPTION "Command line interface(CLI) is used to create & delete hosts."

     VARIATION ospfIfAreaId
     ACCESS read-only
     DESCRIPTION "Command line interface(CLI) is used to set Interface area id."

     VARIATION ospfIfType
     ACCESS read-only
     DESCRIPTION "Command line interface(CLI) is used to set Interface type."

     VARIATION ospfIfAdminStat
     ACCESS read-only
     DESCRIPTION "Command line interface(CLI) is used to set Interface admin status."

     VARIATION ospfIfRtrPriority
     ACCESS read-only
     DESCRIPTION "Command line interface(CLI) is used to set interface router priority."

     VARIATION ospfIfTransitDelay
     ACCESS read-only
     DESCRIPTION "Command line interface(CLI) is used to set interface transit delay."

     VARIATION ospfIfRetransInterval
     ACCESS read-only
     DESCRIPTION "Command line interface(CLI) is used to set interface retransmission interval."

     VARIATION ospfIfHelloInterval
     ACCESS read-only
     DESCRIPTION "Command line interface(CLI) is used to set hello interval."

     VARIATION ospfIfRtrDeadInterval
     ACCESS read-only
     DESCRIPTION "Command line interface(CLI) is used to set dead interval."

     VARIATION ospfIfPollInterval
     ACCESS read-only
     DESCRIPTION "Command line interface(CLI) is used to set poll interval."

     VARIATION ospfIfAuthKey
     ACCESS read-only
     DESCRIPTION "Command line interface(CLI) is used to set interface auth key."

     VARIATION ospfIfStatus
     ACCESS read-only
     DESCRIPTION "Command line interface(CLI) is used to create & delete interfaces."

     VARIATION ospfIfMulticastForwarding
     ACCESS read-only
     DESCRIPTION "Command line interface(CLI) is used to set multicast fwd."

     VARIATION ospfIfDemand
     ACCESS read-only
     DESCRIPTION "Command line interface(CLI) is used to set this attribute."

     VARIATION ospfIfAuthType
     ACCESS read-only
     DESCRIPTION "Command line interface(CLI) is used to set this feature."

     VARIATION ospfIfMetricValue
     ACCESS read-only
     DESCRIPTION "Command line interface(CLI) is used to set this feature."

     VARIATION ospfVirtIfTransitDelay
     ACCESS read-only
     DESCRIPTION "Command line interface(CLI) is used to set this feature."

     VARIATION ospfVirtIfRetransInterval
     ACCESS read-only
     DESCRIPTION "Command line interface(CLI) is used to set this feature."

     VARIATION ospfVirtIfHelloInterval
     ACCESS read-only
     DESCRIPTION "Command line interface(CLI) is used to set this feature."

     VARIATION ospfVirtIfRtrDeadInterval
     ACCESS read-only
     DESCRIPTION "Command line interface(CLI) is used to set this feature."

     VARIATION ospfVirtIfAuthKey
     ACCESS read-only
     DESCRIPTION "Command line interface(CLI) is used to set this feature."

     VARIATION ospfVirtIfStatus
     ACCESS read-only
     DESCRIPTION "Command line interface(CLI) is used to set this feature."

     VARIATION ospfVirtIfAuthType
     ACCESS read-only
     DESCRIPTION "Command line interface(CLI) is used to set this feature."

     VARIATION ospfNbrPriority
     ACCESS read-only
     DESCRIPTION "Command line interface(CLI) is used to set this feature."

     VARIATION ospfNbmaNbrStatus
     ACCESS read-only
     DESCRIPTION "Command line interface(CLI) is used to set this feature."

     VARIATION ospfAreaAggregateStatus
     ACCESS read-only
     DESCRIPTION "Command line interface(CLI) is used to set this feature."

     VARIATION ospfAreaAggregateEffect
     ACCESS read-only
     DESCRIPTION "Command line interface(CLI) is used to set this feature."

     SUPPORTS OSPF-TRAP-MIB
     INCLUDES { 
         ospfTrapControlGroup
     }

     -- ********************* ************ ************ *************** ***

     SUPPORTS RIPv2-MIB
     INCLUDES { 
         rip2GlobalGroup,
         rip2IfStatGroup,
         rip2IfConfGroup,
         rip2PeerGroup
     }
     VARIATION rip2IfStatStatus
     ACCESS read-only
     DESCRIPTION "Command line interface(CLI) is used to set this feature."
   
     VARIATION rip2IfConfDomain
     ACCESS read-only
     DESCRIPTION "Command line interface(CLI) is used to set this feature."

     VARIATION rip2IfConfAuthType
     ACCESS read-only
     DESCRIPTION "Command line interface(CLI) is used to set this feature."

     VARIATION rip2IfConfAuthKey
     ACCESS read-only
     DESCRIPTION "Command line interface(CLI) is used to set this feature."

     VARIATION rip2IfConfSend
     ACCESS read-only
     DESCRIPTION "Command line interface(CLI) is used to set this feature."

     VARIATION rip2IfConfReceive
     ACCESS read-only
     DESCRIPTION "Command line interface(CLI) is used to set this feature."

     VARIATION rip2IfConfDefaultMetric
     ACCESS read-only
     DESCRIPTION "Command line interface(CLI) is used to set this feature."

     VARIATION rip2IfConfStatus
     ACCESS read-only
     DESCRIPTION "Command line interface(CLI) is used to set this feature."

     VARIATION rip2IfConfSrcAddress
     ACCESS read-only
     DESCRIPTION "Command line interface(CLI) is used to set this feature."

     -- ********************* ************ ************ *************** ***

--    SUPPORTS BRIDGE-MIB
--    INCLUDES { 
     -- same as BGP mib?
--    }

     -- ********************* ************ ************ *************** ***

     SUPPORTS Q-BRIDGE-MIB
     INCLUDES { 
        qBridgeBaseGroup,
        qBridgeVlanGroup,
        qBridgeVlanStaticGroup,
        qBridgePortGroup,
        qBridgeFdbUnicastGroup,
        qBridgeServiceRequirementsGroup
     }
     -- note: qBridgeFdbMulticastGroup, mandatory, but not implemented in 3.1

     VARIATION dot1qGvrpStatus
     ACCESS read-only
     DEFVAL { disabled }
     DESCRIPTION "Firmware Version 3.1 does not support GVRP/GARP."

     VARIATION dot1qForwardAllStaticPorts
     ACCESS read-only
     DESCRIPTION "Command line interface(CLI) is used to set this feature."

     VARIATION dot1qForwardAllForbiddenPorts
     ACCESS read-only
     DESCRIPTION "Command line interface(CLI) is used to set this feature."

     VARIATION dot1qForwardUnregisteredStaticPorts
     ACCESS read-only
     DESCRIPTION "Command line interface(CLI) is used to set this feature."

     VARIATION dot1qForwardUnregisteredForbiddenPorts
     ACCESS read-only
     DESCRIPTION "Command line interface(CLI) is used to set this feature."

     VARIATION dot1qStaticUnicastAllowedToGoTo
     ACCESS read-only
     DESCRIPTION "Command line interface(CLI) is used to set this feature."

     VARIATION dot1qStaticUnicastStatus
     ACCESS read-only
     DESCRIPTION "Command line interface(CLI) is used to set this feature."

     VARIATION dot1qStaticMulticastStaticEgressPorts
     ACCESS read-only
     DESCRIPTION "Command line interface(CLI) is used to set this feature."

     VARIATION dot1qStaticMulticastForbiddenEgressPorts
     ACCESS read-only
     DESCRIPTION "Command line interface(CLI) is used to set this feature."

     VARIATION dot1qStaticMulticastStatus
     ACCESS read-only
     DESCRIPTION "Command line interface(CLI) is used to set this feature."

     VARIATION dot1qVlanStaticName
     ACCESS read-only
     DESCRIPTION "Command line interface(CLI) is used to set this feature."

     VARIATION dot1qVlanStaticEgressPorts
     ACCESS read-only
     DESCRIPTION "Command line interface(CLI) is used to set this feature."

     VARIATION dot1qVlanForbiddenEgressPorts
     ACCESS read-only
     DESCRIPTION "Command line interface(CLI) is used to set this feature."

     VARIATION dot1qVlanStaticUntaggedPorts
     ACCESS read-only
     DESCRIPTION "Command line interface(CLI) is used to set this feature."

     VARIATION dot1qVlanStaticRowStatus
     ACCESS read-only
     DESCRIPTION "Command line interface(CLI) is used to set this feature."

     VARIATION dot1qPvid
     ACCESS read-only
     DESCRIPTION "Command line interface(CLI) is used to set this feature."

     VARIATION dot1qPortAcceptableFrameTypes
     ACCESS read-only
     DEFVAL { admitAll }
     DESCRIPTION "SSR firmware 3.1 does not support admitOnlyVlanTagged option."

     VARIATION dot1qPortIngressFiltering
     ACCESS read-only
     DEFVAL { true }
     DESCRIPTION "SSR firmware 3.1 does not support false option per port."

     VARIATION dot1qPortGvrpStatus
     ACCESS read-only
     DEFVAL { disabled }
     DESCRIPTION "GVRP/GARP not supported in firmware 3.1."


     -- ********************* ************ ************ *************** ***

     SUPPORTS P-BRIDGE-MIB
     INCLUDES { 
       pBridgeExtCapGroup,
       pBridgeDevicePriorityGroup,
       pBridgeDefaultPriorityGroup,
       pBridgePriorityGroup,
       pBridgeHCPortGroup
     }

     VARIATION dot1dTrafficClassesEnabled
     ACCESS read-only
     DEFVAL { true } 
     DESCRIPTION "SSR Firmware uses fixed traffic categorization per port in 3.1 release."

     VARIATION dot1dGmrpStatus
     ACCESS read-only
     DEFVAL { disabled } 
     DESCRIPTION "Not supported in release 3.1"

     VARIATION dot1dPortDefaultUserPriority
     ACCESS read-only
     DESCRIPTION "SSR Firmware uses fixed traffic categorization per port in 3.1 release."

     VARIATION dot1dRegenUserPriority
     ACCESS read-only
     DESCRIPTION "Command line interface(CLI) is used to set this feature."

     VARIATION dot1dTrafficClass
     ACCESS read-only
     DESCRIPTION "SSR Firmware uses fixed traffic categorization per port in 3.1 release."

     -- ********************* ************ ************ *************** ***

     SUPPORTS FRAME-RELAY-DTE-MIB
     INCLUDES { 
       frPortGroup, 
       frCircuitGroup,
       frErrGroup,
       frTrapGroup
     }
     VARIATION frDlcmiState
     ACCESS read-only
     DESCRIPTION "Command line interface(CLI) is used to set this feature."

     VARIATION frDlcmiAddress
     ACCESS read-only
     DESCRIPTION "Command line interface(CLI) is used to set this feature."

     VARIATION frDlcmiAddressLen
     ACCESS read-only
     DESCRIPTION "Command line interface(CLI) is used to set this feature."

     VARIATION frDlcmiPollingInterval
     ACCESS read-only
     DESCRIPTION "Command line interface(CLI) is used to set this feature."
     
     VARIATION frDlcmiFullEnquiryInterval
     ACCESS read-only
     DESCRIPTION "Command line interface(CLI) is used to set this feature."

     VARIATION frDlcmiErrorThreshold
     ACCESS read-only
     DESCRIPTION "Command line interface(CLI) is used to set this feature."

     VARIATION frDlcmiMonitoredEvents
     ACCESS read-only
     DESCRIPTION "Command line interface(CLI) is used to set this feature."

     VARIATION frDlcmiMaxSupportedVCs
     ACCESS read-only
     DESCRIPTION "Command line interface(CLI) is used to set this feature."

     VARIATION frDlcmiMulticast
     ACCESS read-only
     DESCRIPTION "Command line interface(CLI) is used to set this feature."

     VARIATION frDlcmiRowStatus
     ACCESS read-only
     DESCRIPTION "Command line interface(CLI) is used to create & delete dlcmi's."

     VARIATION frCircuitState
     ACCESS read-only
     DESCRIPTION "Command line interface(CLI) is used to set this feature."

     VARIATION frCircuitCommittedBurst
     ACCESS read-only
     DESCRIPTION "Command line interface(CLI) is used to set this feature."

     VARIATION frCircuitExcessBurst
     ACCESS read-only
     DESCRIPTION "Command line interface(CLI) is used to set this feature."

     VARIATION frCircuitThroughput
     ACCESS read-only
     DESCRIPTION "Command line interface(CLI) is used to set this feature."

     VARIATION frCircuitMulticast
     ACCESS read-only
     DESCRIPTION "Command line interface(CLI) is used to set this feature."

     VARIATION frCircuitLogicalIfIndex
     ACCESS read-only
     DESCRIPTION "Command line interface(CLI) is used to set this feature."

     VARIATION frCircuitRowStatus
     ACCESS read-only
     DESCRIPTION "Command line interface(CLI) is used to set this feature."

     -- ********************* ************ ************ *************** ***

--     SUPPORTS PPP-LCP-MIB
--     INCLUDES { 
--       smiv1 mib
--     }

     -- ********************* ************ ************ *************** ***

--     SUPPORTS PPP-SEC-MIB
--     INCLUDES { 
--       smiv1 mib
--     }

     -- ********************* ************ ************ *************** ***

--     SUPPORTS PPP-IP-NCP-MIB
--     INCLUDES { 
--       smiv1 mib
--     }

     -- ********************* ************ ************ *************** ***

--     SUPPORTS PPP-BRIDGE-NCP-MIB
--     INCLUDES { 
--       smiv1 mib
--     }

     -- ********************* ************ ************ *************** ***

     SUPPORTS DS1-MIB
     INCLUDES { 
        ds1NearEndConfigGroup,
        ds1NearEndStatisticsGroup
     }
     VARIATION dsx1LineType
     ACCESS read-only
     DESCRIPTION "Command line interface(CLI) is used to set this feature."

     VARIATION dsx1LineCoding
     ACCESS read-only
     DESCRIPTION "Command line interface(CLI) is used to set this feature."

     VARIATION dsx1SendCode
     ACCESS read-only
     DESCRIPTION "Command line interface(CLI) is used to set this feature."

     VARIATION dsx1CircuitIdentifier
     ACCESS read-only
     DESCRIPTION "Command line interface(CLI) is used to set this feature."

     VARIATION dsx1LoopbackConfig
     ACCESS read-only
     DESCRIPTION "Command line interface(CLI) is used to set this feature."

     VARIATION dsx1SignalMode
     ACCESS read-only
     DESCRIPTION "Command line interface(CLI) is used to set this feature."

     VARIATION dsx1TransmitClockSource
     ACCESS read-only
     DESCRIPTION "Command line interface(CLI) is used to set this feature."

     VARIATION dsx1Fdl
     ACCESS read-only
     DESCRIPTION "Command line interface(CLI) is used to set this feature."

     VARIATION dsx1LineLength
     ACCESS read-only
     DESCRIPTION "Command line interface(CLI) is used to set this feature."

     VARIATION dsx1LineStatusChangeTrapEnable
     ACCESS read-only
     DESCRIPTION "Command line interface(CLI) is used to set this feature."

     VARIATION dsx1Channelization
     ACCESS read-only
     DEFVAL  { disabled }
     DESCRIPTION "SSR Firmware 3.1 does not implement channelized T1/E1."


     -- ********************* ************ ************ *************** ***

     SUPPORTS DS3-MIB
     INCLUDES { 
        ds3NearEndConfigGroup,
        ds3NearEndStatisticsGroup
     }

     VARIATION dsx3LineType
     ACCESS read-only
     DESCRIPTION "Command line interface(CLI) is used to set this feature."

     VARIATION dsx3LineCoding
     ACCESS read-only
     DESCRIPTION "Command line interface(CLI) is used to set this feature."

     VARIATION dsx3SendCode
     ACCESS read-only
     DESCRIPTION "Command line interface(CLI) is used to set this feature."

     VARIATION dsx3CircuitIdentifier
     ACCESS read-only
     DESCRIPTION "Command line interface(CLI) is used to set this feature."

     VARIATION dsx3LoopbackConfig
     ACCESS read-only
     DESCRIPTION "Command line interface(CLI) is used to set this feature."

     VARIATION dsx3TransmitClockSource
     ACCESS read-only
     DESCRIPTION "Command line interface(CLI) is used to set this feature."

     VARIATION dsx3LineLength
     ACCESS read-only
     DESCRIPTION "Command line interface(CLI) is used to set this feature."

     VARIATION dsx3LineStatusChangeTrapEnable
     ACCESS read-only
     DESCRIPTION "Command line interface(CLI) is used to set this feature."

     VARIATION dsx3Channelization
     ACCESS read-only
     DEFVAL { disabled }
     DESCRIPTION "SSR 3.1 Firmware does not support channelized T3/E3."

     VARIATION dsx3Ds1ForRemoteLoop
     ACCESS read-only
     DESCRIPTION "Command line interface(CLI) is used to set this feature."

     -- ********************* ************ ************ *************** ***

     SUPPORTS SONET-MIB
     INCLUDES { 
        sonetMediumStuff, 
        sonetSectionStuff,
        sonetLineStuff,
        sonetFarEndLineStuff,
        sonetPathStuff,
        sonetFarEndPathStuff
     }

     -- atm cards with OC3 modular physical port (MODPHY) have above instrumentation
     -- POS OC3/12 do not implement these in 3.1 

     -- ********************* ************ ************ *************** ***

     SUPPORTS ATM-MIB
     INCLUDES { 
        atmInterfaceConfGroup,
        atmTrafficDescrGroup,
        atmInterfaceDs3PlcpGroup,
        atmInterfaceTCGroup,
        atmVpcTerminationGroup,
        atmVccTerminationGroup,
        atmVpCrossConnectGroup,
        atmVcCrossConnectGroup,
        aal5VccGroup
     }    

     -- ********************* ************ ************ *************** ***

     SUPPORTS RADIUS-AUTH-CLIENT-MIB
     INCLUDES { 
          radiusAuthClientMIBGroup
     }

     -- ********************* ************ ************ *************** ***

--     SUPPORTS RMON-MIB
--     INCLUDES { 
--         smiv1 mib
--     }

     -- ********************* ************ ************ *************** ***

     SUPPORTS RMON2-MIB
     INCLUDES { 
        protocolDirectoryGroup,
        protocolDistributionGroup,
        addressMapGroup,
        nlHostGroup,
        nlMatrixGroup,
        alHostGroup,
        alMatrixGroup,
        usrHistoryGroup,
        probeInformationGroup,
        rmon1EnhancementGroup,
        probeConfigurationGroup,
        rmon1EthernetEnhancementGroup
     }
     VARIATION filterProtocolDirDataLocalIndex
     ACCESS not-implemented
     DESCRIPTION "Feature not available in firmware version 3.1"

     VARIATION filterProtocolDirLocalIndex
     ACCESS not-implemented
     DESCRIPTION "Feature not available in firmware version 3.1"

     -- configuration sets to this mib are not persistent. Use CLI to 
     -- make rmon sets persistent across reboots.

     -- ********************* ************ ************ *************** ***

     SUPPORTS VRRP-MIB
     INCLUDES { 
        vrrpOperGroup,
        vrrpStatsGroup,
        vrrpTrapGroup,
        vrrpNotificationGroup
     }
     -- From Draft #9
     VARIATION vrrpOperAdminState
     ACCESS read-only
     DESCRIPTION "Command line interface(CLI) is used to set this feature."

     VARIATION vrrpOperPriority
     ACCESS read-only
     DESCRIPTION "Command line interface(CLI) is used to set this feature."

     VARIATION vrrpOperPrimaryIpAddr
     ACCESS read-only
     DESCRIPTION "Command line interface(CLI) is used to set this feature."

     VARIATION vrrpOperAuthType
     ACCESS read-only
     DESCRIPTION "Command line interface(CLI) is used to set this feature."

     VARIATION vrrpOperAuthKey
     ACCESS read-only
     DESCRIPTION "Command line interface(CLI) is used to set this feature."

     VARIATION vrrpOperAdvertisementInterval
     ACCESS read-only
     DESCRIPTION "Command line interface(CLI) is used to set this feature."

     VARIATION vrrpOperPreemptMode
     ACCESS read-only
     DESCRIPTION "Command line interface(CLI) is used to set this feature."

     VARIATION vrrpOperProtocol
     ACCESS read-only
     DESCRIPTION "Command line interface(CLI) is used to set this feature."

     VARIATION vrrpOperRowStatus
     ACCESS read-only
     DESCRIPTION "Command line interface(CLI) is used to set this feature."

     VARIATION vrrpAssoIpAddrRowStatus
     ACCESS read-only
     DESCRIPTION "Command line interface(CLI) is used to set this feature."

     VARIATION vrrpTrapAuthFailure
     ACCESS not-implemented
     DESCRIPTION "TrapAuthFailure not implemented in 3.1"


     -- ********************* ************ ************ *************** ***

     SUPPORTS CTRON-LFAP-MIB
     INCLUDES { 
        lfapConfGroupV40
     }

     -- ********************* ************ ************ *************** ***

     SUPPORTS CTRON-SSR-POLICY-MIB
     INCLUDES { 
         polGroupV11        
     }

     -- ********************* ************ ************ *************** ***

     SUPPORTS CTRON-SSR-CONFIG-MIB
     INCLUDES { 
         configGroup20
     }

     
     -- ********************* ************ ************ *************** ***

     SUPPORTS CTRON-SSR-HARDWARE-MIB
     INCLUDES { 
         hwConfGroupV30
     }

     -- ********************* ************ ************ *************** ***

     SUPPORTS CTRON-SSR-SERVICE-STATUS-MIB
     INCLUDES { 
         ssConfGroupV11
     }

     -- ********************* ************ ************ *************** ***

     SUPPORTS CTRON-SSR-CAPACITY-MIB
     INCLUDES { 
         capConfGroupV10
     }

   ::= { ssrCapability 1 }

END
