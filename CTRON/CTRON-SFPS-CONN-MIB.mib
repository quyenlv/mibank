CTRON-SFPS-CONN-MIB DEFINITIONS ::= BEGIN

--  sfps-conn-mib.txt
--  Revision: 0.0.02
-- 
--  Cabletron Systems, Inc.
--  35 Industrial Way, P.O. Box 5005
--  Rochester, NH 03867-0505
--  (603) 332-9400
--  support@ctron.com

--  This module provides authoritative definitions for Cabletron's
--  enterprise specific Fast Packet Switching Services MIB.
--
--  This module will be extended, as required.
--

--  Cabletron Systems reserves the right to make changes in
--  specification and other information contained in this document
--  without prior notice.  The reader should consult Cabletron Systems
--  to determine whether any such changes have been made.
--
--  In no event shall Cabletron Systems be liable for any incidental,
--  indirect, special, or consequential damages whatsoever (including
--  but not limited to lost profits) arising out of or related to this
--  document or the information contained in it, even if Cabletron
--  Systems has been advised of, known, or should have known, the
--  possibility of such damages.
--
--  Cabletron grants vendors, end-users, and other interested parties
--  a non-exclusive license to use this Specification in connection
--  with the management of Cabletron products.
--  Copyright October 93 Cabletron Systems
--

 
IMPORTS
      OBJECT-TYPE
                FROM RFC-1212
      DisplayString
                FROM RFC1213-MIB
--      enterprises,
--      IpAddress, 
--      Counter, Gauge, 
      TimeTicks
                FROM RFC1155-SMI

--  These Objects are defined in the file sfps-inc.mib.txt
        sfpsServiceCenter
        
                FROM CTRON-SFPS-INCLUDE-MIB;

--  Textual Conventions

HexInteger ::= INTEGER
--  display this integer in hex format


-- CONNECT

sfpsServiceCenterConnectTable     OBJECT-TYPE
        SYNTAX  SEQUENCE OF SfpsServiceCenterConnectEntry
        ACCESS  not-accessible
        STATUS  mandatory
        DESCRIPTION
                "This table gives connect semantics to call processing."
        ::= { sfpsServiceCenter 4 }

sfpsServiceCenterConnectEntry    OBJECT-TYPE
        SYNTAX  SfpsServiceCenterConnectEntry
        ACCESS  not-accessible
        STATUS  mandatory
        DESCRIPTION
                "Each entry contains the configuration of the Connect Entry."
        INDEX   { sfpsServiceCenterConnectAddress } 
        ::= { sfpsServiceCenterConnectTable 1 }

SfpsServiceCenterConnectEntry ::=
        SEQUENCE {
                sfpsServiceCenterConnectAddress         HexInteger,  
                sfpsServiceCenterConnectMetric          INTEGER,  
                sfpsServiceCenterConnectName            DisplayString,  
                sfpsServiceCenterConnectOperStatus      INTEGER,  
                sfpsServiceCenterConnectAdminStatus     INTEGER,
                sfpsServiceCenterConnectStatusTime      TimeTicks,
                sfpsServiceCenterConnectRequests        INTEGER,
                sfpsServiceCenterConnectResponses       INTEGER
                  
         }  

sfpsServiceCenterConnectAddress   OBJECT-TYPE
        SYNTAX  HexInteger  
        ACCESS  read-only
        STATUS  mandatory
        DESCRIPTION
                "Server hash, part of instance key."
        ::= { sfpsServiceCenterConnectEntry 1 }

sfpsServiceCenterConnectMetric   OBJECT-TYPE
        SYNTAX  INTEGER
        ACCESS  read-only
        STATUS  mandatory
        DESCRIPTION
                "Defines order servers are called low to high."
        ::= { sfpsServiceCenterConnectEntry 2 }

sfpsServiceCenterConnectName   OBJECT-TYPE
        SYNTAX  DisplayString
        ACCESS  read-only
        STATUS  mandatory
        DESCRIPTION
                "Server name."
        ::= { sfpsServiceCenterConnectEntry 3 }

sfpsServiceCenterConnectOperStatus   OBJECT-TYPE
        SYNTAX  INTEGER  {
                        kStatusRunning(1),      --  all is well
                        kStatusHalted(2),       -- admin disabled
                        kStatusPending(3),      -- Trying to run, not there yet
                        kStatusFaulted(4),      -- Internal error, never will recover
                        kStatusNotStarted(5)    -- Not fully started yet
        }

        ACCESS  read-only
        STATUS  mandatory
        DESCRIPTION
                "Operational state of entry."
        ::= { sfpsServiceCenterConnectEntry 4 }

sfpsServiceCenterConnectAdminStatus   OBJECT-TYPE
        SYNTAX  INTEGER       {
                        other(1),               -- Not running or stopped
                        disable(2),             -- Please stop
                        enable(3)               -- Go
        }

        ACCESS  read-write
        STATUS  mandatory
        DESCRIPTION
                "Administrative State of Entry."
        ::= { sfpsServiceCenterConnectEntry 5 }

sfpsServiceCenterConnectStatusTime   OBJECT-TYPE
        SYNTAX  TimeTicks
        ACCESS  read-only
        STATUS  mandatory
        DESCRIPTION
                "Time Tick of last operStatus change."
        ::= { sfpsServiceCenterConnectEntry 6 }

sfpsServiceCenterConnectRequests   OBJECT-TYPE
        SYNTAX   INTEGER
        ACCESS  read-only
        STATUS  mandatory
        DESCRIPTION
                "Requests made to server."
        ::= { sfpsServiceCenterConnectEntry 7 }

sfpsServiceCenterConnectResponses   OBJECT-TYPE
        SYNTAX  INTEGER
        ACCESS  read-only
        STATUS  mandatory
        DESCRIPTION
                "GOOD replies by server."
        ::= { sfpsServiceCenterConnectEntry 8 }
 
END
