-- Copyright 1995 by 3Com Corporation.  All rights reserved.
-- MIB file name:  linkb-mib
-- available in these 3Com devices:  LinkBuilder 3GH hubs
-- For support or more info, check 3Com's web page at http://www.3com.com


		--		LinkBuilder 3GH Management Information Base (MIB)
		--		Version 1.0.7
	 	--		April 12, 1994

		--		3Com Corporation
        --		5400 Bayfront Plaza
        --		Santa Clara, CA 95052-8145
        --		(408) 764-5000

		--			Change History:
		--			 4/11/94	eah		Removed lbBridgePortAddressLearnedEvent and
		--								lbBridgePortAddressForgottenEvent traps
		--			 4/ 7/94	eah		Added lbBridgePortReceiveMulticastLimitExceededCount
		-- 			 6/30/93	eah		Added lbSystemSmtProxyEvents
		--			 6/15/93	eah		Added lbEthernetPortType
		--			 6/11/93	eah 	Added lbBridgeLocalIndex
		--			 5/29/93	eah		Deprecated lbSlot express attributes.
		--								lbFddiMacReceiveMulticastThreshold, and
		--								lbEthernetPortReceiveMulticastThreshold
		--								Added lbSlotBridgeFunctionCount,
		--								lbSlotBridgeFunctionBaseIndex,
		--								lbSystemSmtProxyTimeoutBase
		--			 3/ 9/93	eah		Added lbTrapEnterprise and lbTrapDest 
		--								groups
		--			 3/ 3/93	eah		Added enum for ESM to board type 
		--								objects
		--			 2/18/93	eah		Changed address threshold, address 
		--								learned, and address forgotten events 
		--								to use bridge attributes
		--								Created new groups lbBridge
		--								Deprecated lbExpress,
		--								lbExpressFddiPort, 
		--								lbExpressEthernetPort, and
		--								lbExpressEthernetPortAddress groups
		--								Added lbSystemBridgeFunctionCount to
		--								the lbSystem group
		--								Deprecated lbSystemExpressFunctionCount,
		--								lbSystemExpressFddiPortCount, and
		--								lbSystemExpressEthernetPortCount
		--		  	 1/19/93    eah		Replaced lbPowerSupplyFailureType by
		--								lbPowerSupplyLastFailure which is
		--								read-only and includes a none value
		--								lbPowerSupplyFailureType was deprecated
		--								Changed lbPowerSupplyFailureEvent to
		--								use new object
		--								Changed events to use new logical
		--								object oids
		--			 3/ 1/92	jp		Added new groups using logical
		--								numbering scheme. Marked old groups
		--								as deprecated.
		--			 6/ 4/92	jp		Added "lbFddiMacReceiveMulticastThreshold"
		--								and "lbEthernetPortReceiveMulticastThreshold"
		--								objects.
		--			 6/15/92	jp		Added "lbFddiMacBeaconHistory" object.
		

--------------------------------------------------------------------------------

		LB3GH-1-0-7 DEFINITIONS ::= BEGIN

		IMPORTS
			enterprises, Counter,
				NetworkAddress		FROM RFC1155-SMI
			DisplayString			FROM RFC1213-MIB
			OBJECT-TYPE				FROM RFC-1212
			TRAP-TYPE				FROM RFC-1215;

		--  This MIB module uses the extended OBJECT-TYPE macro as
		--  defined in [9], and the TRAP-TYPE macro as defined in [10].

		a3Com			OBJECT IDENTIFIER ::= { enterprises 43 }
		lb3gh			OBJECT IDENTIFIER ::= { a3Com 7 }

		-- This is the lb3ghMib MIB module.

		lb3ghMib		OBJECT IDENTIFIER ::= { lb3gh 1 }

		chassis			OBJECT IDENTIFIER ::= { lb3ghMib 1 }
		slot			OBJECT IDENTIFIER ::= { lb3ghMib 2 }
		smm				OBJECT IDENTIFIER ::= { lb3ghMib 3 }
		fbcm			OBJECT IDENTIFIER ::= { lb3ghMib 4 }
		fcm				OBJECT IDENTIFIER ::= { lb3ghMib 5 }
		port			OBJECT IDENTIFIER ::= { lb3ghMib 6 }
		elm				OBJECT IDENTIFIER ::= { lb3ghMib 7 }
		elmFddiMAC		OBJECT IDENTIFIER ::= { lb3ghMib 8 }
		elmEthernetPort	OBJECT IDENTIFIER ::= { lb3ghMib 9 }
		elmMACAddress	OBJECT IDENTIFIER ::= { lb3ghMib 10 }

		-- The following are new groups defined in this revision
		-- of the lb3gh-mib. These groups contain all the functionality
		-- of the above named groups plus newly defined objects.

		lbSystem						OBJECT IDENTIFIER ::= { lb3ghMib 11 }
		lbSlot							OBJECT IDENTIFIER ::= { lb3ghMib 12 }
		lbFddiMac						OBJECT IDENTIFIER ::= { lb3ghMib 13 }
		lbEthernetPort					OBJECT IDENTIFIER ::= { lb3ghMib 14 }
		lbFddiPort						OBJECT IDENTIFIER ::= { lb3ghMib 15 }
		lbExpress						OBJECT IDENTIFIER ::= { lb3ghMib 16 }
		lbExpressFddiPort				OBJECT IDENTIFIER ::= { lb3ghMib 17 }
		lbExpressEthernetPort			OBJECT IDENTIFIER ::= { lb3ghMib 18 }
		lbExpressEthernetPortAddress	OBJECT IDENTIFIER ::= { lb3ghMib 19 }
		lbPowerSupply					OBJECT IDENTIFIER ::= { lb3ghMib 20 }

		-- New group for bridge support

		lbBridge						OBJECT IDENTIFIER ::= { lb3ghMib 21 }

		-- New groups for controlling trap "filters"

		lbTrapEnterprise				OBJECT IDENTIFIER ::= { lb3ghMib 22 }
		lbTrapDest						OBJECT IDENTIFIER ::= { lb3ghMib 23 }

		-- The LinkBuilder 3GH Chassis Group
		-- The chassis group contains all objects used to manage the  
		-- LinkBuilder 3GH chassis.

		-- Note that this group has been marked as deprecated and is 
		-- included here for backward compatibilty. It will be removed 
		-- from the next revision of the lb3gh MIB. The objects defined 
		-- in this table are now available via the lbSystem group."

		chassisId OBJECT-TYPE
			SYNTAX	INTEGER 
			ACCESS	read-only
			STATUS	deprecated
			DESCRIPTION
					"The unique identifier assigned to this 
					station during manufacturing."
			::= { chassis 1 }

		chassisType OBJECT-TYPE
			SYNTAX	INTEGER {
						other(1),
						linkBuilder3GH(2)
					}
			ACCESS	read-only
			STATUS	deprecated
			DESCRIPTION
					"The type of the LinkBuilder 3GH 
					chassis."
			::= { chassis 2 }

		chassisRevision OBJECT-TYPE
			SYNTAX	OCTET STRING (SIZE (1))
			ACCESS	read-only
			STATUS	deprecated
			DESCRIPTION
					"The revision number of this chassis."
			::= { chassis 3 }

		chassisName OBJECT-TYPE
			SYNTAX	DisplayString (SIZE (0..128))
			ACCESS	read-only
			STATUS	deprecated
			DESCRIPTION
					"The text string describing this 
					chassis."
			::= { chassis 4 }

		chassisNameAbbrev OBJECT-TYPE
			SYNTAX	DisplayString (SIZE (0..128))
			ACCESS	read-only
			STATUS	deprecated
			DESCRIPTION
					"The text string describing the generic 
					name for this chassis."
			::= { chassis 5 }

		chassisManufacturer OBJECT-TYPE
			SYNTAX	DisplayString (SIZE (0..128))
			ACCESS	read-only
			STATUS	deprecated
			DESCRIPTION
					"The text string describing the 
					manufacturer of this chassis."
			::= { chassis 6 }

		chassisSlotCount OBJECT-TYPE
			SYNTAX	INTEGER
			ACCESS	read-only
			STATUS	deprecated
			DESCRIPTION
					"The number of slots in this chassis."
			::= { chassis 7 }

		chassisBuildTime OBJECT-TYPE
			SYNTAX	DisplayString (SIZE (0..128))
			ACCESS	read-only
			STATUS	deprecated
			DESCRIPTION
					"The build time of the LinkBuilder 3GH 
					system software."
			::= { chassis 8 }

		chassisSoftwareRevision OBJECT-TYPE
			SYNTAX	OCTET STRING (SIZE (4))  
			ACCESS	read-only
			STATUS	deprecated
			DESCRIPTION
					"The revision number of the 
					LinkBuilder 3GH system software."
			::= { chassis 9 }

		chassisControlPanelColumns OBJECT-TYPE
			SYNTAX	INTEGER 
			ACCESS	read-only
			STATUS	deprecated
			DESCRIPTION
					"The number of columns in the control 
					panel display."
			::= { chassis 10 }

		chassisControlPanelLines OBJECT-TYPE
			SYNTAX	INTEGER 
			ACCESS	read-only
			STATUS	deprecated
			DESCRIPTION
					"The number of lines in the control 
					panel display."
			::= { chassis 11 }

		chassisControlPanelText OBJECT-TYPE
			SYNTAX	DisplayString (SIZE (0..128))
			ACCESS	read-only
			STATUS	deprecated
			DESCRIPTION
					"The text currently displayed in the 
					control panel display."
			::= { chassis 12 }

		chassisAction OBJECT-TYPE
			SYNTAX	INTEGER {
						other(1),
						reset(2)
					}
			ACCESS	read-write
			STATUS	deprecated
			DESCRIPTION
					"This object, when read, always returns 
					the value other (1). The result of 
					setting this object to each acceptable 
					value is:

						reset:	resets the LinkBuilder 
						3GH system."
			::= { chassis 13 }


		-- The lb3gh Slot Table

		slotTable OBJECT-TYPE
			SYNTAX	SEQUENCE OF SlotEntry
			ACCESS	not-accessible
			STATUS	deprecated
			DESCRIPTION
					"A list of slot entries. A single 
					instance of this object exists for each 
					slot in the LinkBuilder 3GH chassis."
			::= { slot 1 }

		slotEntry OBJECT-TYPE
			SYNTAX	SlotEntry
			ACCESS	not-accessible
			STATUS	deprecated
			DESCRIPTION
					"A slot entry contains information 
					common to a specified slot within a 
					LinkBuilder 3GH system."
			INDEX	{ slotIndex }
			::= { slotTable 1 }

		SlotEntry ::=
			SEQUENCE {
				slotIndex
					INTEGER,
				slotBoardType
					INTEGER,
				slotBoardRevision
					OCTET STRING,
				slotBoardStatus
					INTEGER,
				slotBoardName
					DisplayString,
				slotBoardNameAbbrev
					DisplayString,
				slotBoardAction
					INTEGER
			}

		slotIndex OBJECT-TYPE
			SYNTAX	INTEGER
			ACCESS	read-only
			STATUS	deprecated
			DESCRIPTION
					"The physical slot number of this slot 
					within the LinkBuilder 3GH chassis."
			::= { slotEntry 1 }

		slotBoardType OBJECT-TYPE
			SYNTAX	INTEGER {
						unknown(1),
						emptySlot(2),
						smm(3),
						fbcm(4),
						fcm(5), 
						elm(6),
						esm(7),
						fcm2(8)
					}
			ACCESS	read-only
			STATUS	deprecated
			DESCRIPTION
					"The type of board residing in this 
					slot."
			::= { slotEntry 2 }
                
		slotBoardRevision OBJECT-TYPE
			SYNTAX	OCTET STRING (SIZE (1))
			ACCESS	read-only
			STATUS	deprecated
			DESCRIPTION
					"The revision number of the board in 
					this slot."
			::= { slotEntry 3 }

		slotBoardStatus OBJECT-TYPE
			SYNTAX	INTEGER {
						notPresent(1),
						testing(2),
						offline(3),
						online(4)
					}
			ACCESS	read-only
			STATUS	deprecated
			DESCRIPTION
					"The status of the board in this slot."
			::= { slotEntry 4 }

		slotBoardName OBJECT-TYPE
			SYNTAX	DisplayString (SIZE (0..256))
			ACCESS	read-only
			STATUS	deprecated
			DESCRIPTION
					"The text string describing this board 
					type."
			::= { slotEntry 5 }

		slotBoardNameAbbrev OBJECT-TYPE
			SYNTAX	DisplayString (SIZE (0..32))
			ACCESS	read-only
			STATUS	deprecated
			DESCRIPTION
					"The abbreviation describing this board 
					type." 
			::= { slotEntry 6 }

		slotBoardAction OBJECT-TYPE
			SYNTAX	INTEGER {
						other(1),
						runDiagnostics(2)
					}
			ACCESS	read-write
			STATUS	deprecated
			DESCRIPTION
					"This object, when read, always returns 
					the value other (1). The result of 
					setting this object to each acceptable 
					value is:

						runDiagnostics:	runs the board's
						offline diagnostics."
			::= { slotEntry 7 }


        -- The lb3gh SMM Table

		smmTable OBJECT-TYPE
			SYNTAX	SEQUENCE OF SMMEntry
			ACCESS	not-accessible
			STATUS	deprecated
			DESCRIPTION
					"A list of System Management Module 
					(SMM) entries. An entry exists for each 
					Slot Table Entry whose board type is 
					SMM. This table is indexed by the 
					physical slot number of this SMM within 
					the LinkBuilder 3GH chassis. The entries
					need not have consecutive slot indices.

					Note that this object has been marked as deprecated and is 
					included here for backward compatibilty. It will be removed 
					from the next revision of the lb3gh MIB. The objects defined 
					in this table are now available via the lbSlot table."
			::= { smm 1 }

		smmEntry OBJECT-TYPE
			SYNTAX	SMMEntry
			ACCESS	not-accessible
			STATUS	deprecated
			DESCRIPTION
					"An SMM entry contains information 
					common to a single System Management 
					Module (SMM) within a LinkBuilder 3GH 
					system."
			INDEX	{ smmSlotIndex }
			::= { smmTable 1 }

		SMMEntry ::=
			SEQUENCE {
				smmSlotIndex
					INTEGER,
				smmEthernetPortCount
					INTEGER,
				smmBaseEthernetPortIndex
					INTEGER
			}

		smmSlotIndex OBJECT-TYPE
			SYNTAX	INTEGER
			ACCESS	read-only
			STATUS	deprecated
			DESCRIPTION
					"The physical slot number of this slot 
					within the LinkBuilder 3GH chassis."
			::= { smmEntry 1 }

		smmEthernetPortCount OBJECT-TYPE
			SYNTAX	INTEGER
			ACCESS	read-only
			STATUS	deprecated
			DESCRIPTION
					"The number of Ethernet ports on this 
					board."
			::= { smmEntry 2 }

		smmBaseEthernetPortIndex OBJECT-TYPE
			SYNTAX	INTEGER
			ACCESS	read-only
			STATUS	deprecated
			DESCRIPTION
					"The system-wide index for the first 
					Ethernet port on this board."
			::= { smmEntry 3 }


		-- The lb3gh FBCM Table

		fbcmTable OBJECT-TYPE
			SYNTAX	SEQUENCE OF FBCMEntry
			ACCESS	not-accessible
			STATUS	deprecated
			DESCRIPTION
					"A list of FDDI Backbone Connectivity 
					Module (FBCM) entries. An entry exists 
					for each Slot Table Entry whose board 
					type is FBCM. This table is indexed by 
					the physical slot number of this FBCM 
					within the LinkBuilder 3GH chassis. 
					The entries need not have consecutive 
 					slot indices.

					Note that this object has been marked as deprecated and is 
					included here for backward compatibilty. It will be removed 
					from the next revision of the lb3gh MIB. The objects defined 
					in this table are now available via the lbSlot table."
			::= { fbcm 1 }

		fbcmEntry OBJECT-TYPE
			SYNTAX	FBCMEntry
			ACCESS	not-accessible
			STATUS	deprecated
			DESCRIPTION
					"An FBCM entry contains information 
					common to a single FDDI Backbone 
					Connectivity Module (FBCM) within a 
					LinkBuilder 3GH system."
			INDEX	{ fbcmSlotIndex }
			::= { fbcmTable 1 }

		FBCMEntry ::=
                SEQUENCE {
					fbcmSlotIndex
						INTEGER,
					fbcmMACCount
						INTEGER,
					fbcmBaseMACIndex
						INTEGER,
					fbcmPortCount
						INTEGER,
					fbcmBasePortIndex
						INTEGER
			}

		fbcmSlotIndex OBJECT-TYPE
			SYNTAX	INTEGER
			ACCESS	read-only
			STATUS	deprecated
			DESCRIPTION
					"The physical slot number of this slot 
					within the LinkBuilder 3GH chassis."
			::= { fbcmEntry 1 }

		fbcmMACCount OBJECT-TYPE
			SYNTAX	INTEGER
			ACCESS	read-only
			STATUS	deprecated
			DESCRIPTION
					"The number of FDDI MACs present on 
					this board."
			::= { fbcmEntry 2 }

		fbcmBaseMACIndex OBJECT-TYPE
			SYNTAX	INTEGER
			ACCESS	read-only
			STATUS	deprecated
			DESCRIPTION
					"The system-wide index of the first FDDI
					MAC on this board. Additional MACs on 
					this board will have consecutively 
					increasing MAC indices following 
					this index."
			::= { fbcmEntry 3 }

		fbcmPortCount OBJECT-TYPE
			SYNTAX	INTEGER
			ACCESS	read-only
			STATUS	deprecated
			DESCRIPTION
					"The number of FDDI ports present on 
					this board."
			::= { fbcmEntry 4 }

		fbcmBasePortIndex OBJECT-TYPE
			SYNTAX	INTEGER
			ACCESS	read-only
			STATUS	deprecated
			DESCRIPTION
					"The system-wide index of the first FDDI
					port on this board. Additional ports on 
					this board will have consecutively 
					increasing port indices following 
					this index."
			::= { fbcmEntry 5 }


		-- The lb3gh FCM Table

		fcmTable OBJECT-TYPE
			SYNTAX	SEQUENCE OF FCMEntry
			ACCESS	not-accessible
			STATUS deprecated
			DESCRIPTION
					"A list of FDDI Concentrator Module 
					(FCM) entries. An entry exists for each 
					Slot Table Entry whose board type is 
					FCM. This table is indexed by the 
					physical slot number of this FCM 
					within the LinkBuilder 3GH chassis. 
					The entries need not have consecutive 
					slot indices.

					Note that this object has been marked as deprecated and is 
					included here for backward compatibilty. It will be removed 
					from the next revision of the lb3gh MIB. The objects defined 
					in this table are now available via the lbSlot table."
			::= { fcm 1 }

		fcmEntry OBJECT-TYPE
			SYNTAX FCMEntry
			ACCESS not-accessible
			STATUS deprecated
			DESCRIPTION
					"An FCM entry contains information 
					common to a single FDDI Concentrator 
					Module (FCM) within a LinkBuilder 3GH 
					system."
			INDEX	{ fcmSlotIndex}
			::= { fcmTable 1 }

		FCMEntry ::=
			SEQUENCE {
				fcmSlotIndex
					INTEGER,
				fcmPortCount
					INTEGER,
				fcmBasePortIndex
					INTEGER
			}

		fcmSlotIndex OBJECT-TYPE
			SYNTAX	INTEGER
			ACCESS	read-only
			STATUS	deprecated
			DESCRIPTION
					"The physical slot number of this slot 
					within the LinkBuilder 3GH chassis."
			::= { fcmEntry 1 }

		fcmPortCount OBJECT-TYPE
			SYNTAX	INTEGER
			ACCESS	read-only
			STATUS	deprecated
			DESCRIPTION
					"The number of FDDI ports present on 
					this board."
			::= { fcmEntry 2 }

		fcmBasePortIndex OBJECT-TYPE
			SYNTAX	INTEGER
			ACCESS	read-only
			STATUS	deprecated
			DESCRIPTION
					"The system-wide index of the first 
					FDDI port on this board. Additional 
					ports on this board will have
					consecutively increasing port indices 
					following this index."
			::= { fcmEntry 3 }


 		-- The lb3gh Port Table

		portTable OBJECT-TYPE
			SYNTAX	SEQUENCE OF PortEntry
			ACCESS	not-accessible
			STATUS	deprecated
			DESCRIPTION
					"A list of port entries. A single 
					instance of this object exists for each 
					port (excluding Ethernet ports) in the 
					LinkBuilder 3GH system.

					Note that this object has been marked as deprecated and is 
					included here for backward compatibilty. It will be removed 
					from the next revision of the lb3gh MIB. The objects defined 
					in this table are now available either via the fddiPort group
					or the enetPort group."
			::= { port 1 }

		portEntry OBJECT-TYPE
			SYNTAX	PortEntry
			ACCESS	not-accessible
			STATUS	deprecated
			DESCRIPTION
					"A port entry contains information 
					common to a particular port located on 
					a particular board within the 
					LinkBuilder 3GH system."
			INDEX	{ portSlotIndex, portIndex}
			::= { portTable 1 }

		PortEntry ::=
			SEQUENCE {
				portSlotIndex
					INTEGER,
				portIndex
					INTEGER,
				portLabel
					DisplayString
			}

		portSlotIndex OBJECT-TYPE
			SYNTAX	INTEGER
			ACCESS	read-only
			STATUS	deprecated
			DESCRIPTION
					"The physical slot number of this slot 
					within the LinkBuilder 3GH chassis."
			::= { portEntry 1 }

		portIndex OBJECT-TYPE
			SYNTAX	INTEGER
			ACCESS	read-only
			STATUS	deprecated
			DESCRIPTION
					"The index of the port on a particular 
					slot."
			::= { portEntry 2 }

		portLabel OBJECT-TYPE
			SYNTAX	DisplayString (SIZE (0..32))
			ACCESS	read-write
			STATUS	deprecated
			DESCRIPTION
					"An ASCII text string describing this 
					port."
			::= { portEntry 3 }


        -- The lb3gh ELM Table

		elmTable OBJECT-TYPE
			SYNTAX	SEQUENCE OF ELMEntry
			ACCESS	not-accessible
			STATUS	deprecated
			DESCRIPTION
					"A list of Ethernet LAN Module (ELM) 
					entries. An entry exists for each 
					Slot Table Entry whose board type is 
					ELM. This table is indexed by the 
					physical slot number of this ELM 
					within the LinkBuilder 3GH chassis. 
					The entries need not have consecutive 
					slot indices.

					Note that this object has been marked as deprecated and is 
					included here for backward compatibilty. It will be removed 
					from the next revision of the lb3gh MIB. The objects defined 
					in this table are now available either via the slot group or
					the express group."
			::= { elm 1 }

		elmEntry OBJECT-TYPE
			SYNTAX	ELMEntry
			ACCESS	not-accessible
			STATUS	deprecated
			DESCRIPTION
					"An ELM entry contains information 
					common to a single Ethernet LAN Module 
					(ELM) within a LinkBuilder 3GH system."
			INDEX	{ elmSlotIndex }
			::= { elmTable 1 }

		ELMEntry ::=
			SEQUENCE {
				elmSlotIndex
					INTEGER,
				elmFddiMACCount
					INTEGER,
				elmBaseFddiMACIndex
					INTEGER,
				elmEthernetPortCount
					INTEGER,
				elmBaseEthernetPortIndex
					INTEGER,
				elmAddressThreshold
					INTEGER
			}

		elmSlotIndex OBJECT-TYPE
			SYNTAX	INTEGER
			ACCESS	read-only
			STATUS	deprecated
			DESCRIPTION
					"The physical slot number of this slot 
					within the LinkBuilder 3GH chassis."
			::= { elmEntry 1 }

		elmFddiMACCount OBJECT-TYPE
			SYNTAX	INTEGER
			ACCESS	read-only
			STATUS	deprecated
			DESCRIPTION
					"The number of FDDI MACs present on 
					this board."
			::= { elmEntry 2 }

		elmBaseFddiMACIndex OBJECT-TYPE
			SYNTAX	INTEGER
			ACCESS	read-only
			STATUS	deprecated
			DESCRIPTION
					"The system-wide index of the first 
					FDDI MAC on this board. Additional ports
					on this board will have consecutively 
					increasing port indices following 
					this index."
			::= { elmEntry 3 }

		elmEthernetPortCount OBJECT-TYPE
			SYNTAX	INTEGER
			ACCESS	read-only
			STATUS	deprecated
			DESCRIPTION
					"The number of Ethernet ports present 
					on this board."
			::= { elmEntry 4 }

		elmBaseEthernetPortIndex OBJECT-TYPE
			SYNTAX	INTEGER
			ACCESS	read-only
			STATUS	deprecated
			DESCRIPTION
					"The system-wide index of the first 
					Ethernet port on this board. Additional 
					ports on this board will have
					consecutively increasing port indices 
					following this index."
			::= { elmEntry 5 }

		elmAddressThreshold OBJECT-TYPE
			SYNTAX	INTEGER 
			ACCESS	read-write
			STATUS	deprecated
			DESCRIPTION
					"A reporting threshold for the total 
					number of Ethernet addresses known for 
					this board. When the threshold is 
					reached, the event elmAddress-
					ThresholdEvent is generated."
			::= { elmEntry 6 }


        -- The lb3gh ELM FDDI MAC Table

		elmFddiMACTable OBJECT-TYPE
			SYNTAX	SEQUENCE OF ELMFddiMACEntry
			ACCESS	not-accessible
			STATUS	deprecated
			DESCRIPTION
					"A list of ELM FDDI MAC entries. The 
					entries need not have consecutive 
					slot indices.

					Note that this object has been marked as deprecated and is 
					included here for backward compatibilty. It will be removed 
					from the next revision of the lb3gh MIB. The objects defined 
					in this table are now available via the expressFddiPort group."
			::= { elmFddiMAC 1 }

		elmFddiMACEntry OBJECT-TYPE
			SYNTAX	ELMFddiMACEntry
			ACCESS	not-accessible
			STATUS	deprecated
			DESCRIPTION
					"An ELM FDDI MAC entry contains 
					information common to an FDDI MAC 
					located on an ELM within a 
					LinkBuilder 3GH system."
			INDEX	{ elmFddiSlotIndex, elmFddiMACIndex}
			::= { elmFddiMACTable 1 }

		ELMFddiMACEntry ::=
			SEQUENCE {
				elmFddiSlotIndex
					INTEGER,
				elmFddiMACIndex
					INTEGER,
				elmFddiMACForwardedCts
					Counter,
				elmFddiMACDroppedCts
					Counter
			}

		elmFddiSlotIndex OBJECT-TYPE
			SYNTAX	INTEGER
			ACCESS	read-only
			STATUS	deprecated
			DESCRIPTION
					"The physical slot number of 
					this board."
			::= { elmFddiMACEntry 1 }

		elmFddiMACIndex OBJECT-TYPE
			SYNTAX	INTEGER
			ACCESS	read-only
			STATUS	deprecated
			DESCRIPTION
					"A unique value for each FDDI MAC 
					on this board."
			::= { elmFddiMACEntry 2 }

		elmFddiMACForwardedCts OBJECT-TYPE
			SYNTAX	Counter
			ACCESS	read-only
			STATUS	deprecated
			DESCRIPTION
					"A counter indicating the number of 
					frames forwarded by a MAC from an 
					Ethernet port to the FDDI network."
			::= { elmFddiMACEntry 3 }

		elmFddiMACDroppedCts OBJECT-TYPE
			SYNTAX	Counter
			ACCESS	read-only
			STATUS	deprecated
			DESCRIPTION
					"A counter indicating the number of 
					frames that were dropped by a MAC 
					due to local resource limitation or 
					unknown destination MAC address."
			::= { elmFddiMACEntry 4 }


        -- The lb3gh ELM Ethernet Port Table

		elmEthernetPortTable OBJECT-TYPE
			SYNTAX	SEQUENCE OF ELMEthernetPortEntry
			ACCESS	not-accessible
			STATUS	deprecated
			DESCRIPTION
					"A list of ELM Ethernet LAN port 
					entries. The slot indices may not be 
					consecutive. The MAC indices must be 
					consecutive.

					Note that this object has been marked as deprecated and is 
					included here for backward compatibilty. It will be removed 
					from the next revision of the lb3gh MIB. The objects defined 
					in this table are now available via the expressEthernetPort group."
			::= { elmEthernetPort 1 }

		elmEthernetPortEntry OBJECT-TYPE
			SYNTAX	ELMEthernetPortEntry
			ACCESS	not-accessible
			STATUS	deprecated
			DESCRIPTION
					"An ELM Ethernet LAN port entry contains
					information common to an Ethernet port 
					located on an Ethernet LAN Module (ELM) 
 					within a LinkBuilder 3GH system."
			INDEX	{ elmEthernetPortSlotIndex, elmEthernetPortIndex }
			::= { elmEthernetPortTable 1 }

		ELMEthernetPortEntry ::=
			SEQUENCE {
				elmEthernetPortSlotIndex
					INTEGER,
				elmEthernetPortIndex
					INTEGER,
				elmEthernetPortLabel
					DisplayString,
				elmEthernetPortForwardedCts
					Counter,
				elmEthernetPortDroppedCts
					Counter,
				elmEthernetPortUTurnCts
					Counter,
				elmEthernetPortState
					INTEGER,
				elmEthernetPortAction
					INTEGER
			}
            
		elmEthernetPortSlotIndex OBJECT-TYPE
			SYNTAX	INTEGER
			ACCESS	read-only
			STATUS	deprecated
			DESCRIPTION
					"The physical slot number of the slot 
					containing this port within the 
					LinkBuilder 3GH chassis."
			::= { elmEthernetPortEntry 1 }

		elmEthernetPortIndex OBJECT-TYPE
			SYNTAX	INTEGER
			ACCESS	read-only
			STATUS	deprecated
			DESCRIPTION
					"The index of the port on a particular 
					ELM board. This index ranges from 1 to 
					elmEthernetPortCount."
			::= { elmEthernetPortEntry 2 }

		elmEthernetPortLabel OBJECT-TYPE
			SYNTAX	DisplayString (SIZE (0..32))
			ACCESS	read-write
			STATUS	deprecated
			DESCRIPTION
					"An ASCII text string describing this 
					Ethernet port."
			::= { elmEthernetPortEntry 3 }

		elmEthernetPortForwardedCts OBJECT-TYPE
			SYNTAX	Counter
			ACCESS	read-only
			STATUS	deprecated
			DESCRIPTION
					"A counter indicating the number of 
					frames forwarded from this Ethernet 
					port onto the FDDI network."
			::= { elmEthernetPortEntry 4 }

		elmEthernetPortDroppedCts OBJECT-TYPE
			SYNTAX	Counter
			ACCESS	read-only
			STATUS	deprecated
			DESCRIPTION
					"A counter indicating the numer of 
					frames received on this port that were 
					dropped because the destination MAC 
					address was determined to be on the
					same Ethernet segment as the source 
					MAC address."
			::= { elmEthernetPortEntry 5 }

		elmEthernetPortUTurnCts OBJECT-TYPE
			SYNTAX	Counter
			ACCESS	read-only
			STATUS	deprecated
			DESCRIPTION
					"A counter indicating the number of 
					frames received on this Ethernet port 
					and directed to another Ethernet port."
			::= { elmEthernetPortEntry 6 }

		elmEthernetPortState OBJECT-TYPE
			SYNTAX	INTEGER {
						onlineActive(1),
						onlineInactive(2),
						offline(3)
					}
			ACCESS	read-write
			STATUS	deprecated
			DESCRIPTION
					"The state of the Ethernet LAN port. 
					This value can be set to enable or 
					disable the Ethernet LAN port."
			::= { elmEthernetPortEntry 7 }

		elmEthernetPortAction OBJECT-TYPE
			SYNTAX	INTEGER {
						other(1),
						freezeAddress(2),
						flushAddress(3),
						flushDynamicAddress(4)
					}
			ACCESS	read-write
			STATUS	deprecated
			DESCRIPTION
					"This object, when read, always returns 
					the value other (1). The result of 
					setting this object to each acceptable 
					value is:

						freezeAddress:	causes all the 
						learned dynamic addresses to be 
						converted into static addresses.

						flushAddress:	causes all the 
						addresses to be flushed from a 
						port's address list.

						flushDynamicAddress:  causes all
						a port's dynamic addresses 
						to be flushed from the port's 
						address list."

			::= { elmEthernetPortEntry 8 }


        -- The lb3gh ELM Ethernet MAC Address Table

		elmEthernetMACAddressTable OBJECT-TYPE
			SYNTAX	SEQUENCE OF ELMEthernetMACAddressEntry
			ACCESS	not-accessible
			STATUS	deprecated
			DESCRIPTION
					"A list of ELM Ethernet LAN Remote MAC 
					Address entries. The slot indices may 
					not be consecutive. The port indices 
					must be consecutive.

					Note that this object has been marked as deprecated and is 
					included here for backward compatibilty. It will be removed 
					from the next revision of the lb3gh MIB. The objects defined 
					in this table are now available via the expressEthernetPort group."
			::= { elmMACAddress 1 }

		elmEthernetMACAddressEntry OBJECT-TYPE
			SYNTAX	ELMEthernetMACAddressEntry
			ACCESS	not-accessible
			STATUS	deprecated
			DESCRIPTION
					"A collection of information describing 
					a remote Ethernet MAC detected to be 
					attached to an Ethernet LAN port."
			INDEX	{ elmEthernetMACAddressSlotIndex,
					elmEthernetMACAddressPortIndex,
					elmEthernetMACAddressIndex}
			::= { elmEthernetMACAddressTable 1 }

		ELMEthernetMACAddressEntry ::=
			SEQUENCE {
				elmEthernetMACAddressSlotIndex
					INTEGER,
				elmEthernetMACAddressPortIndex
					INTEGER,
				elmEthernetMACAddressIndex
					INTEGER,
				elmEthernetMACAddressType
					INTEGER,
				elmEthernetMACAddressRemoteAddress
					OCTET STRING,
				elmEthernetMACAddressIsStatic
					INTEGER,
				elmEthernetMACAddressStaticPort
					INTEGER,
				elmEthernetMACAddressAge
					INTEGER
			}

		elmEthernetMACAddressSlotIndex OBJECT-TYPE
			SYNTAX	INTEGER
			ACCESS	read-write
			STATUS	deprecated
			DESCRIPTION
					"The physical slot number of the slot 
					containing this ELM within the 
					within th LinkBuilder 3GH chassis."
			::= { elmEthernetMACAddressEntry 1 }

		elmEthernetMACAddressPortIndex OBJECT-TYPE
			SYNTAX	INTEGER
			ACCESS	read-write
			STATUS	deprecated
			DESCRIPTION
					"The port index of this address entry 
					within the table. This index ranges 
					from 1 to elmEthernetPortCount."
			::= { elmEthernetMACAddressEntry 2 }

		elmEthernetMACAddressIndex OBJECT-TYPE
			SYNTAX	INTEGER
			ACCESS	read-write
			STATUS	deprecated
			DESCRIPTION
					"The index of this address entry 
					within the table."
			::= { elmEthernetMACAddressEntry 3 }

		elmEthernetMACAddressType OBJECT-TYPE
			SYNTAX INTEGER {
						other(1),
						invalid(2)
					}
			ACCESS	read-write
			STATUS	deprecated
			DESCRIPTION
					"This object, when read, always returns 
					the value other (1). Setting this object
					to invalid (2) removes the corresponding
					address entry from the table."
			::= { elmEthernetMACAddressEntry 4 }

		elmEthernetMACAddressRemoteAddress OBJECT-TYPE
			SYNTAX	OCTET STRING (SIZE (6))
			ACCESS	read-write
			STATUS	deprecated
			DESCRIPTION
					"The remote MAC address detected on this
					Ethernet LAN port."
			::= { elmEthernetMACAddressEntry 5 }

		elmEthernetMACAddressIsStatic OBJECT-TYPE
			SYNTAX	INTEGER {
						isStatic(1),
						isDynamic(2)
					}
			ACCESS	read-write
			STATUS	deprecated
			DESCRIPTION
					"A value indicating whether this MAC 
					address was statically configured or 
					dynamically learned on this port."
			::= { elmEthernetMACAddressEntry 6 }

		elmEthernetMACAddressStaticPort OBJECT-TYPE
			SYNTAX	INTEGER
			ACCESS	read-write
			STATUS	deprecated
			DESCRIPTION
					"If the object elmEthernetMACAddress-
					IsStatic has value isStatic(1), this 
					object indicates the port for which
					this MAC address was statically 
					configured."
			::= { elmEthernetMACAddressEntry 7 }

		elmEthernetMACAddressAge OBJECT-TYPE
			SYNTAX	INTEGER
			ACCESS	read-write
			STATUS	deprecated
			DESCRIPTION
					"This object indicates the time elapsed 
					since this MAC address was added to this
					port's address table."
			::= { elmEthernetMACAddressEntry 8 }


		-- XXX NEW GROUPS
		-- The lb3gh system Group

		lbSystemId OBJECT-TYPE
			SYNTAX	INTEGER 
			ACCESS	read-only
			STATUS	mandatory
			DESCRIPTION
					"The unique identifier assigned to this system 
					during manufacturing."
			::= { lbSystem 1 }

		lbSystemType OBJECT-TYPE
			SYNTAX	INTEGER {
						other(1),
						tweleveSlot(2),
						fourSlot(3)
					}
			ACCESS	read-only
			STATUS	mandatory
			DESCRIPTION
					"The type of the LinkBuilder system."
			::= { lbSystem 2 }

		lbSystemName OBJECT-TYPE
			SYNTAX	DisplayString (SIZE (0..128))
			ACCESS	read-only
			STATUS	mandatory
			DESCRIPTION
					"The text string describing this system."
			::= { lbSystem 3 }

		lbSystemManufacturer OBJECT-TYPE
			SYNTAX	DisplayString (SIZE (0..128))
			ACCESS	read-only
			STATUS	mandatory
			DESCRIPTION
					"The text string describing the manufacturer of 
					this system."
			::= { lbSystem 4 }

		lbSystemBackplaneRevision OBJECT-TYPE
			SYNTAX	OCTET STRING (SIZE (1)) 
			ACCESS	read-only
			STATUS	mandatory
			DESCRIPTION
					"The revision level of the system backplane. 
					Bits 6 and 7 indicate the artwork revision.
					Bits 0 through 5 indicate the rework level."
			::= { lbSystem 5 }

		lbSystemSlotCount OBJECT-TYPE
			SYNTAX	INTEGER
			ACCESS	read-only
			STATUS	mandatory
			DESCRIPTION
					"The number of slots in the system."
			::= { lbSystem 6 }

		lbSystemMemorySize OBJECT-TYPE
			SYNTAX	INTEGER 
			ACCESS	read-only
			STATUS	mandatory
			DESCRIPTION
					"The amount of memory (RAM), in bytes, present
					on the system processor board." 
			::= { lbSystem 7 }

		lbSystemFlashMemorySize OBJECT-TYPE
			SYNTAX	INTEGER 
			ACCESS	read-only
			STATUS	mandatory
			DESCRIPTION
					"The amount of flash memory, in bytes, present
					on the system processor board."
			::= { lbSystem 8 }

		lbSystemNvMemorySize OBJECT-TYPE
			SYNTAX	INTEGER 
			ACCESS	read-only
			STATUS	mandatory
			DESCRIPTION
					"The amount of non-volatile memory, in bytes, 
					present on the system processor board." 
			::= { lbSystem 9 }

		lbSystemSoftwareRevision OBJECT-TYPE
			SYNTAX	OCTET STRING (SIZE (4)) 
			ACCESS	read-only
			STATUS	mandatory
			DESCRIPTION
					"The revision number of the LinkBuilder system software.
					Each byte indicates the following:
						byte 0:	major release number.
						byte 1:	minor release number.
						byte 2:	update number.
						byte 3:
							bits 7-6:	release type.
							bits 5-0:	supplemental identifier."
			::= { lbSystem 10 }

		lbSystemBuildTime OBJECT-TYPE
			SYNTAX	DisplayString (SIZE (0..128))
			ACCESS	read-only
			STATUS	mandatory
			DESCRIPTION
					"The build time of the system software."
			::= { lbSystem 11 }

		lbSystemControlPanelHardwareRevision OBJECT-TYPE
			SYNTAX	OCTET STRING (SIZE (1)) 
			ACCESS	read-only
			STATUS	mandatory
			DESCRIPTION
					"An 8-bit value specifying the revision level of 
					the control panel hardware."
			::= { lbSystem 12 }

		lbSystemControlPanelSoftwareRevision OBJECT-TYPE
			SYNTAX	OCTET STRING (SIZE (1)) 
			ACCESS	read-only
			STATUS	mandatory
			DESCRIPTION
					"An 8-bit value specifying the revision level of 
					the control panel software."
			::= { lbSystem 13 }

		lbSystemControlPanelLines OBJECT-TYPE
			SYNTAX	INTEGER 
			ACCESS	read-only
			STATUS	mandatory
			DESCRIPTION
					"The number of lines in the control panel
					display."
			::= { lbSystem 14 }

		lbSystemControlPanelColumns OBJECT-TYPE
			SYNTAX	INTEGER 
			ACCESS	read-only
			STATUS	mandatory
			DESCRIPTION
					"The number of columns in the control panel 
					display."
			::= { lbSystem 15 }

		lbSystemControlPanelText OBJECT-TYPE
			SYNTAX	OCTET STRING (SIZE (0..128))
			ACCESS	read-only
			STATUS	mandatory
			DESCRIPTION
					"The currently displayed text in the control panel 
					display."
			::= { lbSystem 16 }

		lbSystemFddiMacCount OBJECT-TYPE
			SYNTAX	INTEGER 
			ACCESS	read-only
			STATUS	mandatory
			DESCRIPTION
					"The number of FDDI MAC's present in the system." 
			::= { lbSystem 17 }

		lbSystemFddiPortCount OBJECT-TYPE
			SYNTAX	INTEGER 
			ACCESS	read-only
			STATUS	mandatory
			DESCRIPTION
					"The number of FDDI ports present in the system." 
			::= { lbSystem 18 }

		lbSystemEthernetPortCount OBJECT-TYPE
			SYNTAX	INTEGER 
			ACCESS	read-only
			STATUS	mandatory
			DESCRIPTION
					"The number of ethernet ports present in the system." 
			::= { lbSystem 19 }

		lbSystemExpressFunctionCount OBJECT-TYPE
			SYNTAX	INTEGER 
			ACCESS	read-only
			STATUS	deprecated
			DESCRIPTION
					"The number of Ethernet Express functions present in 
					 the system. Curently this value is equal to the number
					 of Express boards present in the system." 
			::= { lbSystem 20 }

		lbSystemExpressFddiPortCount OBJECT-TYPE
			SYNTAX	INTEGER 
			ACCESS	read-only
			STATUS	deprecated
			DESCRIPTION
					"The number of Ethernet Express FDDI ports present 
					 in the system." 
			::= { lbSystem 21 }

		lbSystemExpressEthernetPortCount OBJECT-TYPE
			SYNTAX	INTEGER 
			ACCESS	read-only
			STATUS	deprecated
			DESCRIPTION
					"The number of Ethernet Express ethernet ports 
					 present in the system." 
			::= { lbSystem 22 }

		lbSystemPowerSupplyCount OBJECT-TYPE
			SYNTAX	INTEGER 
			ACCESS	read-only
			STATUS	mandatory
			DESCRIPTION
					"The number of power supply units present in the system." 
			::= { lbSystem 23 }

		lbSystemAction OBJECT-TYPE
			SYNTAX	INTEGER {
						other(1),
						reset(2)
					}
			ACCESS	read-write
			STATUS	mandatory
			DESCRIPTION
					"This object, when read, always returns the value other (1).
					The behavior of setting this object to each of the 
					acceptable values is as follows:

						reset:	resets the LinkBuilder system."
			::= { lbSystem 24 }

		lbSystemBridgeFunctionCount OBJECT-TYPE
			SYNTAX	INTEGER 
			ACCESS	read-only
			STATUS	mandatory
			DESCRIPTION
					"The number of bridge functions present in 
					 the system. Curently this value is equal to the sum of
					 the number of Express and Switching modules in the system."
			::= { lbSystem 25 }

		lbSystemSmtProxyTimeoutBase OBJECT-TYPE
			SYNTAX	INTEGER (1..10)
			ACCESS	read-write
			STATUS	mandatory
			DESCRIPTION
					"The initial timeout value, in seconds, before the SMT 
					proxy attempts to backoff and retry.  Since the SMT proxy
					will attempt three retries before determining that the
					proxied station is not answering, with the timeout
					doubling for each retry, the total time for a request to
					time out is equal to seven times the base timeout value."
			::= { lbSystem 26 }

		lbSystemSmtProxyEvents OBJECT-TYPE
			SYNTAX	INTEGER {
						enable(1),
						disable(2)
					}
			ACCESS	read-write
			STATUS	mandatory
			DESCRIPTION
					"This object determines if the SMT proxy will generate
					traps for SMT events occuring at other stations.  If
					enabled, the SMT proxy will generate traps for all SMT
					events, those that occur locally, and those that occur
					at other stations.  If disabled, the SMT proxy will only
					generate traps for events which occur locally.  The 
					default value for this object is enabled(1)."
			::= { lbSystem 27 }


		-- The lb3gh Slot Table

		lbSlotTable OBJECT-TYPE
			SYNTAX	SEQUENCE OF LbSlotEntry
			ACCESS	not-accessible
			STATUS	mandatory
			DESCRIPTION
					"A list of slot entries. A single instance of this 
					object exists for each slot in the LinkBuilder system."
			::= { lbSlot 1 }

		lbSlotEntry OBJECT-TYPE
			SYNTAX	LbSlotEntry
			ACCESS	not-accessible
			STATUS	mandatory
			DESCRIPTION
					"A slot entry contains information common to a given 
					slot within a LinkBuilder system."
			INDEX	{ lbSlotIndex }
			::= { lbSlotTable 1 }

		LbSlotEntry ::=
			SEQUENCE {
				lbSlotIndex
					INTEGER,
				lbSlotBoardType
					INTEGER,
				lbSlotBoardRevision
					OCTET STRING,
				lbSlotBoardStatus
					INTEGER,
				lbSlotBoardName
					DisplayString,
				lbSlotBoardNameAbbrev
					DisplayString,
				lbSlotFddiMacCount
					INTEGER,
				lbSlotFddiMacBaseIndex
					INTEGER,
				lbSlotFddiPortCount
					INTEGER,
				lbSlotFddiPortBaseIndex
					INTEGER,
				lbSlotEthernetPortCount
					INTEGER,
				lbSlotEthernetPortBaseIndex
					INTEGER,
				lbSlotExpressFunctionCount
					INTEGER,
				lbSlotExpressFunctionBaseIndex
					INTEGER,
				lbSlotExpressFddiPortCount
					INTEGER,
				lbSlotExpressFddiPortBaseIndex
					INTEGER,
				lbSlotExpressEthernetPortCount
					INTEGER,
				lbSlotExpressEthernetPortBaseIndex
					INTEGER,
				lbSlotBoardAction
					INTEGER,
				lbSlotBridgeFunctionCount
					INTEGER,
				lbSlotBridgeFunctionBaseIndex
					INTEGER
			}

		lbSlotIndex OBJECT-TYPE
			SYNTAX	INTEGER
			ACCESS	read-only
			STATUS	mandatory
			DESCRIPTION
					"The physical slot number of this slot within the 
					 system."
			::= { lbSlotEntry 1 }

		lbSlotBoardType OBJECT-TYPE
			SYNTAX	INTEGER {
						unknown(1),
						emptySlot(2),
						spm(3),
						feam(4),
						fcm(5), 
						elm(6),
						esm(7),
						fcm2(8)
					}
			ACCESS	read-only
			STATUS	mandatory
			DESCRIPTION
					"The type of board residing in this slot."
			::= { lbSlotEntry 2 }
                
		lbSlotBoardRevision OBJECT-TYPE
			SYNTAX	OCTET STRING (SIZE (1))
			ACCESS	read-only
			STATUS	mandatory
			DESCRIPTION
					"The revision number of the board in this slot."
			::= { lbSlotEntry 3 }

		lbSlotBoardStatus OBJECT-TYPE
			SYNTAX	INTEGER {
						notPresent(1),
						testing(2),
						offline(3),
						online(4)
					}
			ACCESS	read-only
			STATUS	mandatory
			DESCRIPTION
					"The status of the board in this slot."
			::= { lbSlotEntry 4 }

		lbSlotBoardName OBJECT-TYPE
			SYNTAX	DisplayString (SIZE (0..256))
			ACCESS	read-only
			STATUS	mandatory
			DESCRIPTION
					"The text string describing this board."
			::= { lbSlotEntry 5 }

		lbSlotBoardNameAbbrev OBJECT-TYPE
			SYNTAX	DisplayString (SIZE (0..32))
			ACCESS	read-only
			STATUS	mandatory
			DESCRIPTION
					"The abbreviation used to describe this board." 
			::= { lbSlotEntry 6 }

		lbSlotFddiMacCount OBJECT-TYPE
			SYNTAX	INTEGER
			ACCESS	read-only
			STATUS	mandatory
			DESCRIPTION
					"The number of FDDI MAC's present in this slot."
			::= { lbSlotEntry 7 }

 		lbSlotFddiMacBaseIndex OBJECT-TYPE
			SYNTAX	INTEGER
			ACCESS	read-only
			STATUS	mandatory
			DESCRIPTION
					"The index of the first FDDI MAC in this slot."
			::= { lbSlotEntry 8 }

 		lbSlotFddiPortCount OBJECT-TYPE
			SYNTAX	INTEGER
			ACCESS	read-only
			STATUS	mandatory
			DESCRIPTION
					"The number of FDDI ports present in this slot."
			::= { lbSlotEntry 9 }

 		lbSlotFddiPortBaseIndex OBJECT-TYPE
			SYNTAX	INTEGER
			ACCESS	read-only
			STATUS	mandatory
			DESCRIPTION
					"The index of the first FDDI port in this slot."
			::= { lbSlotEntry 10 }

 		lbSlotEthernetPortCount OBJECT-TYPE
			SYNTAX	INTEGER
			ACCESS	read-only
			STATUS	mandatory
			DESCRIPTION
					"The number of ethernet ports present in this slot."
			::= { lbSlotEntry 11 }

 		lbSlotEthernetPortBaseIndex OBJECT-TYPE
			SYNTAX	INTEGER
			ACCESS	read-only
			STATUS	mandatory
			DESCRIPTION
					"The index of the first ethernet port in this slot."
			::= { lbSlotEntry 12 }

 		lbSlotExpressFunctionCount OBJECT-TYPE
			SYNTAX	INTEGER
			ACCESS	read-only
			STATUS	deprecated
			DESCRIPTION
					"The number of Express functions present in this slot."
			::= { lbSlotEntry 13 }

 		lbSlotExpressFunctionBaseIndex OBJECT-TYPE
			SYNTAX	INTEGER
			ACCESS	read-only
			STATUS	deprecated
			DESCRIPTION
					"The index of the first Express function in this slot."
			::= { lbSlotEntry 14 }

 		lbSlotExpressFddiPortCount OBJECT-TYPE
			SYNTAX	INTEGER
			ACCESS	read-only
			STATUS	deprecated
			DESCRIPTION
					"The number of Express FDDI ports present in this slot."
			::= { lbSlotEntry 15 }

 		lbSlotExpressFddiPortBaseIndex OBJECT-TYPE
			SYNTAX	INTEGER
			ACCESS	read-only
			STATUS	deprecated
			DESCRIPTION
					"The index of the first Express FDDI port in this slot."
			::= { lbSlotEntry 16 }

  		lbSlotExpressEthernetPortCount OBJECT-TYPE
			SYNTAX	INTEGER
			ACCESS	read-only
			STATUS	deprecated
			DESCRIPTION
					"The number of Express ethernet ports present 
					in this slot."
			::= { lbSlotEntry 17 }

 		lbSlotExpressEthernetPortBaseIndex OBJECT-TYPE
			SYNTAX	INTEGER
			ACCESS	read-only
			STATUS	deprecated
			DESCRIPTION
					"The index of the first Express ethernet port 
					in this slot."
			::= { lbSlotEntry 18 }

		lbSlotBoardAction OBJECT-TYPE
			SYNTAX	INTEGER {
						other(1),
						runDiagnostics(2)
					}
			ACCESS	read-write
			STATUS	mandatory
			DESCRIPTION
					"This object, when read, always returns the 
					value other (1). The behavior of setting this object 
					to each of the acceptable values is as follows:

						runDiagnostics:	runs the board's offline diagnostics."
			::= { lbSlotEntry 19 }

 		lbSlotBridgeFunctionCount OBJECT-TYPE
			SYNTAX	INTEGER
			ACCESS	read-only
			STATUS	mandatory
			DESCRIPTION
					"The number of bridge functions present in this slot."
			::= { lbSlotEntry 20 }

 		lbSlotBridgeFunctionBaseIndex OBJECT-TYPE
			SYNTAX	INTEGER
			ACCESS	read-only
			STATUS	mandatory
			DESCRIPTION
					"The index of the first bridge function in this slot."
			::= { lbSlotEntry 21 }


 		-- FDDI MAC group

		lbFddiMacTable OBJECT-TYPE
			SYNTAX	SEQUENCE OF LbFddiMacEntry
			ACCESS	not-accessible
			STATUS	mandatory
			DESCRIPTION
					"A list of FDDI MAC entries. A single instance of
					this object exists for each FDDI MAC present 
					in the system."
			::= { lbFddiMac 1 }

		lbFddiMacEntry OBJECT-TYPE
			SYNTAX	LbFddiMacEntry
			ACCESS	not-accessible
			STATUS	mandatory
			DESCRIPTION
					"An FDDI MAC entry contains information common to a 
					particular FDDI MAC within the system."
			INDEX	{ lbFddiMacIndex }
			::= { lbFddiMacTable 1 }

		LbFddiMacEntry ::=
			SEQUENCE {
				lbFddiMacIndex
					INTEGER,
				lbFddiMacSlotIndex
					INTEGER,
				lbFddiMacLocalIndex
					INTEGER,
				lbFddiMacByteReceiveRate
					INTEGER,
				lbFddiMacPeakByteReceiveRate
					INTEGER,
				lbFddiMacFrameReceiveRate
					INTEGER,
				lbFddiMacPeakFrameReceiveRate
					INTEGER,
				lbFddiMacByteTransmitRate
					INTEGER,
				lbFddiMacPeakByteTransmitRate
					INTEGER,
				lbFddiMacFrameTransmitRate
					INTEGER,
				lbFddiMacPeakFrameTransmitRate
					INTEGER,
				lbFddiMacReceiveMulticastThreshold
					INTEGER,
				lbFddiMacBeaconHistory
					OCTET STRING
			}

		lbFddiMacIndex OBJECT-TYPE
			SYNTAX	INTEGER
			ACCESS	read-only
			STATUS	mandatory
			DESCRIPTION
					"A unique value for each FDDI MAC in the system.
					The MAC identified by a particular value of this 
					index is the same MAC as identified by the same 
					value of ifIndex."
			::= { lbFddiMacEntry 1 }

		lbFddiMacSlotIndex OBJECT-TYPE
			SYNTAX	INTEGER
			ACCESS	read-only
			STATUS	mandatory
			DESCRIPTION
					"The slot number corresponding to the physical location
					of this MAC."
			::= { lbFddiMacEntry 2 }

		lbFddiMacLocalIndex OBJECT-TYPE
			SYNTAX	INTEGER
			ACCESS	read-only
			STATUS	mandatory
			DESCRIPTION
					"The index of this MAC relative to the slot on which it
					is physically present."
			::= { lbFddiMacEntry 3 }

		lbFddiMacByteReceiveRate OBJECT-TYPE
			SYNTAX	INTEGER
			ACCESS	read-only
			STATUS	mandatory
			DESCRIPTION
					"The average number of bytes received per second by this
					MAC during the most recent sampling period."
			::= { lbFddiMacEntry 4 }

		lbFddiMacPeakByteReceiveRate OBJECT-TYPE
			SYNTAX	INTEGER
			ACCESS	read-only
			STATUS	mandatory
			DESCRIPTION
					"The peak value of lbFddiMacByteReceiveRate for
					this MAC since the system was last initialized."
			::= { lbFddiMacEntry 5 }

		lbFddiMacFrameReceiveRate OBJECT-TYPE
			SYNTAX	INTEGER
			ACCESS	read-only
			STATUS	mandatory
			DESCRIPTION
					"The average number of frames received per second by this
					MAC during the most recent sampling period."
			::= { lbFddiMacEntry 6 }

		lbFddiMacPeakFrameReceiveRate OBJECT-TYPE
			SYNTAX	INTEGER
			ACCESS	read-only
			STATUS	mandatory
			DESCRIPTION
					"The peak value of lbFddiMacFrameReceiveRate for
					this MAC since the system was last initialized."
			::= { lbFddiMacEntry 7 }

		lbFddiMacByteTransmitRate OBJECT-TYPE
			SYNTAX	INTEGER
			ACCESS	read-only
			STATUS	mandatory
			DESCRIPTION
					"The average number of bytes transmitted per second by
					this MAC during the most recent sampling period."
			::= { lbFddiMacEntry 8 }

		lbFddiMacPeakByteTransmitRate OBJECT-TYPE
			SYNTAX	INTEGER
			ACCESS	read-only
			STATUS	mandatory
			DESCRIPTION
					"The peak value of lbFddiMacByteTransmitRate for
					this MAC since the system was last initialized."
			::= { lbFddiMacEntry 9 }

		lbFddiMacFrameTransmitRate OBJECT-TYPE
			SYNTAX	INTEGER
			ACCESS	read-only
			STATUS	mandatory
			DESCRIPTION
					"The average number of frames transmitted per second by 
					this MAC during the most recent sampling period."
			::= { lbFddiMacEntry 10 }

		lbFddiMacPeakFrameTransmitRate OBJECT-TYPE
			SYNTAX	INTEGER
			ACCESS	read-only
			STATUS	mandatory
			DESCRIPTION
					"The peak value of lbFddiMacFrameTransmitRate for
					this MAC since the system was last initialized."
			::= { lbFddiMacEntry 11 }

		lbFddiMacReceiveMulticastThreshold OBJECT-TYPE
			SYNTAX	INTEGER
			ACCESS	read-write
			STATUS	mandatory
			DESCRIPTION
					"The maximum number of multicast frames per second
					that can be received in the sample interval. The
					sample interval is one second. The default value
					for this object is zero which implies an infinite rate."
			::= { lbFddiMacEntry 12 }

		lbFddiMacBeaconHistory OBJECT-TYPE
			SYNTAX	OCTET STRING (SIZE (0..256))
			ACCESS	read-only
			STATUS	mandatory
			DESCRIPTION
					"This object gives a history of the most recent beacon
					information received on this MAC. It can contain up to
					a maximum of eight records. Each record is of the form:
						source MAC:				6 bytes
						beacon data length:		2 bytes.
						beacon data:			0-16 bytes."
			::= { lbFddiMacEntry 13 }


 		-- Ethernet Port group

		lbEthernetPortTable OBJECT-TYPE
			SYNTAX	SEQUENCE OF LbEthernetPortEntry
			ACCESS	not-accessible
			STATUS	mandatory
			DESCRIPTION
					"A list of ethernet port entries. A single instance 
					of this object exists for each ethernet port present
					in the system."
			::= { lbEthernetPort 1 }

		lbEthernetPortEntry OBJECT-TYPE
			SYNTAX	LbEthernetPortEntry
			ACCESS	not-accessible
			STATUS	mandatory
			DESCRIPTION
					"An ethernet port entry contains information common to a 
					particular ethernet port within the system."
			INDEX	{ lbEthernetPortIndex }
			::= { lbEthernetPortTable 1 }

		LbEthernetPortEntry ::=
			SEQUENCE {
				lbEthernetPortIndex
					INTEGER,
				lbEthernetPortSlotIndex
					INTEGER,
				lbEthernetPortLocalIndex
					INTEGER,
				lbEthernetPortLabel
					DisplayString,
				lbEthernetPortChipsetType
					INTEGER,
				lbEthernetPortLinkStatus
					INTEGER,
				lbEthernetPortByteReceiveRate
					INTEGER,
				lbEthernetPortPeakByteReceiveRate
					INTEGER,
				lbEthernetPortFrameReceiveRate
					INTEGER,
				lbEthernetPortPeakFrameReceiveRate
					INTEGER,
				lbEthernetPortByteTransmitRate
					INTEGER,
				lbEthernetPortPeakByteTransmitRate
					INTEGER,
				lbEthernetPortFrameTransmitRate
					INTEGER,
				lbEthernetPortPeakFrameTransmitRate
					INTEGER,
				lbEthernetPortReceiveMulticastThreshold
					INTEGER,
				lbEthernetPortType
					INTEGER
			}

		lbEthernetPortIndex OBJECT-TYPE
			SYNTAX	INTEGER
			ACCESS	read-only
			STATUS	mandatory
			DESCRIPTION
					"A unique value for each ethernet port in the system.
					The port identified by a particular value of this 
					index is the same port as identified by the same 
					value of ifIndex."
			::= { lbEthernetPortEntry 1 }

		lbEthernetPortSlotIndex OBJECT-TYPE
			SYNTAX	INTEGER
			ACCESS	read-only
			STATUS	mandatory
			DESCRIPTION
					"The slot number corresponding to the physical location
					of this port."
			::= { lbEthernetPortEntry 2 }

		lbEthernetPortLocalIndex OBJECT-TYPE
			SYNTAX	INTEGER
			ACCESS	read-only
			STATUS	mandatory
			DESCRIPTION
					"The index of this port relative to the slot on which it
					is physically present."
			::= { lbEthernetPortEntry 3 }

		lbEthernetPortLabel OBJECT-TYPE
			SYNTAX	DisplayString (SIZE (0..32))
			ACCESS	read-write
			STATUS	mandatory
			DESCRIPTION
					"An ASCII text string describing this port."
			::= { lbEthernetPortEntry 4 }

		lbEthernetPortChipsetType OBJECT-TYPE
			SYNTAX	INTEGER {
						other(1),
						chipsetAMD79900(2),
						chipsetIntel82586(3),
						chipsetIntel82596(4),
						chipsetSEEQ8003(5),
						chipsetNational8390(6),
						chipsetNationalSonic(7),
						chipsetFujitsu86950(8)
					}
			ACCESS	read-only
			STATUS	mandatory
			DESCRIPTION
					"The type of chipset used to implement this port."
			::= { lbEthernetPortEntry 5 }

		lbEthernetPortLinkStatus OBJECT-TYPE
			SYNTAX	INTEGER {
						active(1),
						inActive(2)
					}
			ACCESS	read-only
			STATUS	mandatory
			DESCRIPTION
					"The current value of the link status for this port."
			::= { lbEthernetPortEntry 6 }

		lbEthernetPortByteReceiveRate OBJECT-TYPE
			SYNTAX	INTEGER
			ACCESS	read-only
			STATUS	mandatory
			DESCRIPTION
					"The average number of bytes received per second by this
					port during the most recent sampling period."
			::= { lbEthernetPortEntry 7 }

		lbEthernetPortPeakByteReceiveRate OBJECT-TYPE
			SYNTAX	INTEGER
			ACCESS	read-only
			STATUS	mandatory
			DESCRIPTION
					"The peak value of lbEthernetPortByteReceiveRate for
					this port since the system was last initialized."
			::= { lbEthernetPortEntry 8 }

		lbEthernetPortFrameReceiveRate OBJECT-TYPE
			SYNTAX	INTEGER
			ACCESS	read-only
			STATUS	mandatory
			DESCRIPTION
					"The average number of frames received per second by this
					port during the most recent sampling period."
			::= { lbEthernetPortEntry 9 }

		lbEthernetPortPeakFrameReceiveRate OBJECT-TYPE
			SYNTAX	INTEGER
			ACCESS	read-only
			STATUS	mandatory
			DESCRIPTION
					"The peak value of lbEthernetPortFrameReceiveRate for
					this port since the system was last initialized."
			::= { lbEthernetPortEntry 10 }

		lbEthernetPortByteTransmitRate OBJECT-TYPE
			SYNTAX	INTEGER
			ACCESS	read-only
			STATUS	mandatory
			DESCRIPTION
					"The average number of bytes transmitted per second by
					this port during the most recent sampling period."
			::= { lbEthernetPortEntry 11 }

		lbEthernetPortPeakByteTransmitRate OBJECT-TYPE
			SYNTAX	INTEGER
			ACCESS	read-only
			STATUS	mandatory
			DESCRIPTION
					"The peak value of lbEthernetPortByteTransmitRate for
					this port since the system was last initialized."
			::= { lbEthernetPortEntry 12 }

		lbEthernetPortFrameTransmitRate OBJECT-TYPE
			SYNTAX	INTEGER
			ACCESS	read-only
			STATUS	mandatory
			DESCRIPTION
					"The average number of frames transmitted per second by 
					this port during the most recent sampling period."
			::= { lbEthernetPortEntry 13 }

		lbEthernetPortPeakFrameTransmitRate OBJECT-TYPE
			SYNTAX	INTEGER
			ACCESS	read-only
			STATUS	mandatory
			DESCRIPTION
					"The peak value of lbEthernetPortFrameTransmitRate for
					this port since the system was last initialized."
			::= { lbEthernetPortEntry 14 }

		lbEthernetPortReceiveMulticastThreshold OBJECT-TYPE
			SYNTAX	INTEGER
			ACCESS	read-write
			STATUS	mandatory
			DESCRIPTION
					"The maximum number of multicast frames per second
					that can be received in the sample interval. The
					sample interval is one second. The default value
					for this object is zero which implies an infinite rate."
			::= { lbEthernetPortEntry 15 }

		lbEthernetPortType OBJECT-TYPE
			SYNTAX	INTEGER {
						telco10BaseT(1),
						rj4510BaseT(2),
						foirl(3),
						aui(4),
						other(5)
					}
			ACCESS	read-write
			STATUS	mandatory
			DESCRIPTION
					"Specific description of this port's type."
			::= { lbEthernetPortEntry 16 }


 		-- FDDI port group

		lbFddiPortTable OBJECT-TYPE
			SYNTAX	SEQUENCE OF LbFddiPortEntry
			ACCESS	not-accessible
			STATUS	mandatory
			DESCRIPTION
					"A list of FDDI port entries. A single instance of this
					object exists for each FDDI port in the system."
			::= { lbFddiPort 1 }

		lbFddiPortEntry OBJECT-TYPE
			SYNTAX	LbFddiPortEntry
			ACCESS	not-accessible
			STATUS	mandatory
			DESCRIPTION
					"A Port entry contains information common to a 
					particular FDDI port in the system."
			INDEX	{ lbFddiPortIndex }
			::= { lbFddiPortTable 1 }

		LbFddiPortEntry ::=
			SEQUENCE {
				lbFddiPortIndex
					INTEGER,
				lbFddiPortSlotIndex
					INTEGER,
				lbFddiPortLocalIndex
					INTEGER,
				lbFddiPortLabel
					DisplayString
			}

		lbFddiPortIndex OBJECT-TYPE
			SYNTAX	INTEGER
			ACCESS	read-only
			STATUS	mandatory
			DESCRIPTION
					"A unique value for each FDDI port in the system. 
					It's value ranges between 1 and the value of 
					lbSystemFddiPortCount."
			::= { lbFddiPortEntry 1 }

		lbFddiPortSlotIndex OBJECT-TYPE
			SYNTAX	INTEGER
			ACCESS	read-only
			STATUS	mandatory
			DESCRIPTION
					"The slot number corresponding to the physical location
					of this port."
			::= { lbFddiPortEntry 2 }

		lbFddiPortLocalIndex OBJECT-TYPE
			SYNTAX	INTEGER
			ACCESS	read-only
			STATUS	mandatory
			DESCRIPTION
					"The index of this port relative to the slot on which it
					is physically present."
			::= { lbFddiPortEntry 3 }

		lbFddiPortLabel OBJECT-TYPE
			SYNTAX	DisplayString (SIZE (0..32))
			ACCESS	read-write
			STATUS	mandatory
			DESCRIPTION
					"An ASCII text string describing this port."
			::= { lbFddiPortEntry 4 }


 		-- Express Function group

		lbExpressTable OBJECT-TYPE
			SYNTAX	SEQUENCE OF LbExpressEntry
			ACCESS	not-accessible
			STATUS	deprecated
			DESCRIPTION
					"A list of Express function entries."
			::= { lbExpress 1 }

		lbExpressEntry OBJECT-TYPE
			SYNTAX	LbExpressEntry
			ACCESS	not-accessible
			STATUS	deprecated
			DESCRIPTION
					"An Express entry contains information common to a 
					particular Express function in a given system."
			INDEX	{ lbExpressIndex }
			::= { lbExpressTable 1 }

		LbExpressEntry ::=
			SEQUENCE {
				lbExpressIndex
					INTEGER,
				lbExpressSlotIndex
					INTEGER,
				lbExpressLocalIndex
					INTEGER,
				lbExpressAddressThreshold
					INTEGER
			}

		lbExpressIndex OBJECT-TYPE
			SYNTAX	INTEGER
			ACCESS	read-only
			STATUS	deprecated
			DESCRIPTION
					"A unique value for each Express function in the system.
					It's value ranges between 1 and the value of
					lbSystemExpressFunctionCount."
			::= { lbExpressEntry 1 }

		lbExpressSlotIndex OBJECT-TYPE
			SYNTAX	INTEGER
			ACCESS	read-only
			STATUS	deprecated
			DESCRIPTION
					"The slot number corresponding to the physical location
					of this function."
			::= { lbExpressEntry 2 }

		lbExpressLocalIndex OBJECT-TYPE
			SYNTAX	INTEGER
			ACCESS	read-only
			STATUS	deprecated
			DESCRIPTION
					"The index of this function relative to the slot on which it
					is physically present."
			::= { lbExpressEntry 3 }

		lbExpressAddressThreshold OBJECT-TYPE
			SYNTAX	INTEGER 
			ACCESS	read-write
			STATUS	deprecated
			DESCRIPTION
					"A reporting threshold for the total number of Ethernet 
					Addresses known for this board. When this threshold 
					is reached, the event lbEemAddressThresholdEvent is 
					generated."
			::= { lbExpressEntry 4 }


  		-- Express FDDI Port group

		lbExpressFddiPortTable OBJECT-TYPE
			SYNTAX	SEQUENCE OF LbExpressFddiPortEntry
			ACCESS	not-accessible
			STATUS	deprecated
			DESCRIPTION
					"A list of Express FDDI port entries."
			::= { lbExpressFddiPort 1 }

		lbExpressFddiPortEntry OBJECT-TYPE
			SYNTAX	LbExpressFddiPortEntry
			ACCESS	not-accessible
			STATUS	deprecated
			DESCRIPTION
					"A Port entry contains information for a particular 
					Express FDDI port in a given system."
			INDEX	{ lbExpressFddiPortIndex }
			::= { lbExpressFddiPortTable 1 }

		LbExpressFddiPortEntry ::=
			SEQUENCE {
				lbExpressFddiPortIndex
					INTEGER,
				lbExpressFddiPortSlotIndex
					INTEGER,
				lbExpressFddiPortLocalIndex
					INTEGER,
				lbExpressFddiPortForwardedCts
					Counter,
				lbExpressFddiPortDroppedCts
					Counter
			}

		lbExpressFddiPortIndex OBJECT-TYPE
			SYNTAX	INTEGER
			ACCESS	read-only
			STATUS	deprecated
			DESCRIPTION
					"A unique value for each Express port in the system.
					It's value ranges between 1 and the value of
					lbSystemExpressFddiPortCount."
			::= { lbExpressFddiPortEntry 1 }

		lbExpressFddiPortSlotIndex OBJECT-TYPE
			SYNTAX	INTEGER
			ACCESS	read-only
			STATUS	deprecated
			DESCRIPTION
					"The slot number corresponding to the physical location
					of this port."
			::= { lbExpressFddiPortEntry 2 }

		lbExpressFddiPortLocalIndex OBJECT-TYPE
			SYNTAX	INTEGER
			ACCESS	read-only
			STATUS	deprecated
			DESCRIPTION
					"The index of this port relative to the slot on which it
					is physically present."
			::= { lbExpressFddiPortEntry 3 }

		lbExpressFddiPortForwardedCts OBJECT-TYPE
			SYNTAX	Counter
			ACCESS	read-only
			STATUS	deprecated
			DESCRIPTION
					"The number of frames forwarded by this MAC from
					 an ethernet port to the FDDI network."
			::= { lbExpressFddiPortEntry 4 }

		lbExpressFddiPortDroppedCts OBJECT-TYPE
			SYNTAX	Counter
			ACCESS	read-only
			STATUS	deprecated
			DESCRIPTION
					"The number of frames received by this MAC that
					 were not forwarded."
			::= { lbExpressFddiPortEntry 5 }


  		-- Express Ethernet Port group

		lbExpressEthernetPortTable OBJECT-TYPE
			SYNTAX	SEQUENCE OF LbExpressEthernetPortEntry
			ACCESS	not-accessible
			STATUS	deprecated
			DESCRIPTION
					"A list of Express ethernet port entries."
			::= { lbExpressEthernetPort 1 }

		lbExpressEthernetPortEntry OBJECT-TYPE
			SYNTAX	LbExpressEthernetPortEntry
			ACCESS	not-accessible
			STATUS	deprecated
			DESCRIPTION
					"An Expres ethernet port entry contains information
					common to a particular Express ethernet port located
					in the system."
			INDEX	{ lbExpressEthernetPortIndex }
			::= { lbExpressEthernetPortTable 1 }

		LbExpressEthernetPortEntry ::=
			SEQUENCE {
				lbExpressEthernetPortIndex
					INTEGER,
				lbExpressEthernetPortSlotIndex
					INTEGER,
				lbExpressEthernetPortLocalIndex
					INTEGER,
				lbExpressEthernetPortForwardedCts
					Counter,
				lbExpressEthernetPortDroppedCts
					Counter,
				lbExpressEthernetPortUTurnCts
					Counter,
				lbExpressEthernetPortAction
					INTEGER
			}

		lbExpressEthernetPortIndex OBJECT-TYPE
			SYNTAX	INTEGER
			ACCESS	read-only
			STATUS	deprecated
			DESCRIPTION
					"A unique value for each Express ethernet port in the 
					system. It's value ranges between 1 and the value of
					lbSystemExpressEthernetPortCount."
			::= { lbExpressEthernetPortEntry 1 }

		lbExpressEthernetPortSlotIndex OBJECT-TYPE
			SYNTAX	INTEGER
			ACCESS	read-only
			STATUS	deprecated
			DESCRIPTION
					"The slot number corresponding to the physical location
					of this port."
			::= { lbExpressEthernetPortEntry 2 }

		lbExpressEthernetPortLocalIndex OBJECT-TYPE
			SYNTAX	INTEGER
			ACCESS	read-only
			STATUS	deprecated
			DESCRIPTION
					"The index of this port relative to the slot on which it
					is physically present."
			::= { lbExpressEthernetPortEntry 3 }

		lbExpressEthernetPortForwardedCts OBJECT-TYPE
			SYNTAX	Counter
			ACCESS	read-only
			STATUS	deprecated
			DESCRIPTION
					"The number of frames forwarded from this ethernet
					 port to the FDDI network."
			::= { lbExpressEthernetPortEntry 4 }

		lbExpressEthernetPortDroppedCts OBJECT-TYPE
			SYNTAX	Counter
			ACCESS	read-only
			STATUS	deprecated
			DESCRIPTION
					"The number of frames received by this ethernet
					 port that were not forwarded or u-turned."
			::= { lbExpressEthernetPortEntry 5 }

		lbExpressEthernetPortUTurnCts OBJECT-TYPE
			SYNTAX	Counter
			ACCESS	read-only
			STATUS	deprecated
			DESCRIPTION
					"The number of frames received by this ethernet
					 port that were directed to another ethernet port."
			::= { lbExpressEthernetPortEntry 6 }

		lbExpressEthernetPortAction OBJECT-TYPE
			SYNTAX	INTEGER {
						other(1),
						freezeAddress(2),
						flushAddress(3),
						flushDynamicAddress(4)
					}
			ACCESS	read-write
			STATUS	deprecated
			DESCRIPTION
					"This object, when read, always returns the value other (1).
					The behavior of setting this object to each of the 
					acceptable values is as follows:

						freezeAddress:	causes all the learned dynamic addresses 
										to be converted into static addresses.

						flushAddress:	causes all the addresses to be flushed 
										from a port's address list.

						flushDynamicAddress:	
										causes all the port's dynamic addresses 
										to be flushed from a port's address list."

			::= { lbExpressEthernetPortEntry 7 }

 
      -- Express Ethernet port Address Table

		lbExpressEthernetPortAddressTable OBJECT-TYPE
			SYNTAX	SEQUENCE OF LbExpressEthernetPortAddressEntry
			ACCESS	not-accessible
			STATUS	deprecated
			DESCRIPTION
					"A list of Express Remote MAC Address entries."
			::= { lbExpressEthernetPortAddress 1 }

		lbExpressEthernetPortAddressEntry OBJECT-TYPE
			SYNTAX	LbExpressEthernetPortAddressEntry
			ACCESS	not-accessible
			STATUS	deprecated
			DESCRIPTION
					"An entry contains information describing a remote Ethernet 
					MAC detected to be attached to an Express port."
			INDEX	{ lbExpressEthernetPortAddressPortIndex, 
						lbExpressEthernetPortAddressIndex }
			::= { lbExpressEthernetPortAddressTable 1 }

		LbExpressEthernetPortAddressEntry ::=
			SEQUENCE {
				lbExpressEthernetPortAddressPortIndex
					INTEGER,
				lbExpressEthernetPortAddressIndex
					INTEGER,
				lbExpressEthernetPortAddressSlotIndex
					INTEGER,
				lbExpressEthernetPortAddressType
					INTEGER,
				lbExpressEthernetPortAddressRemoteAddress
					OCTET STRING,
				lbExpressEthernetPortAddressIsStatic
					INTEGER,
				lbExpressEthernetPortAddressStaticPort
					INTEGER,
				lbExpressEthernetPortAddressAge
					INTEGER
			}

		lbExpressEthernetPortAddressPortIndex OBJECT-TYPE
			SYNTAX	INTEGER
			ACCESS	read-write
			STATUS	deprecated
			DESCRIPTION
					"A unique value for each Express ethernet port in the
					 system. It's value ranges between 1 and the value of
					lbSystemExpressEthernetPortCount."
			::= { lbExpressEthernetPortAddressEntry 1 }

		lbExpressEthernetPortAddressIndex OBJECT-TYPE
			SYNTAX	INTEGER
			ACCESS	read-write
			STATUS	deprecated
			DESCRIPTION
					"The index of this address entry within the address table." 
			::= { lbExpressEthernetPortAddressEntry 2 }

		lbExpressEthernetPortAddressSlotIndex OBJECT-TYPE
			SYNTAX	INTEGER
			ACCESS	read-write
			STATUS	deprecated
			DESCRIPTION
					"The slot number corresponding to the physical location
					of this port."
			::= { lbExpressEthernetPortAddressEntry 3 }

		lbExpressEthernetPortAddressType OBJECT-TYPE
			SYNTAX INTEGER {
						other(1),
						invalid(2)
					}
			ACCESS	read-write
			STATUS	deprecated
			DESCRIPTION
					"This object, when read, always returns the value other (1).
					Setting this object to invalid (2) will remove the 
					corresponding address entry from the table."
			::= { lbExpressEthernetPortAddressEntry 4 }

		lbExpressEthernetPortAddressRemoteAddress OBJECT-TYPE
			SYNTAX	OCTET STRING (SIZE (6))
			ACCESS	read-write
			STATUS	deprecated
			DESCRIPTION
					"The remote MAC address detected on this port."
			::= { lbExpressEthernetPortAddressEntry 5 }

		lbExpressEthernetPortAddressIsStatic OBJECT-TYPE
			SYNTAX	INTEGER {
						isStatic(1),
						isDynamic(2)
					}
			ACCESS	read-write
			STATUS	deprecated
			DESCRIPTION
					"A value indicating whether this MAC address was statically 
					configured or was dynamically learned on this port."
			::= { lbExpressEthernetPortAddressEntry 6 }

		lbExpressEthernetPortAddressStaticPort OBJECT-TYPE
			SYNTAX	INTEGER
			ACCESS	read-write
			STATUS	deprecated
			DESCRIPTION
					"If the object lbExpressEthernetPortAddressIsStatic has 
					value isStatic(1), this object indicates the port for 
					which this MAC address was statically configured."
			::= { lbExpressEthernetPortAddressEntry 7 }

		lbExpressEthernetPortAddressAge OBJECT-TYPE
			SYNTAX	INTEGER
			ACCESS	read-write
			STATUS	deprecated
			DESCRIPTION
					"This object indicates the time, in seconds, elapsed since 
					this MAC address was added to this port's address table."
			::= { lbExpressEthernetPortAddressEntry 8 }


 		-- Power Supply group

		lbPowerSupplyTable OBJECT-TYPE
			SYNTAX	SEQUENCE OF LbPowerSupplyEntry
			ACCESS	not-accessible
			STATUS	mandatory
			DESCRIPTION
					"A list of power supply entries."
			::= { lbPowerSupply 1 }

		lbPowerSupplyEntry OBJECT-TYPE
			SYNTAX	LbPowerSupplyEntry
			ACCESS	not-accessible
			STATUS	mandatory
			DESCRIPTION
					"A power supply entry contains information common for
					a particular power supply unit in the system."
			INDEX	{ lbPowerSupplyIndex }
			::= { lbPowerSupplyTable 1 }

		LbPowerSupplyEntry ::=
			SEQUENCE {
				lbPowerSupplyIndex
					INTEGER,
				lbPowerSupplyLocation
					INTEGER,
				lbPowerSupplyStatus
					INTEGER,
				lbPowerSupplyFailureType
					INTEGER,
				lbPowerSupplyLastFailure
					INTEGER
			}

		lbPowerSupplyIndex OBJECT-TYPE
			SYNTAX	INTEGER
			ACCESS	read-only
			STATUS	mandatory
			DESCRIPTION
					"A unique value for each power supply in the system.
					It's value ranges between 1 and the value of
					lbSystemPowerSupplyCount."
			::= { lbPowerSupplyEntry 1 }

		lbPowerSupplyLocation OBJECT-TYPE
			SYNTAX	INTEGER
			ACCESS	read-only
			STATUS	mandatory
			DESCRIPTION
					"The physical slot in which this power supply unit 
					resides in the system."
			::= { lbPowerSupplyEntry 2 }

		lbPowerSupplyStatus OBJECT-TYPE
			SYNTAX INTEGER
			ACCESS	read-only
			STATUS	mandatory
			DESCRIPTION
					"The status of the power supply. A value of 0 indicates
					a working unit. A non-zero value represents a bit mask of
					the possible failure types. Each set bit indicates the
					following failure type:
						bit0:	systemAcFailure
						bit1:	systemPlus5Failure
						bit2:	systemPlus12Failure
						bit3:	systemOverTemperatureFailure."
			::= { lbPowerSupplyEntry 3 }

		lbPowerSupplyFailureType OBJECT-TYPE
			SYNTAX INTEGER {
						systemAcFailure(1),
						systemPlus5Failure(2),
						systemPlus12Failure(3),
						systemOverTemperatureFailure(4)
					}
			ACCESS	not-accessible
			STATUS	deprecated
			DESCRIPTION
					"This object is sent in the varlist when the 
					lbPowerSupplyFailureEvent trap is generated. It 
					indicates the particular failure type that caused
					this trap to be generated."
			::= { lbPowerSupplyEntry 4 }

		lbPowerSupplyLastFailure OBJECT-TYPE
			SYNTAX INTEGER {
						systemAcFailure(1),
						systemPlus5Failure(2),
						systemPlus12Failure(3),
						systemOverTemperatureFailure(4),
						none(5)
					}
			ACCESS	read-only
			STATUS	mandatory
			DESCRIPTION
					"This object represents the most recent power
					supply failure type.  If no failure has occured,
					the value of this object is none.  This object is
					included in the varlist when the lbPowerSupplyFailureEvent 
					trap is generated.  It indicates the failure type that 
					caused the trap to be generated."
			::= { lbPowerSupplyEntry 5 }


 		-- Bridge Function Group

		lbBridgeTable OBJECT-TYPE
			SYNTAX	SEQUENCE OF LbBridgeEntry
			ACCESS	not-accessible
			STATUS	mandatory
			DESCRIPTION
					"A list of bridge function entries."
			::= { lbBridge 1 }

		lbBridgeEntry OBJECT-TYPE
			SYNTAX	LbBridgeEntry
			ACCESS	not-accessible
			STATUS	mandatory
			DESCRIPTION
					"A bridge entry contains information common to a 
					particular bridge function in a given system."
			INDEX	{ lbBridgeIndex }
			::= { lbBridgeTable 1 }

		LbBridgeEntry ::=
			SEQUENCE {
				lbBridgeIndex
					INTEGER,
				lbBridgeBaseSlotIndex
					INTEGER,
				lbBridgePortCount
					INTEGER,
				lbBridgeAddressTableSize
					INTEGER,
				lbBridgeAddressThreshold
					INTEGER,
				lbBridgeMode
					INTEGER,
				lbBridgeLocalIndex
					INTEGER
			}

		lbBridgeIndex OBJECT-TYPE
			SYNTAX	INTEGER
			ACCESS	read-only
			STATUS	mandatory
			DESCRIPTION
					"A unique value for each bridge function in the system.
					It's value ranges between 1 and the value of
					lbSystemBridgeFunctionCount."
			::= { lbBridgeEntry 1 }

		lbBridgeBaseSlotIndex OBJECT-TYPE
			SYNTAX	INTEGER
			ACCESS	read-only
			STATUS	mandatory
			DESCRIPTION
					"The slot number of the lowest numbered slot which 
					contains a physical port that this bridge function 
					controls."
			::= { lbBridgeEntry 2 }

		lbBridgePortCount OBJECT-TYPE
			SYNTAX	INTEGER
			ACCESS	read-only
			STATUS	mandatory
			DESCRIPTION
					"The number of ports that this bridge function controls."
			::= { lbBridgeEntry 3 }

		lbBridgeAddressTableSize OBJECT-TYPE
			SYNTAX	INTEGER 
			ACCESS	read-only
			STATUS	mandatory
			DESCRIPTION
					"The size of the address table for this bridge function."
			::= { lbBridgeEntry 4 }

		lbBridgeAddressThreshold OBJECT-TYPE
			SYNTAX	INTEGER 
			ACCESS	read-write
			STATUS	mandatory
			DESCRIPTION
					"A reporting threshold for the total number of 
					addresses known for this board. When this threshold 
					is reached, the event lbBridgeAddressThresholdEvent is 
					generated.  The range of valid values for setting this 
					object is between 1 and the value reported by 
					lbBridgeAddressTableSize + 1 (Note that this range
					applies to values issued in set requests.  The current
					value may be outside this range, for example if the value
					of lbBridgeMode is changed).  Setting this object to one
					greater than the address table size disables the generation
					of lbBridgeAddressThresholdEvents since the limit will 
					never be reached."
			::= { lbBridgeEntry 5 }

		lbBridgeMode OBJECT-TYPE
			SYNTAX	INTEGER {
						expressMode(1),
						ieee8021dBridgeMode(2),
						notSupported(3)
					}
			ACCESS	read-write
			STATUS	mandatory
			DESCRIPTION
					"The operational mode of this bridge function.  Note that
					bridges which report notSupported(3) will not support sets
					of this object, and that the value notSupported(3) is not
					a valid value for a set operation."
			::= { lbBridgeEntry 6 }

		lbBridgeLocalIndex OBJECT-TYPE
			SYNTAX	INTEGER
			ACCESS	read-only
			STATUS	mandatory
			DESCRIPTION
					"The index of this bridge function relative to the slot 
					on which it is physically present."
			::= { lbBridgeEntry 7 }


  		-- Bridge Port Table

		lbBridgePortTable OBJECT-TYPE
			SYNTAX	SEQUENCE OF LbBridgePortEntry
			ACCESS	not-accessible
			STATUS	mandatory
			DESCRIPTION
					"A list of bridge port entries."
			::= { lbBridge 2 }

		lbBridgePortEntry OBJECT-TYPE
			SYNTAX	LbBridgePortEntry
			ACCESS	not-accessible
			STATUS	mandatory
			DESCRIPTION
					"A Port entry contains information for a particular 
					bridge port in a given system."
			INDEX	{ lbBridgePortBridgeIndex, lbBridgePortIndex }
			::= { lbBridgePortTable 1 }

		LbBridgePortEntry ::=
			SEQUENCE {
				lbBridgePortBridgeIndex
					INTEGER,
				lbBridgePortIndex
					INTEGER,
				lbBridgePortSlotIndex
					INTEGER,
				lbBridgePortLocalIndex
					INTEGER,
				lbBridgePortType
					INTEGER,
				lbBridgePortIpFragmentationEnabled
					INTEGER,
				lbBridgePortReceiveMulticastLimit
					INTEGER,
				lbBridgePortAddressAction
					INTEGER,
				lbBridgePortTotalForwardedCts
					Counter,
				lbBridgePortManagementFramesReceived
					Counter,
				lbBridgePortTotalDiscards
					Counter,
				lbBridgePortReceiveBlockedDiscards
					Counter,
				lbBridgePortReceiveMulticastLimitExceededs
					Counter,
				lbBridgePortReceiveSecurityDiscards
					Counter,
				lbBridgePortReceiveUnknownDiscards
					Counter,
				lbBridgePortReceiveOtherDiscards
					Counter,
				lbBridgePortReceiveErrorDiscards
					Counter,
				lbBridgePortSameSegmentDiscards
					Counter,
				lbBridgePortTransmitBlockedDiscards
					Counter,
				lbBridgePortTotalFiltered
					Counter,
				lbBridgePortReceiveUnicastFiltered
					Counter,
				lbBridgePortReceiveMulticastFiltered
					Counter,
				lbBridgePortTransmitUnicastFiltered
					Counter,
				lbBridgePortTransmitMulticastFiltered
					Counter,
				lbBridgePortReceiveMulticastLimitExceededCount
					Counter
			}

		lbBridgePortBridgeIndex OBJECT-TYPE
			SYNTAX	INTEGER
			ACCESS	read-only
			STATUS	mandatory
			DESCRIPTION
					"A unique value for each bridge function in the system.
					It's value ranges between 1 and the value of
					lbSystemBridgeFunctionCount."
			::= { lbBridgePortEntry 1 }

		lbBridgePortIndex OBJECT-TYPE
			SYNTAX	INTEGER
			ACCESS	read-only
			STATUS	mandatory
			DESCRIPTION
					"A unique value for each bridge port controlled by a given
					bridge function.  It's value ranges between 1 and the 
					value of lbBridgePortCount for the bridge function
					which this entry references."
			::= { lbBridgePortEntry 2 }

		lbBridgePortSlotIndex OBJECT-TYPE
			SYNTAX	INTEGER
			ACCESS	read-only
			STATUS	mandatory
			DESCRIPTION
					"The slot number corresponding to the physical location
					of this port."
			::= { lbBridgePortEntry 3 }

		lbBridgePortLocalIndex OBJECT-TYPE
			SYNTAX	INTEGER
			ACCESS	read-only
			STATUS	mandatory
			DESCRIPTION
					"The index of this port relative to the slot on which it
					is physically present and its port type.  For example
					FDDI ports in a slot are identified with local indices from
					1 to the number of FDDI ports in that slot, and the Ethernet
					ports in the same slot are identified with local indices from
					1 to the number of Ethernet ports in that slot."
			::= { lbBridgePortEntry 4 }

		lbBridgePortType OBJECT-TYPE
			SYNTAX  INTEGER {
						ethernet(1),
						fddi(2),
						other(3)
					}
			ACCESS  read-only
			STATUS  mandatory
			DESCRIPTION
					"The type of this port."
			::= { lbBridgePortEntry 5 }

		lbBridgePortIpFragmentationEnabled OBJECT-TYPE
			SYNTAX	INTEGER {
						true(1),
						false(2),
						notSupported(3)
					}
			ACCESS	read-write
			STATUS	mandatory
			DESCRIPTION
					"A flag indicating whether or not IP fragmentation is
					enabled on this bridge port.  Note that bridges which 
					report notSupported(3) will not support sets of this
					object, and that the value notSupported(3) is not
					a valid value for a set operation."
			::= { lbBridgePortEntry 6 }

		lbBridgePortReceiveMulticastLimit OBJECT-TYPE
			SYNTAX	INTEGER (0..65535)
			ACCESS	read-write
			STATUS	mandatory
			DESCRIPTION
					"The maximum number of multicast frames per second
					that can be received in the sample interval. The
					sample interval is four seconds. The default value
					for this object is zero which implies an infinite rate."
			::= { lbBridgePortEntry 7 }

		lbBridgePortAddressAction OBJECT-TYPE
			SYNTAX	INTEGER {
						other(1),
						freezeAddress(2),
						flushAddress(3),
						flushDynamicAddress(4)
					}
			ACCESS	read-write
			STATUS	mandatory
			DESCRIPTION
					"This object, when read, always returns the value other (1).
					The behavior of setting this object to each of the 
					acceptable values is as follows:

						freezeAddress:	causes all the learned dynamic addresses 
										to be converted into static addresses.

						flushAddress:	causes all the addresses to be flushed 
										from the port's address list.

						flushDynamicAddress:	
										causes all dynamic addresses to be
										flushed from the port's address list."
			::= { lbBridgePortEntry 8 }

		lbBridgePortTotalForwardedCts OBJECT-TYPE
			SYNTAX	Counter
			ACCESS	read-only
			STATUS	mandatory
			DESCRIPTION
					"The total number of frames forwarded from this port to
					all other ports of this bridge.  Note that the total forwarded
					count is NOT equal to the receive count minus the discard
					count, as a single received multicast/broadcast frame can
					be forwarded to multiple bridge ports.  Also frames which
					are 'flooded' because of unknown destination addresses
					account for multiple forwarding as well.  The total 
					forwarding count is the instantaneous sumation of the 
					'forwarded to' counts to all other ports of the bridge."
			::= { lbBridgePortEntry 9 }

		lbBridgePortManagementFramesReceived OBJECT-TYPE
			SYNTAX	Counter
			ACCESS	read-only
			STATUS	mandatory
			DESCRIPTION
					"The number of bridge management frames received by this
					port."
			::= { lbBridgePortEntry 10 }

		lbBridgePortTotalDiscards OBJECT-TYPE
			SYNTAX	Counter
			ACCESS	read-only
			STATUS	mandatory
			DESCRIPTION
					"The total number of frames discarded by this port."
			::= { lbBridgePortEntry 11 }

		lbBridgePortReceiveBlockedDiscards OBJECT-TYPE
			SYNTAX	Counter
			ACCESS	read-only
			STATUS	mandatory
			DESCRIPTION
					"The number of frames discarded by this port because the
					the receiving bridge port was not in the 'forwarding'
					state."
			::= { lbBridgePortEntry 12 }

		lbBridgePortReceiveMulticastLimitExceededs OBJECT-TYPE
			SYNTAX	Counter
			ACCESS	read-only
			STATUS	mandatory
			DESCRIPTION
					"The number of multicast/broadcast frames discarded by 
					this port because the lbBridgePortReceiveMulticastLimit
					was exceeded."
			::= { lbBridgePortEntry 13 }

		lbBridgePortReceiveSecurityDiscards OBJECT-TYPE
			SYNTAX	Counter
			ACCESS	read-only
			STATUS	mandatory
			DESCRIPTION
					"The number of frames discarded by this port because they
					contained source addresses which were statically configured
					on another bridge port.  A statically configured address
					(station), which is not allowed to move, appears to have
					moved."
			::= { lbBridgePortEntry 14 }

		lbBridgePortReceiveUnknownDiscards OBJECT-TYPE
			SYNTAX	Counter
			ACCESS	read-only
			STATUS	mandatory
			DESCRIPTION
					"The number of frames discarded by this port because the
					destination address was unknown.  Note that this counter
					is only valid for FDDI ports, and only when the bridge is an
					EEM, or an ESM operating in express mode."
			::= { lbBridgePortEntry 15 }

		lbBridgePortReceiveOtherDiscards OBJECT-TYPE
			SYNTAX	Counter
			ACCESS	read-only
			STATUS	mandatory
			DESCRIPTION
					"The number of frames discarded by this port because they
					contained either invalid (group) source addresses or
					source addresses belonging to this bridge (indicative of
					network loops)."
			::= { lbBridgePortEntry 16 }

		lbBridgePortReceiveErrorDiscards OBJECT-TYPE
			SYNTAX	Counter
			ACCESS	read-only
			STATUS	mandatory
			DESCRIPTION
					"The number of frames discarded by this port because of
					internal bridge system errors (e.g., hardware and 
					software address table discrepencies)."
			::= { lbBridgePortEntry 17 }

		lbBridgePortSameSegmentDiscards OBJECT-TYPE
			SYNTAX	Counter
			ACCESS	read-only
			STATUS	mandatory
			DESCRIPTION
					"The number of frames discarded by this port because the
					destination address is known on the same network segment
					as the source address, i.e., the frame does not need to 
					be bridged."
			::= { lbBridgePortEntry 18 }

		lbBridgePortTransmitBlockedDiscards OBJECT-TYPE
			SYNTAX	Counter
			ACCESS	read-only
			STATUS	mandatory
			DESCRIPTION
					"The number of frames discarded by this port because the
					the transmitting bridge port was not in the 'forwarding'
					state."
			::= { lbBridgePortEntry 19 }

		lbBridgePortTotalFiltered OBJECT-TYPE
			SYNTAX	Counter
			ACCESS	read-only
			STATUS	mandatory
			DESCRIPTION
					"The total number of frames discarded by this port due to
					user defined filters."
			::= { lbBridgePortEntry 20 }

		lbBridgePortReceiveUnicastFiltered OBJECT-TYPE
			SYNTAX	Counter
			ACCESS	read-only
			STATUS	mandatory
			DESCRIPTION
					"The number of frames discarded by this port due to user
					defined receive path filters."
			::= { lbBridgePortEntry 21 }

		lbBridgePortReceiveMulticastFiltered OBJECT-TYPE
			SYNTAX	Counter
			ACCESS	read-only
			STATUS	mandatory
			DESCRIPTION
					"The number of frames discarded by this port due to user
					defined receive multicast path filters."
			::= { lbBridgePortEntry 22 }

		lbBridgePortTransmitUnicastFiltered OBJECT-TYPE
			SYNTAX	Counter
			ACCESS	read-only
			STATUS	mandatory
			DESCRIPTION
					"The number of frames discarded by this port due to user
					defined transmit path filters."
			::= { lbBridgePortEntry 23 }

		lbBridgePortTransmitMulticastFiltered OBJECT-TYPE
			SYNTAX	Counter
			ACCESS	read-only
			STATUS	mandatory
			DESCRIPTION
					"The number of frames discarded by this port due to user
					defined transmit multicast path filters."
			::= { lbBridgePortEntry 24 }

		lbBridgePortReceiveMulticastLimitExceededCount OBJECT-TYPE
			SYNTAX	Counter
			ACCESS	read-only
			STATUS	mandatory
			DESCRIPTION
					"The number of times the lbBridgePortReceiveMulticastLimit was
					exceeded."
			::= { lbBridgePortEntry 25 }


		-- Bridge Port Forwarded-To Table

		lbBridgePortForwardedToTable OBJECT-TYPE
			SYNTAX  SEQUENCE OF LbBridgePortForwardedToEntry
			ACCESS  not-accessible
			STATUS  mandatory
			DESCRIPTION
					"A list of port forwarding count information."
			::= { lbBridge 3 }

		lbBridgePortForwardedToEntry OBJECT-TYPE
			SYNTAX  LbBridgePortForwardedToEntry
			ACCESS  not-accessible
			STATUS  mandatory
			DESCRIPTION
					"A bridge port forwarded-to entry contains information on the
					count of frames forwarded from the receiving port indicated
					by the corresponding lbBridgePortForwardedToReceivePortIndex,
					to the destination port indicated by the corresponding
					lbBridgePortForwardedToDstPortIndex.  Note that no entries
					exist which are indexed with the same values for both the
					lbBridgePortForwardedToReceivePortIndex and the
					lbBridgePortForwardedToDstPortIndex objects."
			INDEX	{ lbBridgePortForwardedToBridgeIndex,
					lbBridgePortForwardedToReceivePortIndex,
					lbBridgePortForwardedToDstPortIndex }
			::= { lbBridgePortForwardedToTable 1 }

		LbBridgePortForwardedToEntry ::=
			SEQUENCE {
				lbBridgePortForwardedToBridgeIndex
					INTEGER,
				lbBridgePortForwardedToReceivePortIndex
					INTEGER,
				lbBridgePortForwardedToDstPortIndex
					INTEGER,
				lbBridgePortForwardedToCount
					Counter
			}

		lbBridgePortForwardedToBridgeIndex OBJECT-TYPE
			SYNTAX	INTEGER
			ACCESS	read-only
			STATUS	mandatory
			DESCRIPTION
					"A unique value for each bridge function in the system.
					It's value ranges between 1 and the value of
					lbSystemBridgeFunctionCount."
			::= { lbBridgePortForwardedToEntry 1 }

		lbBridgePortForwardedToReceivePortIndex OBJECT-TYPE
			SYNTAX	INTEGER
			ACCESS	read-only
			STATUS	mandatory
			DESCRIPTION
					"A unique value for each bridge port controlled by a given
					bridge function.  It's value ranges between 1 and the 
					value of lbBridgePortCount for the bridge function
					which this entry references.  This port index refers to the
					receiving port which is forwarding frames."
			::= { lbBridgePortForwardedToEntry 2 }

		lbBridgePortForwardedToDstPortIndex OBJECT-TYPE
			SYNTAX	INTEGER
			ACCESS	read-only
			STATUS	mandatory
			DESCRIPTION
					"A unique value for each bridge port controlled by a given
					bridge function.  It's value ranges between 1 and the 
					value of lbBridgePortCount for the bridge function
					which this entry references.  This port index refers to
					the destination port to which frames are being forwarded."
			::= { lbBridgePortForwardedToEntry 3 }

		lbBridgePortForwardedToCount OBJECT-TYPE
			SYNTAX	Counter
			ACCESS	read-only
			STATUS	mandatory
			DESCRIPTION
					"The count of frames forwarded from the receiving port to
					the destination port."
			::= { lbBridgePortForwardedToEntry 4 }


		-- Bridge Port Filtered-To Table

		lbBridgePortFilteredToTable OBJECT-TYPE
			SYNTAX  SEQUENCE OF LbBridgePortFilteredToEntry
			ACCESS  not-accessible
			STATUS  mandatory
			DESCRIPTION
					"A list of port filtering count information."
			::= { lbBridge 4 }

		lbBridgePortFilteredToEntry OBJECT-TYPE
			SYNTAX  LbBridgePortFilteredToEntry
			ACCESS  not-accessible
			STATUS  mandatory
			DESCRIPTION
					"A bridge port filtered-to entry contains information on the
					count of frames filtered from the receiving port indicated
					by the corresponding lbBridgePortFilteredToReceivePortIndex,
					to the destination port indicated by the corresponding
					lbBridgePortFilteredToDstPortIndex.  Note that no entries
					exist which are indexed with the same values for both the
					lbBridgePortFilteredToReceivePortIndex and the
					lbBridgePortFilteredToDstPortIndex objects."
			INDEX	{ lbBridgePortFilteredToBridgeIndex,
					lbBridgePortFilteredToReceivePortIndex,
					lbBridgePortFilteredToDstPortIndex }
			::= { lbBridgePortFilteredToTable 1 }

		LbBridgePortFilteredToEntry ::=
			SEQUENCE {
				lbBridgePortFilteredToBridgeIndex
					INTEGER,
				lbBridgePortFilteredToReceivePortIndex
					INTEGER,
				lbBridgePortFilteredToDstPortIndex
					INTEGER,
				lbBridgePortFilteredToCount
					Counter
			}

		lbBridgePortFilteredToBridgeIndex OBJECT-TYPE
			SYNTAX	INTEGER
			ACCESS	read-only
			STATUS	mandatory
			DESCRIPTION
					"A unique value for each bridge function in the system.
					It's value ranges between 1 and the value of
					lbSystemBridgeFunctionCount."
			::= { lbBridgePortFilteredToEntry 1 }

		lbBridgePortFilteredToReceivePortIndex OBJECT-TYPE
			SYNTAX	INTEGER
			ACCESS	read-only
			STATUS	mandatory
			DESCRIPTION
					"A unique value for each bridge port controlled by a given
					bridge function.  It's value ranges between 1 and the 
					value of lbBridgePortCount for the bridge function
					which this entry references.  This port index refers to the
					receiving port which is filtering frames."
			::= { lbBridgePortFilteredToEntry 2 }

		lbBridgePortFilteredToDstPortIndex OBJECT-TYPE
			SYNTAX	INTEGER
			ACCESS	read-only
			STATUS	mandatory
			DESCRIPTION
					"A unique value for each bridge port controlled by a given
					bridge function.  It's value ranges between 1 and the 
					value of lbBridgePortCount for the bridge function
					which this entry references.  This port index refers to
					the destination port to which frames are being filtered."
			::= { lbBridgePortFilteredToEntry 3 }

		lbBridgePortFilteredToCount OBJECT-TYPE
			SYNTAX	Counter
			ACCESS	read-only
			STATUS	mandatory
			DESCRIPTION
					"The count of frames filtered from the receiving port to
					the destination port."
			::= { lbBridgePortFilteredToEntry 4 }


		-- Bridge Port AddressTable

		lbBridgePortAddressTable OBJECT-TYPE
			SYNTAX	SEQUENCE OF LbBridgePortAddressEntry
			ACCESS	not-accessible
			STATUS	mandatory
			DESCRIPTION
					"A list of bridge port address entries."
			::= { lbBridge 5 }

		lbBridgePortAddressEntry OBJECT-TYPE
			SYNTAX	LbBridgePortAddressEntry
			ACCESS	not-accessible
			STATUS	mandatory
			DESCRIPTION
					"An bridge port address entry contains information about
					particular bridge port address in a given system."
			INDEX	{ lbBridgePortAddressBridgeIndex, 
					lbBridgePortAddressPortIndex, 
					lbBridgePortAddressIndex }
			::= { lbBridgePortAddressTable 1 }

		LbBridgePortAddressEntry ::=
			SEQUENCE {
				lbBridgePortAddressBridgeIndex
					INTEGER,
				lbBridgePortAddressPortIndex
					INTEGER,
				lbBridgePortAddressIndex
					INTEGER,
				lbBridgePortAddressRemoteAddress
					OCTET STRING,
				lbBridgePortAddressType
					INTEGER,
				lbBridgePortAddressIsStatic
					INTEGER,
				lbBridgePortAddressStaticPort
					INTEGER,
				lbBridgePortAddressAge
					INTEGER
			}

		lbBridgePortAddressBridgeIndex OBJECT-TYPE
			SYNTAX	INTEGER
			ACCESS	read-only
			STATUS	mandatory
			DESCRIPTION
					"A unique value for each bridge function in the system.
					It's value ranges between 1 and the value of
					lbSystemBridgeFunctionCount."
			::= { lbBridgePortAddressEntry 1 }

		lbBridgePortAddressPortIndex OBJECT-TYPE
			SYNTAX	INTEGER
			ACCESS	read-only
			STATUS	mandatory
			DESCRIPTION
					"A unique value for each bridge port controlled by a given
					bridge function.  It's value ranges between 1 and the 
					value of lbBridgePortCount for the bridge function
					which this entry references."
			::= { lbBridgePortAddressEntry 2 }

		lbBridgePortAddressIndex OBJECT-TYPE
			SYNTAX	INTEGER
			ACCESS	read-only
			STATUS	mandatory
			DESCRIPTION
					"The index of this address entry within the bridge address 
					table." 
			::= { lbBridgePortAddressEntry 3 }

		lbBridgePortAddressRemoteAddress OBJECT-TYPE
			SYNTAX	OCTET STRING (SIZE (6))
			ACCESS	read-write
			STATUS	mandatory
			DESCRIPTION
					"The remote MAC address detected on the port corresponding
					to this entry.  Setting this object attempts to create a
					new entry in the table.  Since the value of 
					lbBridgePortAddressIndex is determined automatically internal
					to the bridge, a set is only successful if the index value
					specified for lbBridgePortAddressIndex is zero.  A get-next
					using the values of lbBridgePortAddressBridgeIndex and 
					lbBridgePortAddressPortIndex can be used to determine the
					address index assigned to the newly added address entry."
			::= { lbBridgePortAddressEntry 4 }

		lbBridgePortAddressType OBJECT-TYPE
			SYNTAX INTEGER {
						other(1),
						invalid(2)
					}
			ACCESS	read-write
			STATUS	mandatory
			DESCRIPTION
					"This object, when read, always returns the value other (1).
					Setting this object to invalid (2) will remove the 
					corresponding address entry from the table."
			::= { lbBridgePortAddressEntry 5 }

		lbBridgePortAddressIsStatic OBJECT-TYPE
			SYNTAX	INTEGER {
						isStatic(1),
						isDynamic(2)
					}
			ACCESS	read-write
			STATUS	mandatory
			DESCRIPTION
					"A value indicating whether this MAC address was statically 
					configured or was dynamically learned."
			::= { lbBridgePortAddressEntry 6 }

		lbBridgePortAddressStaticPort OBJECT-TYPE
			SYNTAX	INTEGER
			ACCESS	read-only
			STATUS	mandatory
			DESCRIPTION
					"If the object lbBridgePortAddressIsStatic has 
					value isStatic(1), this object indicates the local port
					index (as reported by lbBridgePortLocalIndex) for 
					which this MAC address was statically configured.  If
					the object lbBridgePortAddressIsStatic has the value
					isDynamic(2), the value of this object is 0."
			::= { lbBridgePortAddressEntry 7 }

		lbBridgePortAddressAge OBJECT-TYPE
			SYNTAX	INTEGER
			ACCESS	read-only
			STATUS	mandatory
			DESCRIPTION
					"This object indicates the time, in seconds, elapsed since 
					a packet containing this address as a source was last seen
					on the port corresponding to this entry."
			::= { lbBridgePortAddressEntry 8 }


		-- Trap Enterprise Table

		lbTrapEnterpriseTable OBJECT-TYPE
			SYNTAX	SEQUENCE OF LbTrapEnterpriseTableEntry
			ACCESS	not-accessible
			STATUS	mandatory
			DESCRIPTION
					"This table contains a listing of enterprises under which
					various traps are defined.  In all cases except for the 
					MIB-II generic traps, the enterprise under which a trap 
					is defined is the same as that appearing in the ENTERPRISE 
					portion of the trap.  Associated with each trap enterprise
					is a trap enterprise index."
			::= { lbTrapEnterprise 1 }

		lbTrapEnterpriseTableEntry OBJECT-TYPE
			SYNTAX	LbTrapEnterpriseTableEntry
			ACCESS	not-accessible
			STATUS	mandatory
			DESCRIPTION
					"Information relating a specific trap enterprise OID with
					a trap enterprise index."
			INDEX	{ lbTrapEnterpriseIndex }
			::= { lbTrapEnterpriseTable 1 }

		LbTrapEnterpriseTableEntry ::=
			SEQUENCE {
				lbTrapEnterpriseIndex
					INTEGER,
				lbTrapEnterpriseOID
					OBJECT IDENTIFIER
			}

		lbTrapEnterpriseIndex OBJECT-TYPE
			SYNTAX	INTEGER
			ACCESS	read-only
			STATUS	mandatory
			DESCRIPTION
					"A unique index corresponding to a particular enterprise
					OID under which traps are defined.  This value of this 
					object corresponding to a particular enterprise OID will
					remain constant accross system resets."
			::= { lbTrapEnterpriseTableEntry 1 }

		lbTrapEnterpriseOID OBJECT-TYPE
			SYNTAX	OBJECT IDENTIFIER
			ACCESS	read-only
			STATUS	mandatory
			DESCRIPTION
					"An enterpise OID under which traps are defined."
			::= { lbTrapEnterpriseTableEntry 2 }


		-- Trap Destination Table
					
		lbTrapDestTable OBJECT-TYPE
			SYNTAX	SEQUENCE OF LbTrapDestTableEntry
			ACCESS	not-accessible
			STATUS	mandatory
			DESCRIPTION
					"This table contains information specifying which traps
					will be transmitted by the LANplex to a given destination 
					address.  The table is indexed by the destination address, 
					the index of the enterprise which generates the trap, and
					the trap number.  Each entry in the table with a status 
					of valid identifies a trap which, when generated, will be 
					transmitted to the corresponding destination address 
					listed in that entry."
			::= { lbTrapDest 1 }

		lbTrapDestTableEntry OBJECT-TYPE
			SYNTAX	LbTrapDestTableEntry
			ACCESS	not-accessible
			STATUS	mandatory
			DESCRIPTION
					"Information relating a trap with a destination address
					to which the trap will be sent when it is generated."
			INDEX { lbTrapDestAddr, 
					lbTrapDestEnterpriseIndex, 
					lbTrapNumber }
			::= { lbTrapDestTable 1 }

		LbTrapDestTableEntry ::=
			SEQUENCE {
				lbTrapDestAddr
					NetworkAddress,
				lbTrapDestEnterpriseIndex
					INTEGER,
				lbTrapNumber
					INTEGER,
				lbTrapEntryStatus
					INTEGER
			}

		lbTrapDestAddr OBJECT-TYPE
			SYNTAX	NetworkAddress
			ACCESS	read-only
			STATUS	mandatory
			DESCRIPTION
					"The network address to which the trap identified by
					this entry is to be transmitted."
			::= { lbTrapDestTableEntry 1 }

		lbTrapDestEnterpriseIndex OBJECT-TYPE
			SYNTAX	INTEGER
			ACCESS	read-only
			STATUS	mandatory
			DESCRIPTION
					"The enterprise index of the enterprise identified in this
					entry.  The value of this object is the same as the
					lbTrapEnterpriseIndex value for a given enterprise."
			::= { lbTrapDestTableEntry 2 }

		lbTrapNumber OBJECT-TYPE
			SYNTAX	INTEGER
			ACCESS	read-only
			STATUS	mandatory
			DESCRIPTION
					"The number of the trap within the corresponding
					enterprise for this entry."
			::= { lbTrapDestTableEntry 3 }

		lbTrapEntryStatus OBJECT-TYPE
			SYNTAX	INTEGER {
						valid(1),
						invalid(2)
					}
			ACCESS	read-write
			STATUS	mandatory
			DESCRIPTION
					"The status of the trap destination table entry.  Setting
					this object to valid has the effect of attempting to add
					the row corresponding to the instance specified.  If the
					instance already exists, the set is successful (with no
					new entry added).  If the instance specified is invalid,
					the set fails, otherwise the set succeeds and results in
					a new entry being added to the table.  Setting this object
					to invalid has the effect of removing the corresponding 
					entry from the table."
			::= { lbTrapDestTableEntry 4 }


        -- lb3gh MIB traps

		lbSlotInsertEvent TRAP-TYPE
			ENTERPRISE	lb3ghMib
			VARIABLES	{ lbSlotIndex, lbSlotBoardType, lbSlotBoardRevision }
			DESCRIPTION
					"The SNMP trap that is generated when a 
					board is inserted into a particular 
					slot in the chassis."
			::= 1

		lbSlotExtractEvent TRAP-TYPE
			ENTERPRISE	lb3ghMib
			VARIABLES	{ lbSlotIndex }
			DESCRIPTION
					"The SNMP trap that is generated when a 
					board is extracted from a particular 
					slot in the chassis."
			::= 2

		lbBridgeAddressThresholdEvent TRAP-TYPE
			ENTERPRISE	lb3ghMib
			VARIABLES	{ lbBridgeIndex,
						lbBridgeBaseSlotIndex }
			DESCRIPTION
					"The SNMP trap that is generated when the number of
					addresses stored in the bridge reaches 
					lbBridgeAddressThreshold."
			::= 3

		-- The lbBridgePortAddressLearnedEvent and the lbBridgePortAddressForgottenEvent
		-- traps are obsolete and are no longer supported.

		lbSystemOverTemperatureEvent TRAP-TYPE
			ENTERPRISE	lb3ghMib
			DESCRIPTION
					"The SNMP trap that is generated when the system 
					temperature exceeds a certain threshold."
			::= 6

		lbSlotOverTemperatureEvent TRAP-TYPE
			ENTERPRISE	lb3ghMib
			VARIABLES	{ lbSlotIndex,
						lbSlotBoardType,
						lbSlotBoardRevision,
						lbSlotBoardStatus }
			DESCRIPTION
					"The SNMP trap that is generated when the temperature of
					a board in a particular slot exceeds a certain threshold."
			::= 7

		lbPowerSupplyFailureEvent TRAP-TYPE
			ENTERPRISE	lb3ghMib
			VARIABLES	{ lbPowerSupplyIndex,
						lbPowerSupplyLocation,
						lbPowerSupplyLastFailure,
						lbSystemPowerSupplyCount}
			DESCRIPTION
					"The SNMP trap that is generated when a power supply
					unit fails in the system."
			::= 8


		END
