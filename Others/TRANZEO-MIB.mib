-- Title:  TRANZEO  Private MIB
--          This Private MIB supports Tranzeo Sixth Generation product line.
--	Tranzeo Wireless Technologies Inc.
--	19473 Fraser Way
--	Pitt Meadows, BC
--	Canada V3Y 2V4
--	
--
--
-- Version:    0.6
-- Date:       Wednesday July 21 2010
-- Comments:   This is the first private MIB created for Tranzeo.  It will contain basic oid's not already included in MIB-II or 802.11 MIB.
--    iso(1).org(3).dod(6).internet(1).private(4).enterprises(24575).


-- Version  Date  Authors Decription
--
-- v0.1    Nov 28    MR, QA Technician
--          2006
-- v0.2    Dec 27
--		2006	   MR, QA Technician
-- v0.3    May 1
--		2007	   MR, QA Technician. With thanks to Richard E. Brown @ Dartware.com
-- v0.4    Jul 12, 2007  PX, R&D  Add probe reset control
-- v0.5    Feb 6, 2009  MR, QA  Add autoconfig reset
-- v0.6    Jul 21, 2010  MR, QA  Add AP Station List


TRANZEO-MIB DEFINITIONS ::= BEGIN

IMPORTS


     enterprises, OBJECT-TYPE, NetworkAddress
            FROM RFC1155-SMI;

PhysAddress ::= OCTET STRING
              
tranzeo           OBJECT IDENTIFIER ::= { enterprises 24575 }
signal           	OBJECT IDENTIFIER ::= { tranzeo 1 }
probeConfig	      OBJECT IDENTIFIER ::= { tranzeo 2 }

stationStat				OBJECT IDENTIFIER ::= { tranzeo 3 }
assocStation      OBJECT IDENTIFIER ::= { tranzeo 4 }


-- RSSI objects - min, max, and average signal strength (in dBm)

rssi OBJECT IDENTIFIER ::= { signal 1 }

signallow OBJECT-TYPE
   SYNTAX INTEGER (-110..0)
   ACCESS read-only
   STATUS mandatory
   DESCRIPTION
       "This object represents the lowest received signal strength on the current channel in dBm. A 0 means no wireless connection."
   ::= { rssi 1 }

signalaverage OBJECT-TYPE
   SYNTAX INTEGER (-110..0)
   ACCESS read-only
   STATUS mandatory
   DESCRIPTION
       "This object represents the average received signal strength on the current channel in dBm. A 0 means no wireless connection."
   ::= { rssi 2 }

signalhigh OBJECT-TYPE
   SYNTAX INTEGER (-110..0)
   ACCESS read-only
   STATUS mandatory
   DESCRIPTION
       "This object represents the highest received signal strength on the current channel in dBm. A 0 means no wireless connection."
   ::= { rssi 3 }
   
-- Noise objects - min, max, and average noise (in dBm)
noise OBJECT IDENTIFIER ::= { signal 2 }

noiselow OBJECT-TYPE
   SYNTAX INTEGER (-110..0)
   ACCESS read-only
   STATUS mandatory
   DESCRIPTION
       "This object represents the lowest noise on the current channel in dBm. A 0 means no wireless connection."
   ::= { noise 1 }

noiseaverage OBJECT-TYPE
   SYNTAX INTEGER (-110..0)
   ACCESS read-only
   STATUS mandatory
   DESCRIPTION
       "This object represents the average noise on the current channel in dBm. A 0 means no wireless connection."
   ::= { noise 2 }

noisehigh OBJECT-TYPE
   SYNTAX INTEGER (-110..0)
   ACCESS read-only
   STATUS mandatory
   DESCRIPTION
       "This object represents the highest noise on the current channel in dBm. A 0 means no wireless connection."
   ::= { noise 3 }

probeResetControl OBJECT-TYPE
    SYNTAX INTEGER {
               running(1),
               warmBoot(2),
               coldBoot(3),
			   autoconfig(4)
           }
    ACCESS read-write
    STATUS mandatory
    DESCRIPTION
        "Setting this object to warmBoot(2) causes the device to
        restart the application software with current configuration
        parameters saved in non-volatile memory.  Setting this
        object to coldBoot(3) causes the device to reinitialize
        configuration parameters in non-volatile memory to default
        values and restart the application software.  When the device
        is running normally, this variable has a value of
        running(1). Setting this object to autoconfig(4) causes the device to
        reboot and download the configuration using TFTP."
    ::= { probeConfig 1 }

stnNumber OBJECT-TYPE
   SYNTAX INTEGER (0..128)
   ACCESS read-only
   STATUS mandatory
   DESCRIPTION
       "This object represents the number of stations that associates to this AP."
   ::= { stationStat 1 }

stnIpAddr OBJECT-TYPE
   SYNTAX NetworkAddress
   ACCESS read-only
   STATUS mandatory
   DESCRIPTION
       "This object represents the ip address of associated STN to this AP."
   ::= { assocStation 1 }

stnMacAddr OBJECT-TYPE
   SYNTAX PhysAddress
   ACCESS read-only
   STATUS deprecated
   DESCRIPTION
       "This object represents the MAC address of associated STN to this AP."
   ::= { assocStation 2 }

END
