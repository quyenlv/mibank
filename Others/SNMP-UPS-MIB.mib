SNMP-UPS-MIB DEFINITIONS ::= BEGIN

          IMPORTS
              experimental, Counter, TimeTicks
                                                  FROM RFC1155-SMI
              OBJECT-TYPE                         FROM RFC-1212;

mgmt             OBJECT IDENTIFIER ::= { iso org(3) dod(6) internet(1) mgmt(2) }
mib-2            OBJECT IDENTIFIER ::= { mgmt 1 }       
directory        OBJECT IDENTIFIER ::= { internet 1 }
experimental     OBJECT IDENTIFIER ::= { internet 3 }
private          OBJECT IDENTIFIER ::= { internet 4 }
enterprises      OBJECT IDENTIFIER ::= { private 1 }

          univPowerSupply OBJECT IDENTIFIER ::= { experimental 9999 }  -- TBD

          -- groups in the UPS MIB module

          ident   OBJECT IDENTIFIER ::= { univPowerSupply 1 }

          battery OBJECT IDENTIFIER ::= { univPowerSupply 2 }

          input   OBJECT IDENTIFIER ::= { univPowerSupply 3 }

          output  OBJECT IDENTIFIER ::= { univPowerSupply 4 }

          bypass  OBJECT IDENTIFIER ::= { univPowerSupply 5 }

          status  OBJECT IDENTIFIER ::= { univPowerSupply 6 }

          alarm   OBJECT IDENTIFIER ::= { univPowerSupply 7 }

          test    OBJECT IDENTIFIER ::= { univPowerSupply 8 }

          schedule OBJECT IDENTIFIER ::= { univPowerSupply 9 }

          config  OBJECT IDENTIFIER ::= { univPowerSupply 10 }



          --
          -- The Device Identification group.
          --      All objects in this group are set at device initialization
          --      and remain static.
          --


          identDescr OBJECT-TYPE
              SYNTAX OCTET STRING (SIZE (255))
              ACCESS read-only
              STATUS mandatory
              DESCRIPTION
                      "The UPS description. This should include the
                      vendor name, model number and software revision."
                          ::= { ident 1 }

                      identSpecific OBJECT-TYPE
                          SYNTAX OBJECT IDENTIFIER
                          ACCESS read-only
                          STATUS mandatory
                          DESCRIPTION
                                  "A reference to MIB definitions
                                  specific to the particular UPS being
                                  managed. If this information is not
                                  present, its value should be set to
                                  the OBJECT IDENTIFIER { 0 0 }, which
                                  is a syntactically valid object
                                  identifier, and any conformant
                                  implementation of ASN.1 and BER must
                                  be able to generate and recognize this
                                  value."
                         ::= { ident 2 }


                     --
                     -- The Battery group.
                     --


                     batTimeRemaining OBJECT-TYPE
                         SYNTAX INTEGER (0..65535)
                         ACCESS read-only
                         STATUS mandatory
                         DESCRIPTION
                                 "The estimated time to battery charge
                                 depletion. (Unit of measure: Minute)"
                        ::= { battery 1 }

                    batTemperature OBJECT-TYPE
                        SYNTAX INTEGER (-32768..32767)
                        ACCESS read-only
                        STATUS mandatory
                        DESCRIPTION
                                "The battery temperature. (Unit of
                                measure: Degree, Centigrade)"
                       ::= { battery 2 }

                   batVoltage OBJECT-TYPE
                       SYNTAX INTEGER (-32768..32767)
                       ACCESS read-only
                       STATUS mandatory
                       DESCRIPTION
                               "The current battery voltage. (Unit of
                               measure: volt)"
                      ::= { battery 3 }

                  batChargeCurrent OBJECT-TYPE
                      SYNTAX INTEGER (-32768..32767)
                      ACCESS read-only
                      STATUS mandatory
                      DESCRIPTION
                              "The current battery charging current.
                              (Unit of measure: Amp/10)"
                     ::= { battery 4 }

                 batDischargeCurrent OBJECT-TYPE
                     SYNTAX INTEGER (-32768..32767)
                     ACCESS read-only
                     STATUS mandatory
                     DESCRIPTION
                             "The current battery discharging current.
                             (Unit of measure: Amp/10)"
                    ::= { battery 5 }

                batCapacity OBJECT-TYPE
                    SYNTAX INTEGER (0..100)
                    ACCESS read-only
                    STATUS mandatory
                    DESCRIPTION
                            "The current battery capacity in percentage
                            of total available."
                   ::= { battery 6 }


               --
               -- The Input group.
               --


               inputFrequency OBJECT-TYPE
                   SYNTAX INTEGER (-2147483647..2147483647)
                   ACCESS read-only
                   STATUS mandatory
                   DESCRIPTION
                           "The current input frequency. (Unit of
                           measure: mHz)"
                  ::= { input 1 }

              inputBrownOuts OBJECT-TYPE
                  SYNTAX Counter
                  ACCESS read-only
                  STATUS mandatory
                  DESCRIPTION
                          "The number of brown-out conditions since the
                          agent started."
                 ::= { input 2 }

             inputBlackOuts OBJECT-TYPE
                 SYNTAX Counter
                 ACCESS read-only
                 STATUS mandatory
                 DESCRIPTION
                         "The number of black-out conditions since the
                         agent started."
                ::= { input 3 }

            inputTransients OBJECT-TYPE
                SYNTAX Counter
                ACCESS read-only
                STATUS mandatory
                DESCRIPTION
                        "The number of transient (sag and surge)
                        conditions since the agent started."
               ::= { input 4 }

           inputNumPhases OBJECT-TYPE
               SYNTAX INTEGER { one(1), three(3) }
               ACCESS read-only
               STATUS mandatory
               DESCRIPTION
                       "The number of input phases utilized in this
                       device. This entry indicates the number of rows
                       in the input table."
              ::= { input 5 }

          inputTable OBJECT-TYPE
              SYNTAX SEQUENCE OF InputEntry
              ACCESS not-accessible
              STATUS mandatory
              ::= { input 6 }

          inputEntry OBJECT-TYPE
              SYNTAX InputEntry
              ACCESS not-accessible
              STATUS mandatory
              ::= { inputTable 1 }

          InputEntry ::= SEQUENCE {
              inputPhase                  INTEGER,
              inputVoltage                INTEGER,
              inputCurrent                INTEGER,
              inputVA                     INTEGER,
              inputWatts                  INTEGER
          }

          inputPhase OBJECT-TYPE
              SYNTAX INTEGER (1..3)
              ACCESS read-only
              STATUS mandatory
              DESCRIPTION
                      "The input phase."
              ::= { inputEntry 1 }

          inputVoltage OBJECT-TYPE
              SYNTAX INTEGER (-32768..32767)
              ACCESS read-only
              STATUS mandatory
              DESCRIPTION
                      "The input voltage. (Unit of measure: Volt)"
              ::= { inputEntry 2 }

          inputCurrent OBJECT-TYPE
              SYNTAX INTEGER (-32768..32767)
              ACCESS read-only
              STATUS mandatory
              DESCRIPTION
                      "The input current. (Unit of measure: Amp/10)"
              ::= { inputEntry 3 }

          inputVA OBJECT-TYPE
              SYNTAX INTEGER (-32768..32767)
              ACCESS read-only
              STATUS mandatory
              DESCRIPTION
                      "The input volt-amps."
              ::= { inputEntry 4 }

          inputWatts OBJECT-TYPE
              SYNTAX INTEGER (-32768..32767)
              ACCESS read-only
              STATUS mandatory
              DESCRIPTION
                      "The input power. (Unit of measure: Watt)"
              ::= { inputEntry 5 }


          --
          -- The Output group.
          --


          outputFrequency OBJECT-TYPE
              SYNTAX INTEGER (-2147483647..2147483647)
              ACCESS read-only
              STATUS mandatory
              DESCRIPTION
                      "Measured in mHz."
              ::= { output 1 }

          outputInverterTemp OBJECT-TYPE
              SYNTAX INTEGER (-32768..32767)
              ACCESS read-only
              STATUS mandatory
              DESCRIPTION
                      "The temperature of the inverter. (Unit of
                      measure: degree, Centigrade)"
              ::= { output 2 }

          outputControllerTemp OBJECT-TYPE
              SYNTAX INTEGER (-32768..32767)
              ACCESS read-only
              STATUS mandatory
              DESCRIPTION
                      "The temperature of the controller. (Unit of
                      measure: degree, Centigrade)"
              ::= { output 3 }

          outputNumPhases OBJECT-TYPE
              SYNTAX INTEGER { one(1), two(2), three(3) }
              ACCESS read-only
              STATUS mandatory
              DESCRIPTION
                      "The number of output phases utilized in this
                      device. This entry indicates the number of rows in
                      the output table."
              ::= { output 4 }

          outputTable OBJECT-TYPE
              SYNTAX SEQUENCE OF OutputEntry
              ACCESS not-accessible
              STATUS mandatory
              ::= { output 5 }

          outputEntry OBJECT-TYPE
              SYNTAX OutputEntry
              ACCESS not-accessible
              STATUS mandatory
              ::= { outputTable 1 }

          OutputEntry ::= SEQUENCE {
              outputPhase                  INTEGER,
              outputVoltage                INTEGER,
              outputCurrent                INTEGER,
              outputVA                     INTEGER,
              outputWatts                  INTEGER
          }

          outputPhase OBJECT-TYPE
              SYNTAX INTEGER (1..3)
              ACCESS read-only
              STATUS mandatory
              DESCRIPTION
                      "The output phase."
              ::= { outputEntry 1 }

          outputVoltage OBJECT-TYPE
              SYNTAX INTEGER (-2147483647..2147483647)
              ACCESS read-only
              STATUS mandatory
              DESCRIPTION
                      "The output voltage. (Unit of measure: Volt)"
              ::= { outputEntry 2 }

          outputCurrent OBJECT-TYPE
              SYNTAX INTEGER (-2147483647..2147483647)
              ACCESS read-only
              STATUS mandatory
              DESCRIPTION
                      "The output current. (Unit of measure: Amp/10)"
              ::= { outputEntry 3 }

          outputVA OBJECT-TYPE
              SYNTAX INTEGER (-32768..32767)
              ACCESS read-only
              STATUS mandatory
              DESCRIPTION
                      "The output volt-amps."
              ::= { outputEntry 4 }

          outputWatts OBJECT-TYPE
              SYNTAX INTEGER (-32768..32767)
              ACCESS read-only
              STATUS mandatory
              DESCRIPTION
                      "The output power. (Unit of measure: Watt)"
              ::= { outputEntry 5 }


          --
          -- The Bypass group.
          --


          bypassFrequency OBJECT-TYPE
              SYNTAX INTEGER (-2147483647..2147483647)
              ACCESS read-only
              STATUS mandatory
              DESCRIPTION
                      "The bypass frequency. (Unit of measure: mHz)"
              ::= { bypass 1 }

          bypassNumPhases OBJECT-TYPE
              SYNTAX INTEGER { one(1), three(3) }
              ACCESS read-only
              STATUS mandatory
              DESCRIPTION
                      "The number of bypass phases utilized in this
                      device. This entry indicates the number of rows in
                      the input table."
              ::= { bypass 2 }

          bypassTable OBJECT-TYPE
              SYNTAX SEQUENCE OF BypassEntry
              ACCESS not-accessible
              STATUS mandatory
              ::= { bypass 3 }

          bypassEntry OBJECT-TYPE
              SYNTAX BypassEntry
              ACCESS not-accessible
              STATUS mandatory
              ::= { bypassTable 1 }

          BypassEntry ::= SEQUENCE {
              bypassPhase                 INTEGER,
              bypassVoltage               INTEGER,
              bypassCurrent               INTEGER
          }

          bypassPhase OBJECT-TYPE
              SYNTAX INTEGER (1..3)
              ACCESS read-only
              STATUS mandatory
              DESCRIPTION
                      "The bypass phase."
              ::= { bypassEntry 1 }

          bypassVoltage OBJECT-TYPE
              SYNTAX INTEGER (-32768..32767)
              ACCESS read-only
              STATUS mandatory
              DESCRIPTION
                      "The bypass voltage. (Unit of measure: Volt)"
              ::= { bypassEntry 2 }

          bypassCurrent OBJECT-TYPE
              SYNTAX INTEGER (-32768..32767)
              ACCESS read-only
              STATUS mandatory
              DESCRIPTION
                      "The bypass current. (Unit of measure: Amp/10)"
              ::= { bypassEntry 3 }


          --
          -- The Status group.
          --     This group provides a summary of non-critical problems.
          --


          statSummary OBJECT-TYPE
              SYNTAX INTEGER {
                  onLine(1),
                  onBypass(2),
                  replaceBatteries(4)
              }
              ACCESS read-only
              STATUS mandatory
              DESCRIPTION
                      "A summary of non-critical conditions. Each of the
                      enumerated values are added to compute the value
                      of this object."
              ::= { status 1 }


          --
          -- The Alarm group.
          --     This group provides a summary of non-critical problems.
          --


          alarmSummary OBJECT-TYPE
              SYNTAX INTEGER {
                  batteryBad(1),
                  onBattery(2),
                  lowBattery(4),
                  batteryTempBad(8),

                  inputBad(16),
                  inputFreqError(32),

                  outputBad(64),
                  outputOverload(128),
                  inverterTempBad(256),
                  controllerTempBad(512),

                  onBypass(1024),
                  bypassBad(2048),

                  unixStopIssued(4096),
                  chargerFailed(8192),
                  upsOff(16384)
              }
              ACCESS read-only
              STATUS mandatory
              DESCRIPTION
                      "A summary of critical conditions. Each of the
                      enumerated values are added to compute the value
                      of this object."
              ::= { alarm 1 }


          --
          -- The Test group
          --      testXYZ        - Initiates test of the XYZ function.
          --      testXYZStatus  - An enumerated value indicating test results
          --


          testBattery OBJECT-TYPE
              SYNTAX INTEGER { start(1), abort(2) }
              ACCESS read-write
              STATUS mandatory
              DESCRIPTION
                      "Setting this variable to 'start' will initiate
                      the battery test. Setting this variable to 'abort'
                      will stop the battery test if the test is in-
                      progress, otherwise it has no effect. Reading this
                      variable will return zero. If 'testBatteryStatus'
                      is remain in the failure state."
              ::= { test 1 }

          testBatteryStatus OBJECT-TYPE
              SYNTAX  INTEGER {
                  unknown(1),
                  passed(2),
                  failed(3),
                  inProgress(4),
                  sysFailure(5),
                  notSupported(6)
              }
              ACCESS read-only
              STATUS mandatory
              DESCRIPTION
                      "The status of the battery test."
              ::= { test 2 }


          testDiag OBJECT-TYPE
              SYNTAX INTEGER { start(1), abort(2) }
              ACCESS read-write
              STATUS mandatory
              DESCRIPTION
                      "Setting this variable to 'start' will initiate
                      the diagnostics test. Setting this variable to
                      'abort' will stop the diagnostics test if the test
                      is in-progress, otherwise it has no effect.
                      Reading this variable will return zero."
              ::= { test 3 }

          testDiagStatus OBJECT-TYPE
              SYNTAX  INTEGER {
                  unknown(1),
                  passed(2),
                  failed(3),
                  inProgress(4),
                  sysFailure(5),
                  notSupported(6)
              }
              ACCESS read-only
              STATUS mandatory
              DESCRIPTION
                      "The status of the diagnostics test."
              ::= { test 4 }


          testIndicators OBJECT-TYPE
              SYNTAX INTEGER { start(1), abort(2) }
              ACCESS read-write
              STATUS mandatory
              DESCRIPTION
                      "Setting this variable to 'start' will initiate
                      the indicators test. Setting this variable to
                      'abort' will stop the indicators test if the test
                      is in-progress, otherwise it has no effect.
                      Reading this variable will return zero."
              ::= { test 5 }

          testIndicatorsStatus OBJECT-TYPE
              SYNTAX  INTEGER {
                  unknown(1),
                  passed(2),
                  failed(3),
                  inProgress(4),
                  sysFailure(5),
                  notSupported(6)
              }
              ACCESS read-only
              STATUS mandatory
              DESCRIPTION
                      "The status of the indicators test. Note: this
                      test requires
                       physical verification to be useful."
              ::= { test 6 }



          --
          -- The Schedule group.
          --


          schedOutputOffDelay OBJECT-TYPE
              SYNTAX TimeTicks
              ACCESS read-write
              STATUS mandatory
              DESCRIPTION
                      "Setting this object will stop the output after
                      the indicated number of TimeTicks. Setting this
                      object to -1 will abort any shutdown sequence. The
                      output will restart in the number of TimeTicks
                      indicated by 'schedOutputOnDelay' unless it is
                      equal to -1. In the later case, the output will
                      remain inactive. This object will be set to -1
                      when the device is initialized on power-up or
                      restart."
              ::= { schedule 1 }

          schedOutputOnDelay OBJECT-TYPE
              SYNTAX TimeTicks
              ACCESS read-write
              STATUS mandatory
              DESCRIPTION
                      "The length of time to delay before coming on-
                      line. If this value is -1 the output will remain
                      off.  This object will be set to -1 when the
                      device is initialized on power-up or restart."
              ::= { schedule 2 }

          schedSystemShutdown OBJECT-TYPE
              SYNTAX INTEGER { true(1), false(2) }
              ACCESS read-write
              STATUS mandatory
              DESCRIPTION
                      "Setting this object to 'true' will shutdown the
                      device."
              ::= { schedule 3 }

          schedUnixShutdown OBJECT-TYPE
              SYNTAX INTEGER { true(1), false(2) }
              ACCESS read-write
              STATUS mandatory
              DESCRIPTION
                      "Setting this device to 'true' will cause unix
                      shutdown traps to be issued at a system-dependent
                      rate, or until this object is set to false."
              ::= { schedule 4 }

          --
          -- The Configuration group.
          --


          configOutputVoltage OBJECT-TYPE
              SYNTAX INTEGER (-32768..32767)
              ACCESS read-only
              STATUS mandatory
              DESCRIPTION
                      "The nominal output voltage. (Unit of measure:
                      volt)"
              ::= { config 1 }

          configInputVoltage OBJECT-TYPE
              SYNTAX INTEGER (-32768..32767)
              ACCESS read-only
              STATUS mandatory
              DESCRIPTION
                      "The nominal input voltage. (Unit of measure:
                      volt)"
              ::= { config 2 }

          configOutputFreq OBJECT-TYPE
              SYNTAX INTEGER (-2147483647..2147483647)
              ACCESS read-only
              STATUS mandatory
              DESCRIPTION
                      "The nominal output frequency. (Unit of measure:
                      mHz)"
              ::= { config 3 }

          configInputFreq OBJECT-TYPE
              SYNTAX INTEGER (-2147483647..2147483647)
              ACCESS read-only
              STATUS mandatory
              DESCRIPTION
                      "The nominal input frequency. (Unit of measure:
                      mHz)"
              ::= { config 4 }

          configNominalBatTime OBJECT-TYPE
              SYNTAX INTEGER (-32768..32767)
              ACCESS read-only
              STATUS mandatory
              DESCRIPTION
                      "The nominal battery time. (Unit of measure:
                      minute)"
              ::= { config 5 }

          configAudioStatus OBJECT-TYPE
              SYNTAX INTEGER { on(1),off(2), squelch(3) }
              ACCESS read-write
              STATUS mandatory
              DESCRIPTION
                      "The status of the audio alarm. 'Off' indicates
                      the alarm will not sound, while the 'squelch'
                      value indicates the alarm has sounded and
                      squelched. A squelched audio status will return to
                      the previous state ('on' or 'off') when the alarm
                      stops sounding."
              ::= { config 6 }

          configAutoRestart OBJECT-TYPE
              SYNTAX INTEGER { on(1), off(2) }
              ACCESS read-write
              STATUS mandatory
              DESCRIPTION
                      "Setting this object to 'on' will cause the device
                      to restart after a shutdown."
              ::= { config 7 }

          END
