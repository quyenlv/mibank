-- $Header:   K:/WanSuite/archives/include/pvcs/router.mib,v   1.0   13 Jun 2000 14:50:40   richardm  $

IPAD-ROUTER-MIB DEFINITIONS ::= BEGIN

IMPORTS enterprises, 
        IpAddress              FROM RFC1155-SMI
        OBJECT-TYPE            FROM RFC-1212
        DisplayString          FROM RFC1213-MIB;

verilink    OBJECT IDENTIFIER ::= { enterprises 321 }
hbu         OBJECT IDENTIFIER ::= { verilink 100 }
ipad        OBJECT IDENTIFIER ::= { hbu 1 }

-- IPAD sections, listed for historical accuracy

ipadFrPort      OBJECT IDENTIFIER ::= { ipad 1 }
ipadService     OBJECT IDENTIFIER ::= { ipad 2 }
ipadChannel     OBJECT IDENTIFIER ::= { ipad 3 }
ipadDLCI        OBJECT IDENTIFIER ::= { ipad 4 }
ipadEndpoint    OBJECT IDENTIFIER ::= { ipad 5 }
ipadUser        OBJECT IDENTIFIER ::= { ipad 6 }
ipadPPP         OBJECT IDENTIFIER ::= { ipad 7 }
ipadModem       OBJECT IDENTIFIER ::= { ipad 8 }
ipadSvcAware    OBJECT IDENTIFIER ::= { ipad 9 }
ipadPktSwitch   OBJECT IDENTIFIER ::= { ipad 10 }
ipadTrapDest    OBJECT IDENTIFIER ::= { ipad 11 }
ipadMisc        OBJECT IDENTIFIER ::= { ipad 12 }

-- This MIB is located on this branch...

ipadRouter        OBJECT IDENTIFIER ::= { ipad 13 }
ipadCircuitParms  OBJECT IDENTIFIER ::= { ipadRouter 1 }
ipadRIPParms      OBJECT IDENTIFIER ::= { ipadRouter 2 }

-- Circuit parameters

ipadCircuitTable OBJECT-TYPE
    SYNTAX    SEQUENCE OF IpadCircuitTableEntry
    ACCESS    not-accessible
    STATUS    optional
    DESCRIPTION
        "Table of Circuit parameters."
    ::= { ipadCircuitParms 1 }

ipadCircuitTableEntry OBJECT-TYPE
    SYNTAX  IpadCircuitTableEntry
    ACCESS  not-accessible
    STATUS  mandatory
    DESCRIPTION
        "An entry in the ipad Circuit parameter table."
    INDEX   { ipadCircuitIndex }
    ::= { ipadCircuitTable 1 }

IpadCircuitTableEntry ::=
    SEQUENCE
    {
    ipadCircuitIndex                  INTEGER,
    ipadCircuitEndpoint               DisplayString,
    ipadCircuitIpAddress              IpAddress,
    ipadCircuitIpMask                 IpAddress,
    ipadCircuitMaxTransmitUnit        INTEGER,
    ipadCircuitCost                   INTEGER,
    ipadCircuitEnableRIP              INTEGER,
    ipadCircuitEnableOSPF             INTEGER,
    ipadCircuitEnableMulticast        INTEGER
    }

ipadCircuitIndex       OBJECT-TYPE
    SYNTAX  INTEGER
    ACCESS  read-only
    STATUS  mandatory
    DESCRIPTION
        "The index into the Circuit table."
    ::= { ipadCircuitTableEntry 1 }

ipadCircuitEndpoint    OBJECT-TYPE
    SYNTAX  DisplayString
    ACCESS  read-write
    STATUS  mandatory
    DESCRIPTION
        "An entry in the endpoint table."
    ::= { ipadCircuitTableEntry 2 }

ipadCircuitIpAddress    OBJECT-TYPE
    SYNTAX  IpAddress
    ACCESS  read-write
    STATUS  mandatory
    DESCRIPTION
        "The IP Address of the Circuit."
    ::= { ipadCircuitTableEntry 3 }

ipadCircuitIpMask    OBJECT-TYPE
    SYNTAX  IpAddress
    ACCESS  read-write
    STATUS  mandatory
    DESCRIPTION
        "The IP Mask of this Circuit IP address."
    ::= { ipadCircuitTableEntry 4 }

ipadCircuitMaxTransmitUnit    OBJECT-TYPE
    SYNTAX  INTEGER(0..65535)
    ACCESS  read-write
    STATUS  mandatory
    DESCRIPTION
        "The Maximum packet size carried by this Circuit."
    ::= { ipadCircuitTableEntry 5 }

ipadCircuitCost    OBJECT-TYPE
    SYNTAX  INTEGER(0..65535)
    ACCESS  read-write
    STATUS  mandatory
    DESCRIPTION
        "The cost (delay) of this Circuit."
    ::= { ipadCircuitTableEntry 6 }

ipadCircuitEnableRIP    OBJECT-TYPE
    SYNTAX  INTEGER
            {
            disabled(1),
            enabled(2)
            }
    ACCESS  read-write
    STATUS  mandatory
    DESCRIPTION
        "To enable or disable RIP for this Circuit."
    ::= { ipadCircuitTableEntry 7 }

ipadCircuitEnableOSPF    OBJECT-TYPE
    SYNTAX  INTEGER
            {
            disabled(1),
            enabled(2)
            }
    ACCESS  read-write
    STATUS  mandatory
    DESCRIPTION
        "To enable or disable OSPF for this Circuit."
    ::= { ipadCircuitTableEntry 8 }

ipadCircuitEnableMulticast    OBJECT-TYPE
    SYNTAX  INTEGER
            {
            disabled(1),
            enabled(2)
            }
    ACCESS  read-write
    STATUS  mandatory
    DESCRIPTION
        "To allow multicast adressing for this Circuit."
    ::= { ipadCircuitTableEntry 9 }

ipadCircuitAdd    OBJECT-TYPE
    SYNTAX  INTEGER
            {
            other(1),
            addnew(2)
            }
    ACCESS  read-write
    STATUS  mandatory
    DESCRIPTION
        "Writing addnew(2) to this field causes a new (blank) 
        route to be appended to the Circuit Table."
    ::= { ipadCircuitParms 2 }

ipadCircuitDelete    OBJECT-TYPE
    SYNTAX  INTEGER
    ACCESS  read-write
    STATUS  mandatory
    DESCRIPTION
        "Writing the index of an entry in the Circuit table
        causes that entry to be deleted."
    ::= { ipadCircuitParms 3 }

-- RIP general parameters

ipadRIPEnable OBJECT-TYPE
    SYNTAX  INTEGER
            {
            disabled(1),
            enabled(2)
            }
    ACCESS  read-write
    STATUS  mandatory
    DESCRIPTION
        "Determines if RIP routing is enabled."
    ::= { ipadRIPParms 1 }

ipadRIPTrustNeighbors OBJECT-TYPE
    SYNTAX  INTEGER
            {
            disabled(1),
            enabled(2)
            }
    ACCESS  read-write
    STATUS  mandatory
    DESCRIPTION
        "Determines if RIP Neighbors should be trusted."
    ::= { ipadRIPParms 2 }

ipadRIPInterval OBJECT-TYPE
    SYNTAX  INTEGER(0..65535)
    ACCESS  read-write
    STATUS  mandatory
    DESCRIPTION
        "Specifies the RIP interval in seconds."
    ::= { ipadRIPParms 3 }

ipadRIPDomain OBJECT-TYPE
    SYNTAX  INTEGER(0..65535)
    ACCESS  read-write
    STATUS  mandatory
    DESCRIPTION
        "Specifies the RIP Domain."
    ::= { ipadRIPParms 4 }

-- static ARP parameters

ipadRIPStaticARPTable OBJECT-TYPE
    SYNTAX    SEQUENCE OF IpadRIPStaticARPTableEntry
    ACCESS    not-accessible
    STATUS    optional
    DESCRIPTION
        "Table of RIP Static ARP parameters."
    ::= { ipadRIPParms 5 }

ipadRIPStaticARPTableEntry OBJECT-TYPE
    SYNTAX  IpadRIPStaticARPTableEntry
    ACCESS  not-accessible
    STATUS  mandatory
    DESCRIPTION
        "An entry in the ipad RIP Static ARP parameter table."
    INDEX   { ipadRIPStaticARPIndex }
    ::= { ipadRIPStaticARPTable 1 }

IpadRIPStaticARPTableEntry ::=
    SEQUENCE
    {
    ipadRIPStaticARPIndex                INTEGER,
    ipadRIPStaticARPEndpoint             DisplayString,
    ipadRIPStaticARPIpAddress            IpAddress,
    ipadRIPStaticARPMacAddress           DisplayString,
    ipadRIPStaticARPDLCIAddress          INTEGER,
    ipadRIPStaticARPEnableARP            INTEGER
    }

ipadRIPStaticARPIndex       OBJECT-TYPE
    SYNTAX  INTEGER
    ACCESS  read-only
    STATUS  mandatory
    DESCRIPTION
        "The index into the RIP Static ARP table."
    ::= { ipadRIPStaticARPTableEntry 1 }

ipadRIPStaticARPEndpoint    OBJECT-TYPE
    SYNTAX  DisplayString
    ACCESS  read-write
    STATUS  mandatory
    DESCRIPTION
        "An entry in the endpoint table."
    ::= { ipadRIPStaticARPTableEntry 2 }

ipadRIPStaticARPIpAddress    OBJECT-TYPE
    SYNTAX  IpAddress
    ACCESS  read-write
    STATUS  mandatory
    DESCRIPTION
        "This is the IP address of the device we will 
        associate the MAC or DLCI address."
    ::= { ipadRIPStaticARPTableEntry 3 }

ipadRIPStaticARPMacAddress    OBJECT-TYPE
    SYNTAX  DisplayString
    ACCESS  read-write
    STATUS  mandatory
    DESCRIPTION
        "MAC address of the device."
    ::= { ipadRIPStaticARPTableEntry 4 }

ipadRIPStaticARPDLCIAddress    OBJECT-TYPE
    SYNTAX  INTEGER
    ACCESS  read-write
    STATUS  mandatory
    DESCRIPTION
        "DLCI address of the device."
    ::= { ipadRIPStaticARPTableEntry 5 }

ipadRIPStaticARPEnableARP    OBJECT-TYPE
    SYNTAX  INTEGER
            {
            disabled(1),
            enabled(2)
            }
    ACCESS  read-write
    STATUS  mandatory
    DESCRIPTION
        "Enable that Static ARP Entry."
    ::= { ipadRIPStaticARPTableEntry 6 }

ipadRIPStaticARPAdd    OBJECT-TYPE
    SYNTAX  INTEGER
            {
            other(1),
            addnew(2)
            }
    ACCESS  read-write
    STATUS  mandatory
    DESCRIPTION
        "Writing addnew(2) to this field causes a new (blank) 
        route to be appended to the Static ARP Table."
    ::= { ipadRIPParms 6 }

ipadRIPStaticARPDelete    OBJECT-TYPE
    SYNTAX  INTEGER
    ACCESS  read-write
    STATUS  mandatory
    DESCRIPTION
        "Writing the index of an entry in the Static ARP table
        causes that entry to be deleted."
    ::= { ipadRIPParms 7 }

-- static Route parameters

ipadRIPStaticRouteTable OBJECT-TYPE
    SYNTAX    SEQUENCE OF IpadRIPStaticRouteTableEntry
    ACCESS    not-accessible
    STATUS    optional
    DESCRIPTION
        "Table of RIP Static Route parameters."
    ::= { ipadRIPParms 8 }

ipadRIPStaticRouteTableEntry OBJECT-TYPE
    SYNTAX  IpadRIPStaticRouteTableEntry
    ACCESS  not-accessible
    STATUS  mandatory
    DESCRIPTION
        "An entry in the ipad RIP Static Route parameter table."
    INDEX   { ipadRIPStaticRouteIndex }
    ::= { ipadRIPStaticRouteTable 1 }

IpadRIPStaticRouteTableEntry ::=
    SEQUENCE
    {
    ipadRIPStaticRouteIndex              INTEGER,
    ipadRIPStaticRouteEndpoint           DisplayString,
    ipadRIPStaticRouteTargetIpAddress    IpAddress,
    ipadRIPStaticRouteTargetIpMask       IpAddress,
    ipadRIPStaticRouteNextHopIpAddress   IpAddress,
    ipadRIPStaticRouteCost               INTEGER,
    ipadRIPStaticRouteEnableRouter       INTEGER
    }

ipadRIPStaticRouteIndex       OBJECT-TYPE
    SYNTAX  INTEGER
    ACCESS  read-only
    STATUS  mandatory
    DESCRIPTION
        "The index into the RIP Static Route table."
    ::= { ipadRIPStaticRouteTableEntry 1 }

ipadRIPStaticRouteEndpoint    OBJECT-TYPE
    SYNTAX  DisplayString
    ACCESS  read-write
    STATUS  mandatory
    DESCRIPTION
        "An entry in the endpoint table."
    ::= { ipadRIPStaticRouteTableEntry 2 }

ipadRIPStaticRouteTargetIpAddress    OBJECT-TYPE
    SYNTAX  IpAddress
    ACCESS  read-write
    STATUS  mandatory
    DESCRIPTION
        ""
    ::= { ipadRIPStaticRouteTableEntry 3 }

ipadRIPStaticRouteTargetIpMask    OBJECT-TYPE
    SYNTAX  IpAddress
    ACCESS  read-write
    STATUS  mandatory
    DESCRIPTION
        "IP Mask of the IP address."
    ::= { ipadRIPStaticRouteTableEntry 4 }

ipadRIPStaticRouteNextHopIpAddress    OBJECT-TYPE
    SYNTAX  IpAddress
    ACCESS  read-write
    STATUS  mandatory
    DESCRIPTION
        "Next Hop IP address to reach the remote Network."
    ::= { ipadRIPStaticRouteTableEntry 5 }

ipadRIPStaticRouteCost    OBJECT-TYPE
    SYNTAX  INTEGER(0..65535)
    ACCESS  read-write
    STATUS  mandatory
    DESCRIPTION
        "Cost to reach that remote Network."
    ::= { ipadRIPStaticRouteTableEntry 6 }

ipadRIPStaticRouteEnableRouter    OBJECT-TYPE
    SYNTAX  INTEGER
            {
            disabled(1),
            enabled(2)
            }
    ACCESS  read-write
    STATUS  mandatory
    DESCRIPTION
        "Enable or Not this static route."
    ::= { ipadRIPStaticRouteTableEntry 7 }

ipadRIPStaticRouteAdd    OBJECT-TYPE
    SYNTAX  INTEGER
            {
            other(1),
            addnew(2)
            }
    ACCESS  read-write
    STATUS  mandatory
    DESCRIPTION
        "Writing addnew(2) to this field causes a new (blank) 
        route to be appended to the Static Route Table."
    ::= { ipadRIPParms 9 }

ipadRIPStaticRouteDelete    OBJECT-TYPE
    SYNTAX  INTEGER
    ACCESS  read-write
    STATUS  mandatory
    DESCRIPTION
        "Writing the index of an entry in the Static Route table
        causes that entry to be deleted."
    ::= { ipadRIPParms 10 }

-- trusted neighbor table

ipadRIPNeighborTable OBJECT-TYPE
    SYNTAX    SEQUENCE OF IpadRIPNeighborTableEntry
    ACCESS    not-accessible
    STATUS    optional
    DESCRIPTION
        "Table of RIP trusted neighbors."
    ::= { ipadRIPParms 11 }

ipadRIPNeighborTableEntry OBJECT-TYPE
    SYNTAX  IpadRIPNeighborTableEntry
    ACCESS  not-accessible
    STATUS  mandatory
    DESCRIPTION
        "An entry in the ipad RIP trusted neighbor table."
    INDEX   { ipadRIPNeighborIndex }
    ::= { ipadRIPNeighborTable 1 }

IpadRIPNeighborTableEntry ::=
    SEQUENCE
    {
    ipadRIPNeighborIndex   INTEGER,
    ipadRIPNeighborAddress IpAddress
    }

ipadRIPNeighborIndex    OBJECT-TYPE
    SYNTAX  INTEGER
    ACCESS  read-only
    STATUS  mandatory
    DESCRIPTION
        "The index into the ipadRIPNeighborTable."
    ::= { ipadRIPNeighborTableEntry 1 }

ipadRIPNeighborAddress    OBJECT-TYPE
    SYNTAX  IpAddress
    ACCESS  read-only
    STATUS  mandatory
    DESCRIPTION
        "A RIP trusted neighbor."
    ::= { ipadRIPNeighborTableEntry 2 }

ipadRIPNeighborAdd    OBJECT-TYPE
    SYNTAX  IpAddress
    ACCESS  read-write
    STATUS  mandatory
    DESCRIPTION
        "Writing an IP address to this object adds the IP 
        address to the ipad RIP Trusted Neighbor table."
    ::= { ipadRIPParms 12 }

ipadRIPNeighborDelete    OBJECT-TYPE
    SYNTAX  IpAddress
    ACCESS  read-write
    STATUS  mandatory
    DESCRIPTION
        "Writing an IP address to this object removes the 
        IP address from the ipad RIP Trusted Neighbor table."
    ::= { ipadRIPParms 13 }

END
