-- ************************************************************************************************
-- FileName    :mpAlmTRAP.my
-- Description :MultiMedia Platform private MIB(障害管理 TRAP定義ファイル)
-- Revision History     :
--   Ver.     mark   date      
--   01.01    @001   12/21/1998
--
-- ************************************************************************************************
--
-- 障害管理で定義するTRAPのMIB仕様書
--


MP-TRAP DEFINITIONS ::= BEGIN

-- specific-trapの値は、上位3桁（機能ブロック単位の値）を138と定義し、
-- 下位3桁（TRAPコード値）を001より順に定義する。

-- 4桁目は発生・復旧に振り分ける。0=発生　1=復旧

IMPORTS 
           TRAP-TYPE
                         FROM RFC-1215 
           mpEventTimeStamp, mpEventSeverity, mpEventDescription
                         FROM MMPF-MIB;

-- 98/12/15 YI mmpf => mmpf-mib CHG start @001
-- sysObjectID 
   necProduct        OBJECT IDENTIFIER ::= { nec 1 }
   datax             OBJECT IDENTIFIER ::= { necProduct 3 }
   mmpf              OBJECT IDENTIFIER ::= { datax 13 }
   mmn9110           OBJECT IDENTIFIER ::= { mmpf 1 }
   mmn9120           OBJECT IDENTIFIER ::= { mmpf 2 }
-- [sysObjectID]  MM-Node9110/MM-Node9120
--  mmn9110           OBJECT IDENTIFIER ::= { nec necProduct(1) datax(3) mmpf(13) mmn9110(1) }
--  mmn9120           OBJECT IDENTIFIER ::= { nec necProduct(1) datax(3) mmpf(13) mmn9110(2) }


--  mmn9110   OBJECT IDENTIFIER ::= { nec necProduct(1) datax(3) mmpf(13) mmn9110(1) }
--  mmn9120   OBJECT IDENTIFIER ::= { nec necProduct(1) datax(3) mmpf(13) mmn9110(2) }
-- 98/12/15 YI mmpf => mmpf-mib CHG end


--
-- 障害管理に関するTRAP
--

-- アラーム再収集
alarmReCollect  TRAP-TYPE
     ENTERPRISE           { mmn9110 }
     VARIABLES            { mpEventTimeStamp,
                            mpEventSeverity,
                            mpEventDescription }
     DESCRIPTION
           "アラーム再収集を通知する。
            ＣＬＩ／ＮＭＳからのアラーム再収集コマンド及び再開時のアラーム再収集を
            行った場合に通知する。"
     ::= 1380001


END
