AVIDIA-V2-TRAPS DEFINITIONS ::= BEGIN

IMPORTS
    MODULE-IDENTITY, OBJECT-TYPE, NOTIFICATION-TYPE,
    TimeTicks, Counter32, snmpModules, mib-2
        FROM SNMPv2-SMI
    DisplayString, TestAndIncr, TimeStamp
        FROM SNMPv2-TC
    MODULE-COMPLIANCE, OBJECT-GROUP
        FROM SNMPv2-CONF
    pgDSLAMSlotNumber
	    FROM PAIRGAIN-DSLAM-CHASSIS-MIB;

avV2TrapMIB MODULE-IDENTITY
    LAST-UPDATED "0004012000Z"
    ORGANIZATION "PairGain Technologies, Inc."
    CONTACT-INFO ""
    DESCRIPTION
            "The MIB module to describe V2 traps for AVIDIA products"
    ::= { pgainDSLAM 20 }

avV2TrapObjects OBJECT IDENTIFIER ::= { avV2TrapMIB 1 }

avV2TrapModuleRemove NOTIFICATION-TYPE
    OBJECTS { pgDSLAMSlotNumber }
    STATUS  current
    DESCRIPTION
       "A moduleDown trap signifies that the SNMPv2 entity, acting
        in an agent role, has detected that one of its modules is no
        longer present."
    ::= { avV2TrapObjects 1 }

avV2TrapModuleInsert NOTIFICATION-TYPE
    OBJECTS { pgDSLAMSlotNumber }
    STATUS  current
    DESCRIPTION
       "A moduleUp trap signifies that the SNMPv2 entity, acting
        in an agent role, has detected that a module is now
        present in a slot that was previously detected as vacant."
    ::= { avV2TrapObjects 2 }

END
