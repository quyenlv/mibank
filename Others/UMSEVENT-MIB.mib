UMSEVENT-MIB DEFINITIONS ::= BEGIN

IMPORTS
   OBJECT-TYPE
      FROM RFC-1212

   TRAP-TYPE
      FROM RFC-1215

   ibmpsgEvent,
   Boolean, Uint8, Sint8, Uint16, Sint16, Uint32,
   Sint32, Uint64, Sint64, Real32, Real64, String, Datetime
      FROM UMS-MIB;

iBMPSGGenericEvent TRAP-TYPE
   ENTERPRISE     umservices
   VARIABLES    {
      iBMPSGGenericEventIdentifier,
      iBMPSGGenericEventSourceObjectPath,
      iBMPSGGenericEventTargetObjectPath,
      iBMPSGGenericEventdescription,
      iBMPSGGenericEventSeverity,
      iBMPSGGenericEventTimeStamp
   }
   DESCRIPTION    ""
   REFERENCE      "IBMPSG_GenericEvent"
::= 1

iBMPSGGenericEventBindings OBJECT IDENTIFIER ::= { ibmpsgEvent 1 }

iBMPSGGenericEventIdentifier OBJECT-TYPE
   SYNTAX         String
   ACCESS         read-write
   STATUS         mandatory
   DESCRIPTION    ""
   REFERENCE      "IBMPSG_GenericEvent.Identifier"
::= { iBMPSGGenericEventBindings 1 }

iBMPSGGenericEventSourceObjectPath OBJECT-TYPE
   SYNTAX         String
   ACCESS         read-write
   STATUS         mandatory
   DESCRIPTION    ""
   REFERENCE      "IBMPSG_GenericEvent.SourceObjectPath"
::= { iBMPSGGenericEventBindings 2 }

iBMPSGGenericEventTargetObjectPath OBJECT-TYPE
   SYNTAX         String
   ACCESS         read-write
   STATUS         mandatory
   DESCRIPTION    ""
   REFERENCE      "IBMPSG_GenericEvent.TargetObjectPath"
::= { iBMPSGGenericEventBindings 3 }

iBMPSGGenericEventdescription OBJECT-TYPE
   SYNTAX         String
   ACCESS         read-write
   STATUS         mandatory
   DESCRIPTION    ""
   REFERENCE      "IBMPSG_GenericEvent.description"
::= { iBMPSGGenericEventBindings 4 }

iBMPSGGenericEventSeverity OBJECT-TYPE
   SYNTAX         Uint16
   ACCESS         read-write
   STATUS         mandatory
   DESCRIPTION    ""
   REFERENCE      "IBMPSG_GenericEvent.Severity"
::= { iBMPSGGenericEventBindings 5 }

iBMPSGGenericEventTimeStamp OBJECT-TYPE
   SYNTAX         Datetime
   ACCESS         read-write
   STATUS         mandatory
   DESCRIPTION    ""
   REFERENCE      "IBMPSG_GenericEvent.TimeStamp"
::= { iBMPSGGenericEventBindings 6 }

iBMPSGTemperatureEvent TRAP-TYPE
   ENTERPRISE     umservices
   VARIABLES    {
      iBMPSGTemperatureEventIdentifier,
      iBMPSGTemperatureEventSourceObjectPath,
      iBMPSGTemperatureEventTargetObjectPath,
      iBMPSGTemperatureEventSeverity,
      iBMPSGTemperatureEventdescription,
      iBMPSGTemperatureEventTimeStamp
   }
   DESCRIPTION    ""
   REFERENCE      "IBMPSG_TemperatureEvent"
::= 2

iBMPSGTemperatureEventBindings OBJECT IDENTIFIER ::= { ibmpsgEvent 2 }

iBMPSGTemperatureEventIdentifier OBJECT-TYPE
   SYNTAX         String
   ACCESS         read-write
   STATUS         mandatory
   DESCRIPTION    ""
   REFERENCE      "IBMPSG_TemperatureEvent.Identifier"
::= { iBMPSGTemperatureEventBindings 1 }

iBMPSGTemperatureEventSourceObjectPath OBJECT-TYPE
   SYNTAX         String
   ACCESS         read-write
   STATUS         mandatory
   DESCRIPTION    ""
   REFERENCE      "IBMPSG_TemperatureEvent.SourceObjectPath"
::= { iBMPSGTemperatureEventBindings 2 }

iBMPSGTemperatureEventTargetObjectPath OBJECT-TYPE
   SYNTAX         String
   ACCESS         read-write
   STATUS         mandatory
   DESCRIPTION    ""
   REFERENCE      "IBMPSG_TemperatureEvent.TargetObjectPath"
::= { iBMPSGTemperatureEventBindings 3 }

iBMPSGTemperatureEventSeverity OBJECT-TYPE
   SYNTAX         Uint16
   ACCESS         read-write
   STATUS         mandatory
   DESCRIPTION    ""
   REFERENCE      "IBMPSG_TemperatureEvent.Severity"
::= { iBMPSGTemperatureEventBindings 4 }

iBMPSGTemperatureEventdescription OBJECT-TYPE
   SYNTAX         String
   ACCESS         read-write
   STATUS         mandatory
   DESCRIPTION    ""
   REFERENCE      "IBMPSG_TemperatureEvent.description"
::= { iBMPSGTemperatureEventBindings 5 }

iBMPSGTemperatureEventTimeStamp OBJECT-TYPE
   SYNTAX         Datetime
   ACCESS         read-write
   STATUS         mandatory
   DESCRIPTION    ""
   REFERENCE      "IBMPSG_TemperatureEvent.TimeStamp"
::= { iBMPSGTemperatureEventBindings 6 }

iBMPSGVoltageEvent TRAP-TYPE
   ENTERPRISE     umservices
   VARIABLES    {
      iBMPSGVoltageEventIdentifier,
      iBMPSGVoltageEventSourceObjectPath,
      iBMPSGVoltageEventTargetObjectPath,
      iBMPSGVoltageEventSeverity,
      iBMPSGVoltageEventdescription,
      iBMPSGVoltageEventTimeStamp
   }
   DESCRIPTION    ""
   REFERENCE      "IBMPSG_VoltageEvent"
::= 3

iBMPSGVoltageEventBindings OBJECT IDENTIFIER ::= { ibmpsgEvent 3 }

iBMPSGVoltageEventIdentifier OBJECT-TYPE
   SYNTAX         String
   ACCESS         read-write
   STATUS         mandatory
   DESCRIPTION    ""
   REFERENCE      "IBMPSG_VoltageEvent.Identifier"
::= { iBMPSGVoltageEventBindings 1 }

iBMPSGVoltageEventSourceObjectPath OBJECT-TYPE
   SYNTAX         String
   ACCESS         read-write
   STATUS         mandatory
   DESCRIPTION    ""
   REFERENCE      "IBMPSG_VoltageEvent.SourceObjectPath"
::= { iBMPSGVoltageEventBindings 2 }

iBMPSGVoltageEventTargetObjectPath OBJECT-TYPE
   SYNTAX         String
   ACCESS         read-write
   STATUS         mandatory
   DESCRIPTION    ""
   REFERENCE      "IBMPSG_VoltageEvent.TargetObjectPath"
::= { iBMPSGVoltageEventBindings 3 }

iBMPSGVoltageEventSeverity OBJECT-TYPE
   SYNTAX         Uint16
   ACCESS         read-write
   STATUS         mandatory
   DESCRIPTION    ""
   REFERENCE      "IBMPSG_VoltageEvent.Severity"
::= { iBMPSGVoltageEventBindings 4 }

iBMPSGVoltageEventdescription OBJECT-TYPE
   SYNTAX         String
   ACCESS         read-write
   STATUS         mandatory
   DESCRIPTION    ""
   REFERENCE      "IBMPSG_VoltageEvent.description"
::= { iBMPSGVoltageEventBindings 5 }

iBMPSGVoltageEventTimeStamp OBJECT-TYPE
   SYNTAX         Datetime
   ACCESS         read-write
   STATUS         mandatory
   DESCRIPTION    ""
   REFERENCE      "IBMPSG_VoltageEvent.TimeStamp"
::= { iBMPSGVoltageEventBindings 6 }

iBMPSGChassisEvent TRAP-TYPE
   ENTERPRISE     umservices
   VARIABLES    {
      iBMPSGChassisEventIdentifier,
      iBMPSGChassisEventSourceObjectPath,
      iBMPSGChassisEventTargetObjectPath,
      iBMPSGChassisEventSeverity,
      iBMPSGChassisEventdescription,
      iBMPSGChassisEventTimeStamp
   }
   DESCRIPTION    ""
   REFERENCE      "IBMPSG_ChassisEvent"
::= 4

iBMPSGChassisEventBindings OBJECT IDENTIFIER ::= { ibmpsgEvent 4 }

iBMPSGChassisEventIdentifier OBJECT-TYPE
   SYNTAX         String
   ACCESS         read-write
   STATUS         mandatory
   DESCRIPTION    ""
   REFERENCE      "IBMPSG_ChassisEvent.Identifier"
::= { iBMPSGChassisEventBindings 1 }

iBMPSGChassisEventSourceObjectPath OBJECT-TYPE
   SYNTAX         String
   ACCESS         read-write
   STATUS         mandatory
   DESCRIPTION    ""
   REFERENCE      "IBMPSG_ChassisEvent.SourceObjectPath"
::= { iBMPSGChassisEventBindings 2 }

iBMPSGChassisEventTargetObjectPath OBJECT-TYPE
   SYNTAX         String
   ACCESS         read-write
   STATUS         mandatory
   DESCRIPTION    ""
   REFERENCE      "IBMPSG_ChassisEvent.TargetObjectPath"
::= { iBMPSGChassisEventBindings 3 }

iBMPSGChassisEventSeverity OBJECT-TYPE
   SYNTAX         Uint16
   ACCESS         read-write
   STATUS         mandatory
   DESCRIPTION    ""
   REFERENCE      "IBMPSG_ChassisEvent.Severity"
::= { iBMPSGChassisEventBindings 4 }

iBMPSGChassisEventdescription OBJECT-TYPE
   SYNTAX         String
   ACCESS         read-write
   STATUS         mandatory
   DESCRIPTION    ""
   REFERENCE      "IBMPSG_ChassisEvent.description"
::= { iBMPSGChassisEventBindings 5 }

iBMPSGChassisEventTimeStamp OBJECT-TYPE
   SYNTAX         Datetime
   ACCESS         read-write
   STATUS         mandatory
   DESCRIPTION    ""
   REFERENCE      "IBMPSG_ChassisEvent.TimeStamp"
::= { iBMPSGChassisEventBindings 6 }

iBMPSGFanEvent TRAP-TYPE
   ENTERPRISE     umservices
   VARIABLES    {
      iBMPSGFanEventIdentifier,
      iBMPSGFanEventSourceObjectPath,
      iBMPSGFanEventTargetObjectPath,
      iBMPSGFanEventSeverity,
      iBMPSGFanEventdescription,
      iBMPSGFanEventTimeStamp
   }
   DESCRIPTION    ""
   REFERENCE      "IBMPSG_FanEvent"
::=  5

iBMPSGFanEventBindings OBJECT IDENTIFIER ::= { ibmpsgEvent 5 }

iBMPSGFanEventIdentifier OBJECT-TYPE
   SYNTAX         String
   ACCESS         read-write
   STATUS         mandatory
   DESCRIPTION    ""
   REFERENCE      "IBMPSG_FanEvent.Identifier"
::= { iBMPSGFanEventBindings 1 }

iBMPSGFanEventSourceObjectPath OBJECT-TYPE
   SYNTAX         String
   ACCESS         read-write
   STATUS         mandatory
   DESCRIPTION    ""
   REFERENCE      "IBMPSG_FanEvent.SourceObjectPath"
::= { iBMPSGFanEventBindings 2 }

iBMPSGFanEventTargetObjectPath OBJECT-TYPE
   SYNTAX         String
   ACCESS         read-write
   STATUS         mandatory
   DESCRIPTION    ""
   REFERENCE      "IBMPSG_FanEvent.TargetObjectPath"
::= { iBMPSGFanEventBindings 3 }

iBMPSGFanEventSeverity OBJECT-TYPE
   SYNTAX         Uint16
   ACCESS         read-write
   STATUS         mandatory
   DESCRIPTION    ""
   REFERENCE      "IBMPSG_FanEvent.Severity"
::= { iBMPSGFanEventBindings 4 }

iBMPSGFanEventdescription OBJECT-TYPE
   SYNTAX         String
   ACCESS         read-write
   STATUS         mandatory
   DESCRIPTION    ""
   REFERENCE      "IBMPSG_FanEvent.description"
::= { iBMPSGFanEventBindings 5 }

iBMPSGFanEventTimeStamp OBJECT-TYPE
   SYNTAX         Datetime
   ACCESS         read-write
   STATUS         mandatory
   DESCRIPTION    ""
   REFERENCE      "IBMPSG_FanEvent.TimeStamp"
::= { iBMPSGFanEventBindings 6 }

iBMPSGProcessorEvent TRAP-TYPE
   ENTERPRISE     umservices
   VARIABLES    {
      iBMPSGProcessorEventIdentifier,
      iBMPSGProcessorEventSourceObjectPath,
      iBMPSGProcessorEventTargetObjectPath,
      iBMPSGProcessorEventSeverity,
      iBMPSGProcessorEventdescription,
      iBMPSGProcessorEventTimeStamp
   }
   DESCRIPTION    ""
   REFERENCE      "IBMPSG_ProcessorEvent"
::= 6

iBMPSGProcessorEventBindings OBJECT IDENTIFIER ::= { ibmpsgEvent 6 }

iBMPSGProcessorEventIdentifier OBJECT-TYPE
   SYNTAX         String
   ACCESS         read-write
   STATUS         mandatory
   DESCRIPTION    ""
   REFERENCE      "IBMPSG_ProcessorEvent.Identifier"
::= { iBMPSGProcessorEventBindings 1 }

iBMPSGProcessorEventSourceObjectPath OBJECT-TYPE
   SYNTAX         String
   ACCESS         read-write
   STATUS         mandatory
   DESCRIPTION    ""
   REFERENCE      "IBMPSG_ProcessorEvent.SourceObjectPath"
::= { iBMPSGProcessorEventBindings 2 }

iBMPSGProcessorEventTargetObjectPath OBJECT-TYPE
   SYNTAX         String
   ACCESS         read-write
   STATUS         mandatory
   DESCRIPTION    ""
   REFERENCE      "IBMPSG_ProcessorEvent.TargetObjectPath"
::= { iBMPSGProcessorEventBindings 3 }

iBMPSGProcessorEventSeverity OBJECT-TYPE
   SYNTAX         Uint16
   ACCESS         read-write
   STATUS         mandatory
   DESCRIPTION    ""
   REFERENCE      "IBMPSG_ProcessorEvent.Severity"
::= { iBMPSGProcessorEventBindings 4 }

iBMPSGProcessorEventdescription OBJECT-TYPE
   SYNTAX         String
   ACCESS         read-write
   STATUS         mandatory
   DESCRIPTION    ""
   REFERENCE      "IBMPSG_ProcessorEvent.description"
::= { iBMPSGProcessorEventBindings 5 }

iBMPSGProcessorEventTimeStamp OBJECT-TYPE
   SYNTAX         Datetime
   ACCESS         read-write
   STATUS         mandatory
   DESCRIPTION    ""
   REFERENCE      "IBMPSG_ProcessorEvent.TimeStamp"
::= { iBMPSGProcessorEventBindings 6 }

iBMPSGStorageEvent TRAP-TYPE
   ENTERPRISE     umservices
   VARIABLES    {
      iBMPSGStorageEventIdentifier,
      iBMPSGStorageEventSourceObjectPath,
      iBMPSGStorageEventTargetObjectPath,
      iBMPSGStorageEventSeverity,
      iBMPSGStorageEventdescription,
      iBMPSGStorageEventTimeStamp
   }
   DESCRIPTION    ""
   REFERENCE      "IBMPSG_StorageEvent"
::= 7

iBMPSGStorageEventBindings OBJECT IDENTIFIER ::= { ibmpsgEvent 7 }

iBMPSGStorageEventIdentifier OBJECT-TYPE
   SYNTAX         String
   ACCESS         read-write
   STATUS         mandatory
   DESCRIPTION    ""
   REFERENCE      "IBMPSG_StorageEvent.Identifier"
::= { iBMPSGStorageEventBindings 1 }

iBMPSGStorageEventSourceObjectPath OBJECT-TYPE
   SYNTAX         String
   ACCESS         read-write
   STATUS         mandatory
   DESCRIPTION    ""
   REFERENCE      "IBMPSG_StorageEvent.SourceObjectPath"
::= { iBMPSGStorageEventBindings 2 }

iBMPSGStorageEventTargetObjectPath OBJECT-TYPE
   SYNTAX         String
   ACCESS         read-write
   STATUS         mandatory
   DESCRIPTION    ""
   REFERENCE      "IBMPSG_StorageEvent.TargetObjectPath"
::= { iBMPSGStorageEventBindings 3 }

iBMPSGStorageEventSeverity OBJECT-TYPE
   SYNTAX         Uint16
   ACCESS         read-write
   STATUS         mandatory
   DESCRIPTION    ""
   REFERENCE      "IBMPSG_StorageEvent.Severity"
::= { iBMPSGStorageEventBindings 4 }

iBMPSGStorageEventdescription OBJECT-TYPE
   SYNTAX         String
   ACCESS         read-write
   STATUS         mandatory
   DESCRIPTION    ""
   REFERENCE      "IBMPSG_StorageEvent.description"
::= { iBMPSGStorageEventBindings 5 }

iBMPSGStorageEventTimeStamp OBJECT-TYPE
   SYNTAX         Datetime
   ACCESS         read-write
   STATUS         mandatory
   DESCRIPTION    ""
   REFERENCE      "IBMPSG_StorageEvent.TimeStamp"
::= { iBMPSGStorageEventBindings 6 }

iBMPSGAssetEvent TRAP-TYPE
   ENTERPRISE     umservices
   VARIABLES    {
      iBMPSGAssetEventIdentifier,
      iBMPSGAssetEventSourceObjectPath,
      iBMPSGAssetEventTargetObjectPath,
      iBMPSGAssetEventSeverity,
      iBMPSGAssetEventdescription,
      iBMPSGAssetEventTimeStamp
   }
   DESCRIPTION    ""
   REFERENCE      "IBMPSG_AssetEvent"
::= 8

iBMPSGAssetEventBindings OBJECT IDENTIFIER ::= { ibmpsgEvent 8 }

iBMPSGAssetEventIdentifier OBJECT-TYPE
   SYNTAX         String
   ACCESS         read-write
   STATUS         mandatory
   DESCRIPTION    ""
   REFERENCE      "IBMPSG_AssetEvent.Identifier"
::= { iBMPSGAssetEventBindings 1 }

iBMPSGAssetEventSourceObjectPath OBJECT-TYPE
   SYNTAX         String
   ACCESS         read-write
   STATUS         mandatory
   DESCRIPTION    ""
   REFERENCE      "IBMPSG_AssetEvent.SourceObjectPath"
::= { iBMPSGAssetEventBindings 2 }

iBMPSGAssetEventTargetObjectPath OBJECT-TYPE
   SYNTAX         String
   ACCESS         read-write
   STATUS         mandatory
   DESCRIPTION    ""
   REFERENCE      "IBMPSG_AssetEvent.TargetObjectPath"
::= { iBMPSGAssetEventBindings 3 }

iBMPSGAssetEventSeverity OBJECT-TYPE
   SYNTAX         Uint16
   ACCESS         read-write
   STATUS         mandatory
   DESCRIPTION    ""
   REFERENCE      "IBMPSG_AssetEvent.Severity"
::= { iBMPSGAssetEventBindings 4 }

iBMPSGAssetEventdescription OBJECT-TYPE
   SYNTAX         String
   ACCESS         read-write
   STATUS         mandatory
   DESCRIPTION    ""
   REFERENCE      "IBMPSG_AssetEvent.description"
::= { iBMPSGAssetEventBindings 5 }

iBMPSGAssetEventTimeStamp OBJECT-TYPE
   SYNTAX         Datetime
   ACCESS         read-write
   STATUS         mandatory
   DESCRIPTION    ""
   REFERENCE      "IBMPSG_AssetEvent.TimeStamp"
::= { iBMPSGAssetEventBindings 6 }

iBMPSGSMARTEvent TRAP-TYPE
   ENTERPRISE     umservices
   VARIABLES    {
      iBMPSGSMARTEventIdentifier,
      iBMPSGSMARTEventSourceObjectPath,
      iBMPSGSMARTEventTargetObjectPath,
      iBMPSGSMARTEventSeverity,
      iBMPSGSMARTEventdescription,
      iBMPSGSMARTEventTimeStamp
   }
   DESCRIPTION    ""
   REFERENCE      "IBMPSG_SMARTEvent"
::= 9

iBMPSGSMARTEventBindings OBJECT IDENTIFIER ::= { ibmpsgEvent 9 }

iBMPSGSMARTEventIdentifier OBJECT-TYPE
   SYNTAX         String
   ACCESS         read-write
   STATUS         mandatory
   DESCRIPTION    ""
   REFERENCE      "IBMPSG_SMARTEvent.Identifier"
::= { iBMPSGSMARTEventBindings 1 }

iBMPSGSMARTEventSourceObjectPath OBJECT-TYPE
   SYNTAX         String
   ACCESS         read-write
   STATUS         mandatory
   DESCRIPTION    ""
   REFERENCE      "IBMPSG_SMARTEvent.SourceObjectPath"
::= { iBMPSGSMARTEventBindings 2 }

iBMPSGSMARTEventTargetObjectPath OBJECT-TYPE
   SYNTAX         String
   ACCESS         read-write
   STATUS         mandatory
   DESCRIPTION    ""
   REFERENCE      "IBMPSG_SMARTEvent.TargetObjectPath"
::= { iBMPSGSMARTEventBindings 3 }

iBMPSGSMARTEventSeverity OBJECT-TYPE
   SYNTAX         Uint16
   ACCESS         read-write
   STATUS         mandatory
   DESCRIPTION    ""
   REFERENCE      "IBMPSG_SMARTEvent.Severity"
::= { iBMPSGSMARTEventBindings 4 }

iBMPSGSMARTEventdescription OBJECT-TYPE
   SYNTAX         String
   ACCESS         read-write
   STATUS         mandatory
   DESCRIPTION    ""
   REFERENCE      "IBMPSG_SMARTEvent.description"
::= { iBMPSGSMARTEventBindings 5 }

iBMPSGSMARTEventTimeStamp OBJECT-TYPE
   SYNTAX         Datetime
   ACCESS         read-write
   STATUS         mandatory
   DESCRIPTION    ""
   REFERENCE      "IBMPSG_SMARTEvent.TimeStamp"
::= { iBMPSGSMARTEventBindings 6 }

iBMPSGPOSTEvent TRAP-TYPE
   ENTERPRISE     umservices
   VARIABLES    {
      iBMPSGPOSTEventIdentifier,
      iBMPSGPOSTEventSourceObjectPath,
      iBMPSGPOSTEventTargetObjectPath,
      iBMPSGPOSTEventSeverity,
      iBMPSGPOSTEventdescription,
      iBMPSGPOSTEventTimeStamp
   }
   DESCRIPTION    ""
   REFERENCE      "IBMPSG_POSTEvent"
::= 10

iBMPSGPOSTEventBindings OBJECT IDENTIFIER ::= { ibmpsgEvent 10 }

iBMPSGPOSTEventIdentifier OBJECT-TYPE
   SYNTAX         String
   ACCESS         read-write
   STATUS         mandatory
   DESCRIPTION    ""
   REFERENCE      "IBMPSG_POSTEvent.Identifier"
::= { iBMPSGPOSTEventBindings 1 }

iBMPSGPOSTEventSourceObjectPath OBJECT-TYPE
   SYNTAX         String
   ACCESS         read-write
   STATUS         mandatory
   DESCRIPTION    ""
   REFERENCE      "IBMPSG_POSTEvent.SourceObjectPath"
::= { iBMPSGPOSTEventBindings 2 }

iBMPSGPOSTEventTargetObjectPath OBJECT-TYPE
   SYNTAX         String
   ACCESS         read-write
   STATUS         mandatory
   DESCRIPTION    ""
   REFERENCE      "IBMPSG_POSTEvent.TargetObjectPath"
::= { iBMPSGPOSTEventBindings 3 }

iBMPSGPOSTEventSeverity OBJECT-TYPE
   SYNTAX         Uint16
   ACCESS         read-write
   STATUS         mandatory
   DESCRIPTION    ""
   REFERENCE      "IBMPSG_POSTEvent.Severity"
::= { iBMPSGPOSTEventBindings 4 }

iBMPSGPOSTEventdescription OBJECT-TYPE
   SYNTAX         String
   ACCESS         read-write
   STATUS         mandatory
   DESCRIPTION    ""
   REFERENCE      "IBMPSG_POSTEvent.description"
::= { iBMPSGPOSTEventBindings 5 }

iBMPSGPOSTEventTimeStamp OBJECT-TYPE
   SYNTAX         Datetime
   ACCESS         read-write
   STATUS         mandatory
   DESCRIPTION    ""
   REFERENCE      "IBMPSG_POSTEvent.TimeStamp"
::= { iBMPSGPOSTEventBindings 6 }

iBMPSGConfigurationChangeEvent TRAP-TYPE
   ENTERPRISE     umservices
   VARIABLES    {
      iBMPSGConfigurationChangeEventIdentifier,
      iBMPSGConfigurationChangeEventSourceObjectPath,
      iBMPSGConfigurationChangeEventTargetObjectPath,
      iBMPSGConfigurationChangeEventSeverity,
      iBMPSGConfigurationChangeEventdescription,
      iBMPSGConfigurationChangeEventTimeStamp
   }
   DESCRIPTION    ""
   REFERENCE      "IBMPSG_ConfigurationChangeEvent"
::= 11

iBMPSGConfigurationChangeEventBindings OBJECT IDENTIFIER ::= { ibmpsgEvent 11 }

iBMPSGConfigurationChangeEventIdentifier OBJECT-TYPE
   SYNTAX         String
   ACCESS         read-write
   STATUS         mandatory
   DESCRIPTION    ""
   REFERENCE      "IBMPSG_ConfigurationChangeEvent.Identifier"
::= { iBMPSGConfigurationChangeEventBindings 1 }

iBMPSGConfigurationChangeEventSourceObjectPath OBJECT-TYPE
   SYNTAX         String
   ACCESS         read-write
   STATUS         mandatory
   DESCRIPTION    ""
   REFERENCE      "IBMPSG_ConfigurationChangeEvent.SourceObjectPath"
::= { iBMPSGConfigurationChangeEventBindings 2 }

iBMPSGConfigurationChangeEventTargetObjectPath OBJECT-TYPE
   SYNTAX         String
   ACCESS         read-write
   STATUS         mandatory
   DESCRIPTION    ""
   REFERENCE      "IBMPSG_ConfigurationChangeEvent.TargetObjectPath"
::= { iBMPSGConfigurationChangeEventBindings 3 }

iBMPSGConfigurationChangeEventSeverity OBJECT-TYPE
   SYNTAX         Uint16
   ACCESS         read-write
   STATUS         mandatory
   DESCRIPTION    ""
   REFERENCE      "IBMPSG_ConfigurationChangeEvent.Severity"
::= { iBMPSGConfigurationChangeEventBindings 4 }

iBMPSGConfigurationChangeEventdescription OBJECT-TYPE
   SYNTAX         String
   ACCESS         read-write
   STATUS         mandatory
   DESCRIPTION    ""
   REFERENCE      "IBMPSG_ConfigurationChangeEvent.description"
::= { iBMPSGConfigurationChangeEventBindings 5 }

iBMPSGConfigurationChangeEventTimeStamp OBJECT-TYPE
   SYNTAX         Datetime
   ACCESS         read-write
   STATUS         mandatory
   DESCRIPTION    ""
   REFERENCE      "IBMPSG_ConfigurationChangeEvent.TimeStamp"
::= { iBMPSGConfigurationChangeEventBindings 6 }

iBMPSGLANLeashEvent TRAP-TYPE
   ENTERPRISE     umservices
   VARIABLES    {
      iBMPSGLANLeashEventIdentifier,
      iBMPSGLANLeashEventSourceObjectPath,
      iBMPSGLANLeashEventTargetObjectPath,
      iBMPSGLANLeashEventSeverity,
      iBMPSGLANLeashEventdescription,
      iBMPSGLANLeashEventTimeStamp
   }
   DESCRIPTION    ""
   REFERENCE      "IBMPSG_LANLeashEvent"
::= 12

iBMPSGLANLeashEventBindings OBJECT IDENTIFIER ::= { ibmpsgEvent 12 }

iBMPSGLANLeashEventIdentifier OBJECT-TYPE
   SYNTAX         String
   ACCESS         read-write
   STATUS         mandatory
   DESCRIPTION    ""
   REFERENCE      "IBMPSG_LANLeashEvent.Identifier"
::= { iBMPSGLANLeashEventBindings 1 }

iBMPSGLANLeashEventSourceObjectPath OBJECT-TYPE
   SYNTAX         String
   ACCESS         read-write
   STATUS         mandatory
   DESCRIPTION    ""
   REFERENCE      "IBMPSG_LANLeashEvent.SourceObjectPath"
::= { iBMPSGLANLeashEventBindings 2 }

iBMPSGLANLeashEventTargetObjectPath OBJECT-TYPE
   SYNTAX         String
   ACCESS         read-write
   STATUS         mandatory
   DESCRIPTION    ""
   REFERENCE      "IBMPSG_LANLeashEvent.TargetObjectPath"
::= { iBMPSGLANLeashEventBindings 3 }

iBMPSGLANLeashEventSeverity OBJECT-TYPE
   SYNTAX         Uint16
   ACCESS         read-write
   STATUS         mandatory
   DESCRIPTION    ""
   REFERENCE      "IBMPSG_LANLeashEvent.Severity"
::= { iBMPSGLANLeashEventBindings 4 }

iBMPSGLANLeashEventdescription OBJECT-TYPE
   SYNTAX         String
   ACCESS         read-write
   STATUS         mandatory
   DESCRIPTION    ""
   REFERENCE      "IBMPSG_LANLeashEvent.description"
::= { iBMPSGLANLeashEventBindings 5 }

iBMPSGLANLeashEventTimeStamp OBJECT-TYPE
   SYNTAX         Datetime
   ACCESS         read-write
   STATUS         mandatory
   DESCRIPTION    ""
   REFERENCE      "IBMPSG_LANLeashEvent.TimeStamp"
::= { iBMPSGLANLeashEventBindings 6 }

iBMPSGLeaseExpirationEvent TRAP-TYPE
   ENTERPRISE     umservices
   VARIABLES    {
      iBMPSGLeaseExpirationEventIdentifier,
      iBMPSGLeaseExpirationEventSourceObjectPath,
      iBMPSGLeaseExpirationEventTargetObjectPath,
      iBMPSGLeaseExpirationEventSeverity,
      iBMPSGLeaseExpirationEventdescription,
      iBMPSGLeaseExpirationEventTimeStamp
   }
   DESCRIPTION    ""
   REFERENCE      "IBMPSG_LeaseExpirationEvent"
::= 13

iBMPSGLeaseExpirationEventBindings OBJECT IDENTIFIER ::= { ibmpsgEvent 13 }

iBMPSGLeaseExpirationEventIdentifier OBJECT-TYPE
   SYNTAX         String
   ACCESS         read-write
   STATUS         mandatory
   DESCRIPTION    ""
   REFERENCE      "IBMPSG_LeaseExpirationEvent.Identifier"
::= { iBMPSGLeaseExpirationEventBindings 1 }

iBMPSGLeaseExpirationEventSourceObjectPath OBJECT-TYPE
   SYNTAX         String
   ACCESS         read-write
   STATUS         mandatory
   DESCRIPTION    ""
   REFERENCE      "IBMPSG_LeaseExpirationEvent.SourceObjectPath"
::= { iBMPSGLeaseExpirationEventBindings 2 }

iBMPSGLeaseExpirationEventTargetObjectPath OBJECT-TYPE
   SYNTAX         String
   ACCESS         read-write
   STATUS         mandatory
   DESCRIPTION    ""
   REFERENCE      "IBMPSG_LeaseExpirationEvent.TargetObjectPath"
::= { iBMPSGLeaseExpirationEventBindings 3 }

iBMPSGLeaseExpirationEventSeverity OBJECT-TYPE
   SYNTAX         Uint16
   ACCESS         read-write
   STATUS         mandatory
   DESCRIPTION    ""
   REFERENCE      "IBMPSG_LeaseExpirationEvent.Severity"
::= { iBMPSGLeaseExpirationEventBindings 4 }

iBMPSGLeaseExpirationEventdescription OBJECT-TYPE
   SYNTAX         String
   ACCESS         read-write
   STATUS         mandatory
   DESCRIPTION    ""
   REFERENCE      "IBMPSG_LeaseExpirationEvent.description"
::= { iBMPSGLeaseExpirationEventBindings 5 }

iBMPSGLeaseExpirationEventTimeStamp OBJECT-TYPE
   SYNTAX         Datetime
   ACCESS         read-write
   STATUS         mandatory
   DESCRIPTION    ""
   REFERENCE      "IBMPSG_LeaseExpirationEvent.TimeStamp"
::= { iBMPSGLeaseExpirationEventBindings 6 }

iBMPSGWarrantyExpirationEvent TRAP-TYPE
   ENTERPRISE     umservices
   VARIABLES    {
      iBMPSGWarrantyExpirationEventIdentifier,
      iBMPSGWarrantyExpirationEventSourceObjectPath,
      iBMPSGWarrantyExpirationEventTargetObjectPath,
      iBMPSGWarrantyExpirationEventSeverity,
      iBMPSGWarrantyExpirationEventdescription,
      iBMPSGWarrantyExpirationEventTimeStamp
   }
   DESCRIPTION    ""
   REFERENCE      "IBMPSG_WarrantyExpirationEvent"
::= 14

iBMPSGWarrantyExpirationEventBindings OBJECT IDENTIFIER ::= { ibmpsgEvent 14 }

iBMPSGWarrantyExpirationEventIdentifier OBJECT-TYPE
   SYNTAX         String
   ACCESS         read-write
   STATUS         mandatory
   DESCRIPTION    ""
   REFERENCE      "IBMPSG_WarrantyExpirationEvent.Identifier"
::= { iBMPSGWarrantyExpirationEventBindings 1 }

iBMPSGWarrantyExpirationEventSourceObjectPath OBJECT-TYPE
   SYNTAX         String
   ACCESS         read-write
   STATUS         mandatory
   DESCRIPTION    ""
   REFERENCE      "IBMPSG_WarrantyExpirationEvent.SourceObjectPath"
::= { iBMPSGWarrantyExpirationEventBindings 2 }

iBMPSGWarrantyExpirationEventTargetObjectPath OBJECT-TYPE
   SYNTAX         String
   ACCESS         read-write
   STATUS         mandatory
   DESCRIPTION    ""
   REFERENCE      "IBMPSG_WarrantyExpirationEvent.TargetObjectPath"
::= { iBMPSGWarrantyExpirationEventBindings 3 }

iBMPSGWarrantyExpirationEventSeverity OBJECT-TYPE
   SYNTAX         Uint16
   ACCESS         read-write
   STATUS         mandatory
   DESCRIPTION    ""
   REFERENCE      "IBMPSG_WarrantyExpirationEvent.Severity"
::= { iBMPSGWarrantyExpirationEventBindings 4 }

iBMPSGWarrantyExpirationEventdescription OBJECT-TYPE
   SYNTAX         String
   ACCESS         read-write
   STATUS         mandatory
   DESCRIPTION    ""
   REFERENCE      "IBMPSG_WarrantyExpirationEvent.description"
::= { iBMPSGWarrantyExpirationEventBindings 5 }

iBMPSGWarrantyExpirationEventTimeStamp OBJECT-TYPE
   SYNTAX         Datetime
   ACCESS         read-write
   STATUS         mandatory
   DESCRIPTION    ""
   REFERENCE      "IBMPSG_WarrantyExpirationEvent.TimeStamp"
::= { iBMPSGWarrantyExpirationEventBindings 6 }

iBMPSGRedundantNetworkAdapterEvent TRAP-TYPE
   ENTERPRISE     umservices
   VARIABLES    {
      iBMPSGRedundantNetworkAdapterEventIdentifier,
      iBMPSGRedundantNetworkAdapterEventSourceObjectPath,
      iBMPSGRedundantNetworkAdapterEventTargetObjectPath,
      iBMPSGRedundantNetworkAdapterEventSeverity,
      iBMPSGRedundantNetworkAdapterEventdescription,
      iBMPSGRedundantNetworkAdapterEventTimeStamp
   }
::= 15

iBMPSGRedundantNetworkAdapterEventBindings OBJECT IDENTIFIER ::= { ibmpsgEvent 15 }

iBMPSGRedundantNetworkAdapterEventIdentifier OBJECT-TYPE
   SYNTAX         String
   ACCESS         read-write
   STATUS         mandatory
   DESCRIPTION    ""
::= { iBMPSGRedundantNetworkAdapterEventBindings 1 }

iBMPSGRedundantNetworkAdapterEventSourceObjectPath OBJECT-TYPE
   SYNTAX         String
   ACCESS         read-write
   STATUS         mandatory
   DESCRIPTION    ""
::= { iBMPSGRedundantNetworkAdapterEventBindings 2 }

iBMPSGRedundantNetworkAdapterEventTargetObjectPath OBJECT-TYPE
   SYNTAX         String
   ACCESS         read-write
   STATUS         mandatory
   DESCRIPTION    ""
::= { iBMPSGRedundantNetworkAdapterEventBindings 3 }

iBMPSGRedundantNetworkAdapterEventdescription OBJECT-TYPE
   SYNTAX         String
   ACCESS         read-write
   STATUS         mandatory
   DESCRIPTION    ""
::= { iBMPSGRedundantNetworkAdapterEventBindings 4 }

iBMPSGRedundantNetworkAdapterEventSeverity OBJECT-TYPE
   SYNTAX         Uint16
   ACCESS         read-write
   STATUS         mandatory
   DESCRIPTION    ""
::= { iBMPSGRedundantNetworkAdapterEventBindings 5 }

iBMPSGRedundantNetworkAdapterEventTimeStamp OBJECT-TYPE
   SYNTAX         Datetime
   ACCESS         read-write
   STATUS         mandatory
   DESCRIPTION    ""
::= { iBMPSGRedundantNetworkAdapterEventBindings 6 }

iBMPSGRedundantNetworkAdapterSwitchoverEvent TRAP-TYPE
   ENTERPRISE     umservices
   VARIABLES    {
      iBMPSGRedundantNetworkAdapterSwitchoverEventIdentifier,
      iBMPSGRedundantNetworkAdapterSwitchoverEventSourceObjectPath,
      iBMPSGRedundantNetworkAdapterSwitchoverEventTargetObjectPath,
      iBMPSGRedundantNetworkAdapterSwitchoverEventSeverity,
      iBMPSGRedundantNetworkAdapterSwitchoverEventdescription,
      iBMPSGRedundantNetworkAdapterSwitchoverEventTimeStamp
   }
::= 16

iBMPSGRedundantNetworkAdapterSwitchoverEventBindings OBJECT IDENTIFIER ::= { ibmpsgEvent 16 }

iBMPSGRedundantNetworkAdapterSwitchoverEventIdentifier OBJECT-TYPE
   SYNTAX         String
   ACCESS         read-write
   STATUS         mandatory
   DESCRIPTION    ""
::= { iBMPSGRedundantNetworkAdapterSwitchoverEventBindings 1 }

iBMPSGRedundantNetworkAdapterSwitchoverEventSourceObjectPath OBJECT-TYPE
   SYNTAX         String
   ACCESS         read-write
   STATUS         mandatory
   DESCRIPTION    ""
::= { iBMPSGRedundantNetworkAdapterSwitchoverEventBindings 2 }

iBMPSGRedundantNetworkAdapterSwitchoverEventTargetObjectPath OBJECT-TYPE
   SYNTAX         String
   ACCESS         read-write
   STATUS         mandatory
   DESCRIPTION    ""
::= { iBMPSGRedundantNetworkAdapterSwitchoverEventBindings 3 }

iBMPSGRedundantNetworkAdapterSwitchoverEventdescription OBJECT-TYPE
   SYNTAX         String
   ACCESS         read-write
   STATUS         mandatory
   DESCRIPTION    ""
::= { iBMPSGRedundantNetworkAdapterSwitchoverEventBindings 4 }

iBMPSGRedundantNetworkAdapterSwitchoverEventSeverity OBJECT-TYPE
   SYNTAX         Uint16
   ACCESS         read-write
   STATUS         mandatory
   DESCRIPTION    ""
::= { iBMPSGRedundantNetworkAdapterSwitchoverEventBindings 5 }

iBMPSGRedundantNetworkAdapterSwitchoverEventTimeStamp OBJECT-TYPE
   SYNTAX         Datetime
   ACCESS         read-write
   STATUS         mandatory
   DESCRIPTION    ""
::= { iBMPSGRedundantNetworkAdapterSwitchoverEventBindings 6 }

iBMPSGRedundantNetworkAdapterSwitchbackEvent TRAP-TYPE
   ENTERPRISE     umservices
   VARIABLES    {
      iBMPSGRedundantNetworkAdapterSwitchbackEventIdentifier,
      iBMPSGRedundantNetworkAdapterSwitchbackEventSourceObjectPath,
      iBMPSGRedundantNetworkAdapterSwitchbackEventTargetObjectPath,
      iBMPSGRedundantNetworkAdapterSwitchbackEventSeverity,
      iBMPSGRedundantNetworkAdapterSwitchbackEventdescription,
      iBMPSGRedundantNetworkAdapterSwitchbackEventTimeStamp
   }
::= 17

iBMPSGRedundantNetworkAdapterSwitchbackEventBindings OBJECT IDENTIFIER ::= { ibmpsgEvent 17 }

iBMPSGRedundantNetworkAdapterSwitchbackEventIdentifier OBJECT-TYPE
   SYNTAX         String
   ACCESS         read-write
   STATUS         mandatory
   DESCRIPTION    ""
::= { iBMPSGRedundantNetworkAdapterSwitchbackEventBindings 1 }

iBMPSGRedundantNetworkAdapterSwitchbackEventSourceObjectPath OBJECT-TYPE
   SYNTAX         String
   ACCESS         read-write
   STATUS         mandatory
   DESCRIPTION    ""
::= { iBMPSGRedundantNetworkAdapterSwitchbackEventBindings 2 }

iBMPSGRedundantNetworkAdapterSwitchbackEventTargetObjectPath OBJECT-TYPE
   SYNTAX         String
   ACCESS         read-write
   STATUS         mandatory
   DESCRIPTION    ""
::= { iBMPSGRedundantNetworkAdapterSwitchbackEventBindings 3 }

iBMPSGRedundantNetworkAdapterSwitchbackEventdescription OBJECT-TYPE
   SYNTAX         String
   ACCESS         read-write
   STATUS         mandatory
   DESCRIPTION    ""
::= { iBMPSGRedundantNetworkAdapterSwitchbackEventBindings 4 }

iBMPSGRedundantNetworkAdapterSwitchbackEventSeverity OBJECT-TYPE
   SYNTAX         Uint16
   ACCESS         read-write
   STATUS         mandatory
   DESCRIPTION    ""
::= { iBMPSGRedundantNetworkAdapterSwitchbackEventBindings 5 }

iBMPSGRedundantNetworkAdapterSwitchbackEventTimeStamp OBJECT-TYPE
   SYNTAX         Datetime
   ACCESS         read-write
   STATUS         mandatory
   DESCRIPTION    ""
::= { iBMPSGRedundantNetworkAdapterSwitchbackEventBindings 6 }

iBMPSGProcessorPFEvent TRAP-TYPE
   ENTERPRISE     umservices
   VARIABLES    {
      iBMPSGProcessorPFEventIdentifier,
      iBMPSGProcessorPFEventSourceObjectPath,
      iBMPSGProcessorPFEventTargetObjectPath,      
      iBMPSGProcessorPFEventSeverity,
      iBMPSGProcessorPFEventdescription,
      iBMPSGProcessorPFEventTimeStamp
   }
::= 18

iBMPSGProcessorPFEventBindings OBJECT IDENTIFIER ::= { ibmpsgEvent 18 }

iBMPSGProcessorPFEventIdentifier OBJECT-TYPE
   SYNTAX         String
   ACCESS         read-write
   STATUS         mandatory
   DESCRIPTION    ""
::= { iBMPSGProcessorPFEventBindings 1 }

iBMPSGProcessorPFEventSourceObjectPath OBJECT-TYPE
   SYNTAX         String
   ACCESS         read-write
   STATUS         mandatory
   DESCRIPTION    ""
::= { iBMPSGProcessorPFEventBindings 2 }

iBMPSGProcessorPFEventTargetObjectPath OBJECT-TYPE
   SYNTAX         String
   ACCESS         read-write
   STATUS         mandatory
   DESCRIPTION    ""
::= { iBMPSGProcessorPFEventBindings 3 }

iBMPSGProcessorPFEventSeverity OBJECT-TYPE
   SYNTAX         Uint16
   ACCESS         read-write
   STATUS         mandatory
   DESCRIPTION    ""
::= { iBMPSGProcessorPFEventBindings 4 }

iBMPSGProcessorPFEventdescription OBJECT-TYPE
   SYNTAX         String
   ACCESS         read-write
   STATUS         mandatory
   DESCRIPTION    ""
::= { iBMPSGProcessorPFEventBindings 5 }

iBMPSGProcessorPFEventTimeStamp OBJECT-TYPE
   SYNTAX         Datetime
   ACCESS         read-write
   STATUS         mandatory
   DESCRIPTION    ""
::= { iBMPSGProcessorPFEventBindings 6 }

iBMPSGMemoryPFEvent TRAP-TYPE
   ENTERPRISE     umservices
   VARIABLES    {
      iBMPSGMemoryPFEventIdentifier,
      iBMPSGMemoryPFEventSourceObjectPath,
      iBMPSGMemoryPFEventTargetObjectPath,
      iBMPSGMemoryPFEventSeverity,
      iBMPSGMemoryPFEventdescription,
      iBMPSGMemoryPFEventTimeStamp
   }
::= 19

iBMPSGMemoryPFEventBindings OBJECT IDENTIFIER ::= { ibmpsgEvent 19 }

iBMPSGMemoryPFEventIdentifier OBJECT-TYPE
   SYNTAX         String
   ACCESS         read-write
   STATUS         mandatory
   DESCRIPTION    ""
::= { iBMPSGMemoryPFEventBindings 1 }

iBMPSGMemoryPFEventSourceObjectPath OBJECT-TYPE
   SYNTAX         String
   ACCESS         read-write
   STATUS         mandatory
   DESCRIPTION    ""
::= { iBMPSGMemoryPFEventBindings 2 }

iBMPSGMemoryPFEventTargetObjectPath OBJECT-TYPE
   SYNTAX         String
   ACCESS         read-write
   STATUS         mandatory
   DESCRIPTION    ""
::= { iBMPSGMemoryPFEventBindings 3 }

iBMPSGMemoryPFEventSeverity OBJECT-TYPE
   SYNTAX         Uint16
   ACCESS         read-write
   STATUS         mandatory
   DESCRIPTION    ""
::= { iBMPSGMemoryPFEventBindings 4 }

iBMPSGMemoryPFEventdescription OBJECT-TYPE
   SYNTAX         String
   ACCESS         read-write
   STATUS         mandatory
   DESCRIPTION    ""
::= { iBMPSGMemoryPFEventBindings 5 }

iBMPSGMemoryPFEventTimeStamp OBJECT-TYPE
   SYNTAX         Datetime
   ACCESS         read-write
   STATUS         mandatory
   DESCRIPTION    ""
::= { iBMPSGMemoryPFEventBindings 6 }

iBMPSGPFAEvent TRAP-TYPE
   ENTERPRISE     umservices
   VARIABLES    {
      iBMPSGPFAEventIdentifier,
      iBMPSGPFAEventSourceObjectPath,
      iBMPSGPFAEventTargetObjectPath,
      iBMPSGPFAEventSeverity,
      iBMPSGPFAEventdescription,
      iBMPSGPFAEventTimeStamp
   }
::= 22

iBMPSGPFAEventBindings OBJECT IDENTIFIER ::= { ibmpsgEvent 22 }

iBMPSGPFAEventIdentifier OBJECT-TYPE
   SYNTAX         String
   ACCESS         read-write
   STATUS         mandatory
   DESCRIPTION    ""
::= { iBMPSGPFAEventBindings 1 }

iBMPSGPFAEventSourceObjectPath OBJECT-TYPE
   SYNTAX         String
   ACCESS         read-write
   STATUS         mandatory
   DESCRIPTION    ""
::= { iBMPSGPFAEventBindings 2 }

iBMPSGPFAEventTargetObjectPath OBJECT-TYPE
   SYNTAX         String
   ACCESS         read-write
   STATUS         mandatory
   DESCRIPTION    ""
::= { iBMPSGPFAEventBindings 3 }

iBMPSGPFAEventSeverity OBJECT-TYPE
   SYNTAX         Uint16
   ACCESS         read-write
   STATUS         mandatory
   DESCRIPTION    ""
::= { iBMPSGPFAEventBindings 4 }

iBMPSGPFAEventdescription OBJECT-TYPE
   SYNTAX         String
   ACCESS         read-write
   STATUS         mandatory
   DESCRIPTION    ""
::= { iBMPSGPFAEventBindings 5 }

iBMPSGPFAEventTimeStamp OBJECT-TYPE
   SYNTAX         Datetime
   ACCESS         read-write
   STATUS         mandatory
   DESCRIPTION    ""
::= { iBMPSGPFAEventBindings 6 }

iBMPSGPowerSupplyEvent TRAP-TYPE
   ENTERPRISE     umservices
   VARIABLES    {
      iBMPSGPowerSupplyEventIdentifier,
      iBMPSGPowerSupplyEventSourceObjectPath,
      iBMPSGPowerSupplyEventTargetObjectPath,
      iBMPSGPowerSupplyEventSeverity,
      iBMPSGPowerSupplyEventdescription,
      iBMPSGPowerSupplyEventTimeStamp
   }
::= 23

iBMPSGPowerSupplyEventBindings OBJECT IDENTIFIER ::= { ibmpsgEvent 23 }

iBMPSGPowerSupplyEventIdentifier OBJECT-TYPE
   SYNTAX         String
   ACCESS         read-write
   STATUS         mandatory
   DESCRIPTION    ""
::= { iBMPSGPowerSupplyEventBindings 1 }

iBMPSGPowerSupplyEventSourceObjectPath OBJECT-TYPE
   SYNTAX         String
   ACCESS         read-write
   STATUS         mandatory
   DESCRIPTION    ""
::= { iBMPSGPowerSupplyEventBindings 2 }

iBMPSGPowerSupplyEventTargetObjectPath OBJECT-TYPE
   SYNTAX         String
   ACCESS         read-write
   STATUS         mandatory
   DESCRIPTION    ""
::= { iBMPSGPowerSupplyEventBindings 3 }

iBMPSGPowerSupplyEventSeverity OBJECT-TYPE
   SYNTAX         Uint16
   ACCESS         read-write
   STATUS         mandatory
   DESCRIPTION    ""
::= { iBMPSGPowerSupplyEventBindings 4 }

iBMPSGPowerSupplyEventdescription OBJECT-TYPE
   SYNTAX         String
   ACCESS         read-write
   STATUS         mandatory
   DESCRIPTION    ""
::= { iBMPSGPowerSupplyEventBindings 5 }

iBMPSGPowerSupplyEventTimeStamp OBJECT-TYPE
   SYNTAX         Datetime
   ACCESS         read-write
   STATUS         mandatory
   DESCRIPTION    ""
::= { iBMPSGPowerSupplyEventBindings 6 }

iBMPSGErrorLogEvent TRAP-TYPE
   ENTERPRISE     umservices
   VARIABLES    {
      iBMPSGErrorLogEventIdentifier,
      iBMPSGErrorLogEventSourceObjectPath,
      iBMPSGErrorLogEventTargetObjectPath,
      iBMPSGErrorLogEventSeverity,
      iBMPSGErrorLogEventdescription,
      iBMPSGErrorLogEventTimeStamp
   }
::= 24

iBMPSGErrorLogEventBindings OBJECT IDENTIFIER ::= { ibmpsgEvent 24 }

iBMPSGErrorLogEventIdentifier OBJECT-TYPE
   SYNTAX         String
   ACCESS         read-write
   STATUS         mandatory
   DESCRIPTION    ""
::= { iBMPSGErrorLogEventBindings 1 }

iBMPSGErrorLogEventSourceObjectPath OBJECT-TYPE
   SYNTAX         String
   ACCESS         read-write
   STATUS         mandatory
   DESCRIPTION    ""
::= { iBMPSGErrorLogEventBindings 2 }

iBMPSGErrorLogEventTargetObjectPath OBJECT-TYPE
   SYNTAX         String
   ACCESS         read-write
   STATUS         mandatory
   DESCRIPTION    ""
::= { iBMPSGErrorLogEventBindings 3 }

iBMPSGErrorLogEventSeverity OBJECT-TYPE
   SYNTAX         Uint16
   ACCESS         read-write
   STATUS         mandatory
   DESCRIPTION    ""
::= { iBMPSGErrorLogEventBindings 4 }

iBMPSGErrorLogEventdescription OBJECT-TYPE
   SYNTAX         String
   ACCESS         read-write
   STATUS         mandatory
   DESCRIPTION    ""
::= { iBMPSGErrorLogEventBindings 5 }

iBMPSGErrorLogEventTimeStamp OBJECT-TYPE
   SYNTAX         Datetime
   ACCESS         read-write
   STATUS         mandatory
   DESCRIPTION    ""
::= { iBMPSGErrorLogEventBindings 6 }

iBMPSGRemoteLoginEvent TRAP-TYPE
   ENTERPRISE     umservices
   VARIABLES    {
      iBMPSGRemoteLoginEventIdentifier,
      iBMPSGRemoteLoginEventSourceObjectPath,
      iBMPSGRemoteLoginEventTargetObjectPath,
      iBMPSGRemoteLoginEventSeverity,
      iBMPSGRemoteLoginEventdescription,
      iBMPSGRemoteLoginEventTimeStamp
   }
::= 25

iBMPSGRemoteLoginEventBindings OBJECT IDENTIFIER ::= { ibmpsgEvent 25 }

iBMPSGRemoteLoginEventIdentifier OBJECT-TYPE
   SYNTAX         String
   ACCESS         read-write
   STATUS         mandatory
   DESCRIPTION    ""
::= { iBMPSGRemoteLoginEventBindings 1 }

iBMPSGRemoteLoginEventSourceObjectPath OBJECT-TYPE
   SYNTAX         String
   ACCESS         read-write
   STATUS         mandatory
   DESCRIPTION    ""
::= { iBMPSGRemoteLoginEventBindings 2 }

iBMPSGRemoteLoginEventTargetObjectPath OBJECT-TYPE
   SYNTAX         String
   ACCESS         read-write
   STATUS         mandatory
   DESCRIPTION    ""
::= { iBMPSGRemoteLoginEventBindings 3 }

iBMPSGRemoteLoginEventSeverity OBJECT-TYPE
   SYNTAX         Uint16
   ACCESS         read-write
   STATUS         mandatory
   DESCRIPTION    ""
::= { iBMPSGRemoteLoginEventBindings 4 }

iBMPSGRemoteLoginEventdescription OBJECT-TYPE
   SYNTAX         String
   ACCESS         read-write
   STATUS         mandatory
   DESCRIPTION    ""
::= { iBMPSGRemoteLoginEventBindings 5 }

iBMPSGRemoteLoginEventTimeStamp OBJECT-TYPE
   SYNTAX         Datetime
   ACCESS         read-write
   STATUS         mandatory
   DESCRIPTION    ""
::= { iBMPSGRemoteLoginEventBindings 6 }
END
