-- ********************************************************************
-- RITTAL GmbH & Co. KG, Herborn
-- CMC-III-MIB Version 1.1
-- CMC-III-PU - 7030.000, 7030.010, 7030.020
--
-- Management Information Base for SNMP Network Management
--
-- Copyright 2011 Rittal Herborn.
-- All Rights Reserved.
--
-- The information in this document is subject to change without notice.
-- Refer to document "AGB-Software-Rittal.pdf"
--
-- ********************************************************************
-- File   : $RCSfile: $
-- Rev.   : $Revision: $
-- Date   : $Date: $
-- Author : $Author: $
-- Id     : $Id: $
-- ********************************************************************

RITTAL-CMC-III-PRODUCTS-MIB DEFINITIONS ::= BEGIN

IMPORTS
        MODULE-IDENTITY
    FROM         SNMPv2-SMI
        cmcIII
    FROM         RITTAL-CMC-III-MIB;


cmcIIIProducts   MODULE-IDENTITY
    LAST-UPDATED "201205250000Z"
    ORGANIZATION "RITTAL GmbH & Co. KG"
    CONTACT-INFO "www.rittal.de
    
                  RITTAL GmbH & Co. KG
                  Forschung & Entwicklung
                  Auf dem Stuetzelberg
                  D-35745 Herborn
                  Germany, Europe

                  +49(0)2772 5050
                  info@rittal.de" 
    DESCRIPTION  "The MIB module for representing cmcIII SNMP agent product entities"
    REVISION     "201109010000Z"
    DESCRIPTION  "Initial Version of cmcIII MIB."
--  ::=          { iso(1) org(3) dod(6) internet(1) private(4) enterprises(1) rittal(2606) cmcIII(7) }
    ::=          { cmcIII 7 }

-- ********************************************************************

-- rittal                          OBJECT IDENTIFIER ::= { enterprises       2606 }
--   cmcIII                        OBJECT IDENTIFIER ::= {   rittal             7 }
--     cmcIIIProducts              OBJECT IDENTIFIER ::= {     cmcIII           7 }
         cmcIIIProductUnit         OBJECT IDENTIFIER ::= {       cmcIIIProducts 1 }
         cmcIIIProductPort         OBJECT IDENTIFIER ::= {       cmcIIIProducts 2 }
         cmcIIIProductPowerSupply  OBJECT IDENTIFIER ::= {       cmcIIIProducts 3 }
         cmcIIIProductChassis      OBJECT IDENTIFIER ::= {       cmcIIIProducts 4 }
         cmcIIIProductSensor       OBJECT IDENTIFIER ::= {       cmcIIIProducts 5 }

-- ********************************************************************

    cmcIIIProductUnitUnknown               OBJECT IDENTIFIER ::= { cmcIIIProductUnit     1 }
    cmcIIIProductUnitPUIII                 OBJECT IDENTIFIER ::= { cmcIIIProductUnit     2 }
    cmcIIIProductUnitCompact               OBJECT IDENTIFIER ::= { cmcIIIProductUnit     3 }
    cmcIIIProductUnitLCP                   OBJECT IDENTIFIER ::= { cmcIIIProductUnit     4 }

    cmcIIIProductPortUnknown               OBJECT IDENTIFIER ::= { cmcIIIProductPort     1 }
    cmcIIIProductPortLoopback              OBJECT IDENTIFIER ::= { cmcIIIProductPort     2 }
    cmcIIIProductPortCanBus                OBJECT IDENTIFIER ::= { cmcIIIProductPort     3 }
    cmcIIIProductPortEthernet              OBJECT IDENTIFIER ::= { cmcIIIProductPort     4 }
    cmcIIIProductPortVirtualCanBus         OBJECT IDENTIFIER ::= { cmcIIIProductPort     5 }

    cmcIIIProductPowerSupplyUnknown        OBJECT IDENTIFIER ::= { cmcIIIProductPowerSupply      1 }
    cmcIIIProductPowerSupplyAcAdapter      OBJECT IDENTIFIER ::= { cmcIIIProductPowerSupply      2 }
    cmcIIIProductPowerSupplyTerminalStrip  OBJECT IDENTIFIER ::= { cmcIIIProductPowerSupply      3 }
    cmcIIIProductPowerSupplyPOE            OBJECT IDENTIFIER ::= { cmcIIIProductPowerSupply      4 }
    cmcIIIProductPowerSupplyUSB            OBJECT IDENTIFIER ::= { cmcIIIProductPowerSupply      5 }

    cmcIIIProductChassisGateSensorUnknown  OBJECT IDENTIFIER ::= { cmcIIIProductChassis   256 } -- 0x0100
    cmcIIIProductChassisGateLock           OBJECT IDENTIFIER ::= { cmcIIIProductChassis   512 } -- 0x0200
    cmcIIIProductChassisTemperature        OBJECT IDENTIFIER ::= { cmcIIIProductChassis   768 } -- 0x0300
    cmcIIIProductChassisTempHumi           OBJECT IDENTIFIER ::= { cmcIIIProductChassis  1024 } -- 0x0400
    cmcIIIProductChassisVandalism          OBJECT IDENTIFIER ::= { cmcIIIProductChassis  1280 } -- 0x0500
    cmcIIIProductChassisPressure           OBJECT IDENTIFIER ::= { cmcIIIProductChassis  1536 } -- 0x0600
    cmcIIIProductChassisAccess             OBJECT IDENTIFIER ::= { cmcIIIProductChassis  1792 } -- 0x0700
    cmcIIIProductChassisIOInput            OBJECT IDENTIFIER ::= { cmcIIIProductChassis  2048 } -- 0x0800
    cmcIIIProductChassisGateUnit-Cfg1      OBJECT IDENTIFIER ::= { cmcIIIProductChassis  2304 } -- 0x0900
    cmcIIIProductChassisGateUnit-Cfg2      OBJECT IDENTIFIER ::= { cmcIIIProductChassis  2305 } -- 0x0901	
    cmcIIIProductChassisGateUnit-Cfg3      OBJECT IDENTIFIER ::= { cmcIIIProductChassis  2306 } -- 0x0902
    cmcIIIProductChassisGateUnit-Cfg4      OBJECT IDENTIFIER ::= { cmcIIIProductChassis  2307 } -- 0x0903
    cmcIIIProductChassisPowerOld           OBJECT IDENTIFIER ::= { cmcIIIProductChassis  2560 } -- 0x0A00
	cmcIIIProductChassisPower              OBJECT IDENTIFIER ::= { cmcIIIProductChassis  3584 } -- 0x0E00
    cmcIIIProductChassisUniInput           OBJECT IDENTIFIER ::= { cmcIIIProductChassis  3328 } -- 0x0D00
	cmcIIIProductChassisLCP                OBJECT IDENTIFIER ::= { cmcIIIProductChassis  8192 } -- 0x2000
	cmcIIIProductChassisPSM-M16            OBJECT IDENTIFIER ::= { cmcIIIProductChassis 12288 } -- 0x3000
	cmcIIIProductChassisPSM-M32            OBJECT IDENTIFIER ::= { cmcIIIProductChassis 12544 } -- 0x3100
	cmcIIIProductChassisPSM-MID-M16        OBJECT IDENTIFIER ::= { cmcIIIProductChassis 13312 } -- 0x3400
	cmcIIIProductChassisPSM-MID-M32        OBJECT IDENTIFIER ::= { cmcIIIProductChassis 13568 } -- 0x3500	
    cmcIIIProductChassisInternal           OBJECT IDENTIFIER ::= { cmcIIIProductChassis 32768 } -- 0x8000
    cmcIIIProductChassisVirtualTwoLevel    OBJECT IDENTIFIER ::= { cmcIIIProductChassis 61440 } -- 0xF000
    cmcIIIProductChassisVirtualAccess      OBJECT IDENTIFIER ::= { cmcIIIProductChassis 61696 } -- 0xF100
    cmcIIIProductChassisGateSensorAccess   OBJECT IDENTIFIER ::= { cmcIIIProductChassis   273 } -- 0x0111
    cmcIIIProductChassisGateSensorMotion   OBJECT IDENTIFIER ::= { cmcIIIProductChassis   277 } -- 0x0115
    cmcIIIProductChassisGateSensorSmoke    OBJECT IDENTIFIER ::= { cmcIIIProductChassis   279 } -- 0x0117
    cmcIIIProductChassisGateSensorAirflow  OBJECT IDENTIFIER ::= { cmcIIIProductChassis   281 } -- 0x0119
    cmcIIIProductChassisGateSensorInputNO  OBJECT IDENTIFIER ::= { cmcIIIProductChassis   289 } -- 0x0121
    cmcIIIProductChassisGateSensorInputNC  OBJECT IDENTIFIER ::= { cmcIIIProductChassis   290 } -- 0x0122
    cmcIIIProductChassisGateSensorVoltage  OBJECT IDENTIFIER ::= { cmcIIIProductChassis   297 } -- 0x0129
    cmcIIIProductChassisGateSensorTemp     OBJECT IDENTIFIER ::= { cmcIIIProductChassis   305 } -- 0x0131
    cmcIIIProductChassisGateSensor4to20mA  OBJECT IDENTIFIER ::= { cmcIIIProductChassis   307 } -- 0x0133
    cmcIIIProductChassisGateSensorFireError  OBJECT IDENTIFIER ::= { cmcIIIProductChassis 337 } -- 0x0151
    cmcIIIProductChassisGateSensorFirePre  OBJECT IDENTIFIER ::= { cmcIIIProductChassis   338 } -- 0x0152
    cmcIIIProductChassisGateSensorFireMain OBJECT IDENTIFIER ::= { cmcIIIProductChassis   339 } -- 0x0153
    cmcIIIProductChassisGateSensorLeakage  OBJECT IDENTIFIER ::= { cmcIIIProductChassis   345 } -- 0x0159
    cmcIIIProductChassisGateSensorOutput   OBJECT IDENTIFIER ::= { cmcIIIProductChassis   401 } -- 0x0191
    cmcIIIProductChassisGateSensorDoorMag  OBJECT IDENTIFIER ::= { cmcIIIProductChassis   402 } -- 0x0192


END
