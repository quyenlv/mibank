-----------------------------------------------------------------------
--  Danware Data A/S
--  Copyright © Danware Data A/S 2001.  All Rights Reserved.
--
--  NetOp Remote control
--  File: DANWARE.MIB
--
--  SNMP MIB file for NetOp Remote Control
--  OID 1.3.6.1.4.1.8116
-----------------------------------------------------------------------

         DANWARE-MIB DEFINITIONS ::= BEGIN

         IMPORTS
                 enterprises
                         FROM RFC1155-SMI
                  OBJECT-TYPE
                         FROM RFC-1212
                   TRAP-TYPE
                         FROM RFC-1215
                 DisplayString
                         FROM RFC1213-MIB;

         danware         OBJECT IDENTIFIER ::= { enterprises 8116 }
         netop           OBJECT IDENTIFIER ::= { danware 2 }
         netopEvent           OBJECT IDENTIFIER ::= { netop 6 }

-----------------------------------------------------------------------
-- NetOp MIB definitions:
-----------------------------------------------------------------------

         netopManufacturer OBJECT-TYPE
             SYNTAX  DisplayString
             ACCESS  read-only
             STATUS  mandatory
             DESCRIPTION
                     "The name of the netop's manufacturer."
             ::= { netop 1 }

         netopProducts OBJECT-TYPE
             SYNTAX  INTEGER  {
                         unknown(0),
                         guest(1),
                         teacher(10),
                         host(20),
                         nameserver(21),
                         gateway(22),
                         logserver(23),
                         accessserver(24),
                         classserver(25),
                         student(30)
                     }
             ACCESS  read-only
             STATUS  mandatory
             DESCRIPTION
                     "Type of installed NetOp products."
             ::= { netop 2 }

         netopVersionNumber OBJECT-TYPE
             SYNTAX  DisplayString
             ACCESS  read-only
             STATUS  mandatory
             DESCRIPTION
                     "The NetOp product version info."
             ::= { netop 3 }

         netopStatus OBJECT-TYPE
             SYNTAX  DisplayString
             ACCESS  read-only
             STATUS  mandatory
             DESCRIPTION
                     "The NetOp product status information."
             ::= { netop 4 }

-----------------------------------------------------------------------
-- NetOp Trap definitions:
-----------------------------------------------------------------------

         netopCallHost TRAP-TYPE
             ENTERPRISE  netopEvent
             DESCRIPTION "A Netop Remote control Event"
             ::= 0

         netopHangupHost TRAP-TYPE
             ENTERPRISE  netopEvent
             DESCRIPTION "A Netop Remote control Event"
             ::= 1

         netopStartHelp TRAP-TYPE
             ENTERPRISE  netopEvent
             DESCRIPTION "A Netop Remote control Event"
             ::= 2

         netopStopHelp TRAP-TYPE
             ENTERPRISE  netopEvent
             DESCRIPTION "A Netop Remote control Event"
             ::= 3

         netopHelpDefined TRAP-TYPE
             ENTERPRISE  netopEvent
             DESCRIPTION "A Netop Remote control Event"
             --#SEVERITY INFORMATION
             ::= 4

         netopHelpDeleted TRAP-TYPE
             ENTERPRISE  netopEvent
             DESCRIPTION "A Netop Remote control Event"
             --#SEVERITY INFORMATION
             ::= 5

         netopHelpReqReceived TRAP-TYPE
             ENTERPRISE  netopEvent
             DESCRIPTION "A Netop Remote control Event"
             ::= 6

         netopHelpReqCancel TRAP-TYPE
             ENTERPRISE  netopEvent
             DESCRIPTION "A Netop Remote control Event"
             ::= 7

         netopSesRecStarted TRAP-TYPE
             ENTERPRISE  netopEvent
             DESCRIPTION "A Netop Remote control Event"
             ::= 8

         netopSesRecStop TRAP-TYPE
             ENTERPRISE  netopEvent
             DESCRIPTION "A Netop Remote control Event"
             ::= 9

         netopACLogin TRAP-TYPE
             ENTERPRISE  netopEvent
             DESCRIPTION "A Netop Remote control Event"
             --#SEVERITY WARNING
             ::= 10

         netopACLogOff  TRAP-TYPE
             ENTERPRISE  netopEvent
             DESCRIPTION "A Netop Remote control Event"
             --#SEVERITY WARNING
             ::= 11

         netopUnknown TRAP-TYPE
             ENTERPRISE  netopEvent
             DESCRIPTION "A Netop Remote control Event"
             ::= 12

         netopHostStarted TRAP-TYPE
             ENTERPRISE  netopEvent
             DESCRIPTION "A Netop Remote control Event"
             ::= 32

         netopHostStopped TRAP-TYPE
             ENTERPRISE  netopEvent
             DESCRIPTION "A Netop Remote control Event"
             ::= 33

         netopStartRemoteCtrl TRAP-TYPE
             ENTERPRISE  netopEvent
             DESCRIPTION "A Netop Remote control Event"
             ::= 34

         netopStopRemoteCtrl TRAP-TYPE
             ENTERPRISE  netopEvent
             DESCRIPTION "A Netop Remote control Event"
             ::= 35

         netopStartCallback TRAP-TYPE
             ENTERPRISE  netopEvent
             DESCRIPTION "A Netop Remote control Event"
             ::= 36

         netopHelpReqSent TRAP-TYPE
             ENTERPRISE  netopEvent
             DESCRIPTION "A Netop Remote control Event"
             ::= 37

         netopHstHelpReqCancel TRAP-TYPE
             ENTERPRISE  netopEvent
             DESCRIPTION "A Netop Remote control Event"
             ::= 38

         netopIndvSeqEnab TRAP-TYPE
             ENTERPRISE  netopEvent
             DESCRIPTION "A Netop Remote control Event"
             --#SEVERITY WARNING
             ::= 39

         netopIndvSeqDisab TRAP-TYPE
             ENTERPRISE  netopEvent
             DESCRIPTION "A Netop Remote control Event"
             --#SEVERITY WARNING
             ::= 40

         netopSecRoleAdded TRAP-TYPE
             ENTERPRISE  netopEvent
             DESCRIPTION "A Netop Remote control Event"
             --#SEVERITY WARNING
             ::= 41

         netopSecRoleDeleted TRAP-TYPE
             ENTERPRISE  netopEvent
             DESCRIPTION "A Netop Remote control Event"
             --#SEVERITY WARNING
             ::= 42

          netopSecRoleChange TRAP-TYPE
             ENTERPRISE  netopEvent
             DESCRIPTION "A Netop Remote control Event"
             --#SEVERITY WARNING
             ::= 43

         netopGstGrpAdded TRAP-TYPE
             ENTERPRISE  netopEvent
             DESCRIPTION "A Netop Remote control Event"
             --#SEVERITY INFORMATION
             ::= 44

         netopGstGrpDeleted TRAP-TYPE
             ENTERPRISE  netopEvent
             DESCRIPTION "A Netop Remote control Event"
             --#SEVERITY INFORMATION
             ::= 45

         netopGstGrpChange TRAP-TYPE
             ENTERPRISE  netopEvent
             DESCRIPTION "A Netop Remote control Event"
             --#SEVERITY INFORMATION
             ::= 46

         netopPWEnabled TRAP-TYPE
             ENTERPRISE  netopEvent
             DESCRIPTION "A Netop Remote control Event"
             --#SEVERITY WARNING
             ::= 47

         netopPWDisabled TRAP-TYPE
             ENTERPRISE  netopEvent
             DESCRIPTION "A Netop Remote control Event"
             --#SEVERITY WARNING
             ::= 48

         netopPWChange TRAP-TYPE
             ENTERPRISE  netopEvent
             DESCRIPTION "A Netop Remote control Event"
             --#SEVERITY WARNING
             ::= 49

         netopCallBEnabled TRAP-TYPE
             ENTERPRISE  netopEvent
             DESCRIPTION "A Netop Remote control Event"
             --#SEVERITY WARNING
             ::= 50

         netopCallBDisabled TRAP-TYPE
             ENTERPRISE  netopEvent
             DESCRIPTION "A Netop Remote control Event"
             --#SEVERITY WARNING
             ::= 51

         netopCallBChange TRAP-TYPE
             ENTERPRISE  netopEvent
             DESCRIPTION "A Netop Remote control Event"
             --#SEVERITY WARNING
             ::= 52

         netopConfAccEnab TRAP-TYPE
             ENTERPRISE  netopEvent
             DESCRIPTION "A Netop Remote control Event"
             --#SEVERITY WARNING
             ::= 53

          netopConfAccDisab TRAP-TYPE
             ENTERPRISE  netopEvent
             DESCRIPTION "A Netop Remote control Event"
             --#SEVERITY WARNING
             ::= 54

          netopGatewCallb TRAP-TYPE
             ENTERPRISE  netopEvent
             DESCRIPTION "A Netop Remote control Event"
             ::= 64

          netopGatewIndvDef TRAP-TYPE
             ENTERPRISE  netopEvent
             DESCRIPTION "A Netop Remote control Event"
             --#SEVERITY INFORMATION
             ::= 65

          netopGatewIndvDEL TRAP-TYPE
             ENTERPRISE  netopEvent
             DESCRIPTION "A Netop Remote control Event"
             --#SEVERITY INFORMATION
             ::= 66

          netopGatewGstAdded TRAP-TYPE
             ENTERPRISE  netopEvent
             DESCRIPTION "A Netop Remote control Event"
             --#SEVERITY INFORMATION
             ::= 67

          netopGatewGstDelete TRAP-TYPE
             ENTERPRISE  netopEvent
             DESCRIPTION "A Netop Remote control Event"
             --#SEVERITY INFORMATION
             ::= 68

          netopGatewGstChange TRAP-TYPE
             ENTERPRISE  netopEvent
             DESCRIPTION "A Netop Remote control Event"
             --#SEVERITY INFORMATION
             ::= 69

          netopGatewPWEnab TRAP-TYPE
             ENTERPRISE  netopEvent
             DESCRIPTION "A Netop Remote control Event"
             --#SEVERITY INFORMATION
             ::= 70

          netopGatewPWDisab TRAP-TYPE
             ENTERPRISE  netopEvent
             DESCRIPTION "A Netop Remote control Event"
             --#SEVERITY INFORMATION
             ::= 71

          netopGatewPWChange TRAP-TYPE
             ENTERPRISE  netopEvent
             DESCRIPTION "A Netop Remote control Event"
             --#SEVERITY INFORMATION
             ::= 72

          netopGatewCallbEnab TRAP-TYPE
             ENTERPRISE  netopEvent
             DESCRIPTION "A Netop Remote control Event"
             --#SEVERITY INFORMATION
             ::= 73

          netopGatewCallbDisab TRAP-TYPE
             ENTERPRISE  netopEvent
             DESCRIPTION "A Netop Remote control Event"
             --#SEVERITY INFORMATION
             ::= 74

          netopGatewCallbChange TRAP-TYPE
             ENTERPRISE  netopEvent
             DESCRIPTION "A Netop Remote control Event"
             --#SEVERITY INFORMATION
             ::= 75

          netopFileReceive TRAP-TYPE
             ENTERPRISE  netopEvent
             DESCRIPTION "A Netop Remote control Event"
             ::= 96

          netopFileSent TRAP-TYPE
             ENTERPRISE  netopEvent
             DESCRIPTION "A Netop Remote control Event"
             ::= 97

          netopBooted TRAP-TYPE
             ENTERPRISE  netopEvent
             DESCRIPTION "A Netop Remote control Event"
             ::= 98

          netopConectionLost TRAP-TYPE
             ENTERPRISE  netopEvent
             DESCRIPTION "A Netop Remote control Event"
             ::= 99

          netopPassWordRejected TRAP-TYPE
             ENTERPRISE  netopEvent
             DESCRIPTION "A Netop Remote control Event"
             --#SEVERITY MAJOR
            ::= 100

          netopConfAccessDenied TRAP-TYPE
             ENTERPRISE  netopEvent
             DESCRIPTION "A Netop Remote control Event"
             --#SEVERITY MAJOR
            ::= 101

          netopASPWRejected TRAP-TYPE
             ENTERPRISE  netopEvent
             DESCRIPTION "A Netop Remote control Event"
             --#SEVERITY MAJOR
             ::= 102

          netopASAdminChange TRAP-TYPE
             ENTERPRISE  netopEvent
             DESCRIPTION "A Netop Remote control Event"
             --#SEVERITY INFORMATION
             ::= 103

          netopEventLoggingFailed TRAP-TYPE
             ENTERPRISE  netopEvent
             DESCRIPTION "A Netop Remote control Event"
             ::= 112

          netopSNMPLoggingFailed TRAP-TYPE
             ENTERPRISE  netopEvent
             DESCRIPTION "A Netop Remote control Event"
             ::= 113

          netopRCStarted TRAP-TYPE
             ENTERPRISE  netopEvent
             DESCRIPTION "A Netop Remote control Event"
             ::= 114

          netopRCStopped TRAP-TYPE
             ENTERPRISE  netopEvent
             DESCRIPTION "A Netop Remote control Event"
             ::= 115

          netopFileTrStarted TRAP-TYPE
             ENTERPRISE  netopEvent
             DESCRIPTION "A Netop Remote control Event"
             ::= 116

          netopFileTrStopped TRAP-TYPE
             ENTERPRISE  netopEvent
             DESCRIPTION "A Netop Remote control Event"
             ::= 117

          netopGChatStarted TRAP-TYPE
             ENTERPRISE  netopEvent
             DESCRIPTION "A Netop Remote control Event"
             ::= 118

          netopGChatStopped TRAP-TYPE
             ENTERPRISE  netopEvent
             DESCRIPTION "A Netop Remote control Event"
             ::= 119

          netopGAudioStarted TRAP-TYPE
             ENTERPRISE  netopEvent
             DESCRIPTION "A Netop Remote control Event"
             ::= 120

          netopGAudioStopped TRAP-TYPE
             ENTERPRISE  netopEvent
             DESCRIPTION "A Netop Remote control Event"
             ::= 121

          netopClipReceived TRAP-TYPE
             ENTERPRISE  netopEvent
             DESCRIPTION "A Netop Remote control Event"
             ::= 122

          netopClipSent TRAP-TYPE
             ENTERPRISE  netopEvent
             DESCRIPTION "A Netop Remote control Event"
             ::= 123

          netopRrintReceived TRAP-TYPE
             ENTERPRISE  netopEvent
             DESCRIPTION "A Netop Remote control Event"
             ::= 124

          netopPrintSent TRAP-TYPE
             ENTERPRISE  netopEvent
             DESCRIPTION "A Netop Remote control Event"
             ::= 125

          netopCommProfileStart TRAP-TYPE
             ENTERPRISE  netopEvent
             DESCRIPTION "A Netop Remote control Event"
             ::= 126

          netopCommProfileStop TRAP-TYPE
             ENTERPRISE  netopEvent
             DESCRIPTION "A Netop Remote control Event"
             ::= 127

          netopLogLocalOn TRAP-TYPE
             ENTERPRISE  netopEvent
             DESCRIPTION "A Netop Remote control Event"
             --#SEVERITY INFORMATION
             ::= 128

          netopLogLocalOff TRAP-TYPE
             ENTERPRISE  netopEvent
             DESCRIPTION "A Netop Remote control Event"
             --#SEVERITY INFORMATION
             ::= 129

          netopLogLocalChange TRAP-TYPE
             ENTERPRISE  netopEvent
             DESCRIPTION "A Netop Remote control Event"
             --#SEVERITY INFORMATION
             ::= 130

          netopLogServerOn TRAP-TYPE
             ENTERPRISE  netopEvent
             DESCRIPTION "A Netop Remote control Event"
             --#SEVERITY INFORMATION
             ::= 131

         netopLogServerOff TRAP-TYPE
             ENTERPRISE  netopEvent
             DESCRIPTION "A Netop Remote control Event"
             --#SEVERITY INFORMATION
             ::= 132

         netopIsLogServer TRAP-TYPE
             ENTERPRISE  netopEvent
             DESCRIPTION "A Netop Remote control Event"
             --#SEVERITY INFORMATION
             ::= 133

         netopIsNotLogServer TRAP-TYPE
             ENTERPRISE  netopEvent
             DESCRIPTION "A Netop Remote control Event"
             --#SEVERITY INFORMATION
             ::= 134

         netopLogEventlogOn TRAP-TYPE
             ENTERPRISE  netopEvent
             DESCRIPTION "A Netop Remote control Event"
             --#SEVERITY INFORMATION
             ::= 135

         netopLogEventlogOff TRAP-TYPE
             ENTERPRISE  netopEvent
             DESCRIPTION "A Netop Remote control Event"
             --#SEVERITY INFORMATION
             ::= 136

         netopLogSNMPOn TRAP-TYPE
             ENTERPRISE  netopEvent
             DESCRIPTION "A Netop Remote control Event"
             --#SEVERITY INFORMATION
             ::= 137

         netopLogSNMPOff TRAP-TYPE
             ENTERPRISE  netopEvent
             DESCRIPTION "A Netop Remote control Event"
             --#SEVERITY INFORMATION
             ::= 138

         netopKbdLock TRAP-TYPE
             ENTERPRISE  netopEvent
             DESCRIPTION "A Netop Remote control Event"
             ::= 139

         netopKbdUnlock TRAP-TYPE
             ENTERPRISE  netopEvent
             DESCRIPTION "A Netop Remote control Event"
             ::= 140

         netopScrBlank TRAP-TYPE
             ENTERPRISE  netopEvent
             DESCRIPTION "A Netop Remote control Event"
             ::= 141

         netopScrUnblank TRAP-TYPE
             ENTERPRISE  netopEvent
             DESCRIPTION "A Netop Remote control Event"
             ::= 142

         netopLogoff TRAP-TYPE
             ENTERPRISE  netopEvent
             DESCRIPTION "A Netop Remote control Event"
             ::= 143

         netopGWLogin TRAP-TYPE
             ENTERPRISE  netopEvent
             DESCRIPTION "A Netop Remote control Event"
             ::= 144

         netopOptWaitStart TRAP-TYPE
             ENTERPRISE  netopEvent
             DESCRIPTION "A Netop Remote control Event"
             --#SEVERITY INFORMATION
             ::= 145

         netopOptLoadStar TRAP-TYPE
             ENTERPRISE  netopEvent
             DESCRIPTION "A Netop Remote control Event"
             --#SEVERITY INFORMATION
             ::= 146

         netopOptMinStart TRAP-TYPE
             ENTERPRISE  netopEvent
             DESCRIPTION "A Netop Remote control Event"
             --#SEVERITY INFORMATION
             ::= 147

         netopOptStealth TRAP-TYPE
             ENTERPRISE  netopEvent
             DESCRIPTION "A Netop Remote control Event"
             --#SEVERITY INFORMATION
             ::= 148

         netopOptMinConn TRAP-TYPE
             ENTERPRISE  netopEvent
             DESCRIPTION "A Netop Remote control Event"
             --#SEVERITY INFORMATION
             ::= 149

         netopOptOnTop TRAP-TYPE
             ENTERPRISE  netopEvent
             DESCRIPTION "A Netop Remote control Event"
             --#SEVERITY INFORMATION
             ::= 150

         netopOptShowFile TRAP-TYPE
             ENTERPRISE  netopEvent
             DESCRIPTION "A Netop Remote control Event"
             --#SEVERITY INFORMATION
             ::= 151

         netopOptKeepAlive TRAP-TYPE
             ENTERPRISE  netopEvent
             DESCRIPTION "A Netop Remote control Event"
             --#SEVERITY INFORMATION
             ::= 152

         netopOptBootHangUp TRAP-TYPE
             ENTERPRISE  netopEvent
             DESCRIPTION "A Netop Remote control Event"
             --#SEVERITY INFORMATION
             ::= 153

         netopOptLogOffHangUp TRAP-TYPE
             ENTERPRISE  netopEvent
             DESCRIPTION "A Netop Remote control Event"
             --#SEVERITY INFORMATION
             ::= 154

         netopOptNaming TRAP-TYPE
             ENTERPRISE  netopEvent
             DESCRIPTION "A Netop Remote control Event"
             --#SEVERITY INFORMATION
             ::= 155

         netopOptPublic TRAP-TYPE
             ENTERPRISE  netopEvent
             DESCRIPTION "A Netop Remote control Event"
             --#SEVERITY INFORMATION
             ::= 156

         netopOptNotification TRAP-TYPE
             ENTERPRISE  netopEvent
             DESCRIPTION "A Netop Remote control Event"
             --#SEVERITY INFORMATION
             ::= 157

         netopOptHlpDescr TRAP-TYPE
             ENTERPRISE  netopEvent
             DESCRIPTION "A Netop Remote control Event"
             --#SEVERITY INFORMATION
             ::= 158

         netopOptHlpProvid TRAP-TYPE
             ENTERPRISE  netopEvent
             DESCRIPTION "A Netop Remote control Event"
             --#SEVERITY INFORMATION
             ::= 159

         netopOptHlpComm TRAP-TYPE
             ENTERPRISE  netopEvent
             DESCRIPTION "A Netop Remote control Event"
             --#SEVERITY INFORMATION
             ::= 160

         netopOptHlpAdr TRAP-TYPE
             ENTERPRISE  netopEvent
             DESCRIPTION "A Netop Remote control Event"
             --#SEVERITY INFORMATION
             ::= 161

         netopOptHlpIcon TRAP-TYPE
             ENTERPRISE  netopEvent
             DESCRIPTION "A Netop Remote control Event"
             --#SEVERITY INFORMATION
             ::= 162

         netopOptAudDuplex TRAP-TYPE
             ENTERPRISE  netopEvent
             DESCRIPTION "A Netop Remote control Event"
             --#SEVERITY INFORMATION
             ::= 163

         netopOptAudSilence TRAP-TYPE
             ENTERPRISE  netopEvent
             DESCRIPTION "A Netop Remote control Event"
             --#SEVERITY INFORMATION
             ::= 164

         netopOptAudLineHold TRAP-TYPE
             ENTERPRISE  netopEvent
             DESCRIPTION "A Netop Remote control Event"
             --#SEVERITY INFORMATION
             ::= 165

         netopOptNNSChg TRAP-TYPE
             ENTERPRISE  netopEvent
             DESCRIPTION "A Netop Remote control Event"
             --#SEVERITY INFORMATION
             ::= 166

         netopMaintGuest TRAP-TYPE
             ENTERPRISE  netopEvent
             DESCRIPTION "A Netop Remote control Event"
             --#SEVERITY INFORMATION
             ::= 167

         netopMaintGW TRAP-TYPE
             ENTERPRISE  netopEvent
             DESCRIPTION "A Netop Remote control Event"
             --#SEVERITY INFORMATION
             ::= 168

         netopMaintOther TRAP-TYPE
             ENTERPRISE  netopEvent
             DESCRIPTION "A Netop Remote control Event"
             --#SEVERITY INFORMATION
             ::= 169

         netopMaintExit TRAP-TYPE
             ENTERPRISE  netopEvent
             DESCRIPTION "A Netop Remote control Event"
             --#SEVERITY INFORMATION
             ::= 170

         netopMaintProtect TRAP-TYPE
             ENTERPRISE  netopEvent
             DESCRIPTION "A Netop Remote control Event"
             --#SEVERITY INFORMATION
             ::= 171

         netopMaintPW TRAP-TYPE
             ENTERPRISE  netopEvent
             DESCRIPTION "A Netop Remote control Event"
             --#SEVERITY INFORMATION
             ::= 172

         netopAccessAllowance TRAP-TYPE
             ENTERPRISE  netopEvent
             DESCRIPTION "A Netop Remote control Event"
             --#SEVERITY INFORMATION
             ::= 173

         netopAccessMACIP TRAP-TYPE
             ENTERPRISE  netopEvent
             DESCRIPTION "A Netop Remote control Event"
             --#SEVERITY INFORMATION
             ::= 174

         netopAccessFTrans TRAP-TYPE
             ENTERPRISE  netopEvent
             DESCRIPTION "A Netop Remote control Event"
             --#SEVERITY INFORMATION
             ::= 175

         netopSSGroupIDChg TRAP-TYPE
             ENTERPRISE  netopEvent
             DESCRIPTION "A Netop Remote control Event"
             --#SEVERITY INFORMATION
             ::= 176

         netopPWRejectLimit TRAP-TYPE
             ENTERPRISE  netopEvent
             DESCRIPTION "A Netop Remote control Event"
             --#SEVERITY CRITICAL
             ::= 177

         netopNameServerStart TRAP-TYPE
             ENTERPRISE  netopEvent
             DESCRIPTION "A Netop Remote control Event"
             --#SEVERITY MAJOR
             ::= 178

         netopNameServerStop TRAP-TYPE
             ENTERPRISE  netopEvent
             DESCRIPTION "A Netop Remote control Event"
             --#SEVERITY CRITICAL
             ::= 179

         netopSecurityServerStart TRAP-TYPE
             ENTERPRISE  netopEvent
             DESCRIPTION "A Netop Remote control Event"
             --#SEVERITY MAJOR
             ::= 180

         netopSecurityServerStop TRAP-TYPE
             ENTERPRISE  netopEvent
             DESCRIPTION "A Netop Remote control Event"
             --#SEVERITY CRITICAL
             ::= 181

         netopGatewayStart TRAP-TYPE
             ENTERPRISE  netopEvent
             DESCRIPTION "A Netop Remote control Event"
             --#SEVERITY MAJOR
             ::= 182

         netopGatwayStop TRAP-TYPE
             ENTERPRISE  netopEvent
             DESCRIPTION "A Netop Remote control Event"
             --#SEVERITY CRITICAL
             ::= 183

         netopOptLockHangUp TRAP-TYPE
             ENTERPRISE  netopEvent
             DESCRIPTION "A Netop Remote control Event"
             --#SEVERITY INFORMATION
             ::= 184

         netopOptNothingHangUp TRAP-TYPE
             ENTERPRISE  netopEvent
             DESCRIPTION "A Netop Remote control Event"
             --#SEVERITY INFORMATION
             ::= 185

         netopOptUserName TRAP-TYPE
             ENTERPRISE  netopEvent
             DESCRIPTION "A Netop Remote control Event"
             --#SEVERITY INFORMATION
             ::= 186

         netopFMStarted TRAP-TYPE
             ENTERPRISE  netopEvent
             DESCRIPTION "A Netop Remote control Event"
             --#SEVERITY INFORMATION
             ::= 187

         netopFMStopped TRAP-TYPE
             ENTERPRISE  netopEvent
             DESCRIPTION "A Netop Remote control Event"
             --#SEVERITY INFORMATION
             ::= 188

         netopHChatStarted TRAP-TYPE
             ENTERPRISE  netopEvent
             DESCRIPTION "A Netop Remote control Event"
             --#SEVERITY INFORMATION
             ::= 189

         netopHChatStopped TRAP-TYPE
             ENTERPRISE  netopEvent
             DESCRIPTION "A Netop Remote control Event"
             --#SEVERITY INFORMATION
             ::= 190

         netopHAudioStarted TRAP-TYPE
             ENTERPRISE  netopEvent
             DESCRIPTION "A Netop Remote control Event"
             --#SEVERITY INFORMATION
             ::= 191

         netopHAudioStopped TRAP-TYPE
             ENTERPRISE  netopEvent
             DESCRIPTION "A Netop Remote control Event"
             --#SEVERITY INFORMATION
             ::= 192

         netopCommunicationStarted TRAP-TYPE
             ENTERPRISE  netopEvent
             DESCRIPTION "A Netop Remote control Event"
             --#SEVERITY INFORMATION
             ::= 193

         netopCommunicationStopped TRAP-TYPE
             ENTERPRISE  netopEvent
             DESCRIPTION "A Netop Remote control Event"
             --#SEVERITY INFORMATION
             ::= 194

         netopRunScript TRAP-TYPE
             ENTERPRISE  netopEvent
             DESCRIPTION "A Netop Remote control Event"
             --#SEVERITY INFORMATION
             ::= 195

         netopRunProgram TRAP-TYPE
             ENTERPRISE  netopEvent
             DESCRIPTION "A Netop Remote control Event"
             --#SEVERITY INFORMATION
             ::= 196

         netopExecuteCommand TRAP-TYPE
             ENTERPRISE  netopEvent
             DESCRIPTION "A Netop Remote control Event"
             --#SEVERITY INFORMATION
             ::= 197

         netopGatewGrpDefined TRAP-TYPE
             ENTERPRISE  netopEvent
             DESCRIPTION "A Netop Remote control Event"
             --#SEVERITY INFORMATION
             ::= 198

         netopGatewGrpDeleted TRAP-TYPE
             ENTERPRISE  netopEvent
             DESCRIPTION "A Netop Remote control Event"
             --#SEVERITY INFORMATION
             ::= 199

         netopGatewAccessAllowed TRAP-TYPE
             ENTERPRISE  netopEvent
             DESCRIPTION "A Netop Remote control Event"
             --#SEVERITY INFORMATION
             ::= 200

         netopGatewNNSGDIChanged TRAP-TYPE
             ENTERPRISE  netopEvent
             DESCRIPTION "A Netop Remote control Event"
             --#SEVERITY INFORMATION
             ::= 201

         netopAccessServerPWChanged TRAP-TYPE
             ENTERPRISE  netopEvent
             DESCRIPTION "A Netop Remote control Event"
             --#SEVERITY INFORMATION
             ::= 202

         netopInventoryReceived TRAP-TYPE
             ENTERPRISE  netopEvent
             DESCRIPTION "A Netop Remote control Event"
             --#SEVERITY INFORMATION
             ::= 203

         netopMessageSent TRAP-TYPE
             ENTERPRISE  netopEvent
             DESCRIPTION "A Netop Remote control Event"
             --#SEVERITY INFORMATION
             ::= 204

         netopInventorySent TRAP-TYPE
             ENTERPRISE  netopEvent
             DESCRIPTION "A Netop Remote control Event"
             --#SEVERITY INFORMATION
             ::= 205

         netopMessageReceived TRAP-TYPE
             ENTERPRISE  netopEvent
             DESCRIPTION "A Netop Remote control Event"
             --#SEVERITY INFORMATION
             ::= 206

         netopTimeoutLimitExeded TRAP-TYPE
             ENTERPRISE  netopEvent
             DESCRIPTION "A Netop Remote control Event"
             --#SEVERITY MAJOR
             ::= 207

         netopAuthenticatedUser TRAP-TYPE
             ENTERPRISE  netopEvent
             DESCRIPTION "A Netop Remote control Event"
             --#SEVERITY INFORMATION
             ::= 208

         netopGatewayPWRejected TRAP-TYPE
             ENTERPRISE  netopEvent
             DESCRIPTION "A Netop Remote control Event"
             --#SEVERITY MAJOR
             ::= 209

         netopWebUpdateCheck TRAP-TYPE
             ENTERPRISE  netopEvent
             DESCRIPTION "A Netop Remote control Event"
             --#SEVERITY INFORMATION
             ::= 210

         netopWebUpdateDownload TRAP-TYPE
             ENTERPRISE  netopEvent
             DESCRIPTION "A Netop Remote control Event"
             --#SEVERITY INFORMATION
             ::= 211

         netopWebUpdateInstall TRAP-TYPE
             ENTERPRISE  netopEvent
             DESCRIPTION "A Netop Remote control Event"
             --#SEVERITY INFORMATION
             ::= 212

         netopWebUpdateSuccess TRAP-TYPE
             ENTERPRISE  netopEvent
             DESCRIPTION "A Netop Remote control Event"
             --#SEVERITY INFORMATION
             ::= 213

         netopWebUpdateFailed TRAP-TYPE
             ENTERPRISE  netopEvent
             DESCRIPTION "A Netop Remote control Event"
             --#SEVERITY INFORMATION
             ::= 214

         netopClassServerStart TRAP-TYPE
             ENTERPRISE  netopEvent
             DESCRIPTION "A Netop Remote control Event"
             --#SEVERITY MAJOR
             ::= 215

         netopClassServerStop TRAP-TYPE
             ENTERPRISE  netopEvent
             DESCRIPTION "A Netop Remote control Event"
             --#SEVERITY CRITICAL
             ::= 216

         netopOptMultiGuest TRAP-TYPE
             ENTERPRISE  netopEvent
             DESCRIPTION "A Netop Remote control Event"
             --#SEVERITY INFORMATION
             ::= 217

         netopRemoteMgmStarted TRAP-TYPE
             ENTERPRISE  netopEvent
             DESCRIPTION "A Netop Remote control Event"
             --#SEVERITY INFORMATION
             ::= 218

         netopRemoteMgmStopped TRAP-TYPE
             ENTERPRISE  netopEvent
             DESCRIPTION "A Netop Remote control Event"
             --#SEVERITY INFORMATION
             ::= 219


         netopRemoteMgmStarted2 TRAP-TYPE
             ENTERPRISE  netopEvent
             DESCRIPTION "A Netop Remote control Event"
             --#SEVERITY INFORMATION
             ::= 220

         netopRemoteMgmStopped2 TRAP-TYPE
             ENTERPRISE  netopEvent
             DESCRIPTION "A Netop Remote control Event"
             --#SEVERITY INFORMATION
             ::= 221


-----------------------------------------------------------------------
-- End of NetOp definitions
-----------------------------------------------------------------------

        END
