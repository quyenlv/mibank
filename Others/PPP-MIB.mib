PPP-MIB DEFINITIONS ::= BEGIN


-- Copyright (C) 1997 Intel Corporation. All rights reserved.
--
-- ScaNet Private PPP MIB, 26-03-1997
--
-- This MIB provides objects for PPP.
--
-- Change History:
-- <date> <change>
--

          IMPORTS
          Counter
                      FROM RFC1155-SMI
            scanet                                              FROM SCANET-MIB
            OBJECT-TYPE                                 FROM RFC-1212;


        ppp     OBJECT IDENTIFIER ::= { scanet 43 }
        pppLink OBJECT IDENTIFIER ::= { ppp 1}


PppProtocolState ::= INTEGER {
         initial(1),
         starting(2),
         closed(3),
         stopped(4),
         closing(5),
         stopping(6),
         reqsent(7),
         ackrcvd(8),
         acksent(9),
         opened(10),
         disabled(11)
        }


pppLinkProtoStateTable OBJECT-TYPE
    SYNTAX SEQUENCE OF PppLinkProtoStateEntry
    ACCESS not-accessible
    STATUS mandatory
    DESCRIPTION "Table containing protocol states and link type
    (standard, multilink slave or multilink master)."
    ::= { pppLink 1 }

pppLinkProtoStateEntry OBJECT-TYPE
    SYNTAX PppLinkProtoStateEntry
    ACCESS not-accessible
    STATUS mandatory
    DESCRIPTION ""
    INDEX { pppLinkProtoStateIfIndex}
    ::= { pppLinkProtoStateTable 1 }

PppLinkProtoStateEntry ::= SEQUENCE {
        pppLinkProtoStateIfIndex
        INTEGER,
        pppLinkProtoStatePppLinkType
        INTEGER,
        pppLinkProtoStateLcpState
        INTEGER,
        pppLinkProtoStateIpcpState
        INTEGER,
        pppLinkProtoStateIpxcpState
        INTEGER,
         pppLinkProtoStateBcpState
        INTEGER,
        pppLinkProtoStateCcpState
        INTEGER,
        pppLinkProtoStateEcpState
        INTEGER
}

pppLinkProtoStateIfIndex OBJECT-TYPE
    SYNTAX INTEGER
    ACCESS read-only
    STATUS mandatory
    DESCRIPTION "Interface index."
    ::= {  pppLinkProtoStateEntry 1 }

pppLinkProtoStatePppLinkType OBJECT-TYPE
    SYNTAX INTEGER {
        standard(1), multilinkmaster(2), multilinkslave(3) }
    ACCESS read-only
    STATUS mandatory
    DESCRIPTION "PPP Link type."
    ::= {  pppLinkProtoStateEntry 2 }

pppLinkProtoStateLcpState OBJECT-TYPE
    SYNTAX PppProtocolState
    ACCESS read-only
    STATUS mandatory
    DESCRIPTION "LCP (Link Control Protocol) state."
    ::= {  pppLinkProtoStateEntry 3 }

pppLinkProtoStateIpcpState OBJECT-TYPE
    SYNTAX PppProtocolState
    ACCESS read-only
    STATUS mandatory
    DESCRIPTION "IPCP (Ip Control Protocol) state. Not used for multilink
    slave links (pppLinkProtoStatePppLinkType = multilinkslave)."
    ::= {  pppLinkProtoStateEntry 4 }

pppLinkProtoStateIpxcpState OBJECT-TYPE
    SYNTAX PppProtocolState
    ACCESS read-only
    STATUS mandatory
    DESCRIPTION "IPXCP (Ipx Control Protocol) state. Not used for multilink
    slave links (pppLinkProtoStatePppLinkType = multilinkslave)."
    ::= {  pppLinkProtoStateEntry 5 }

pppLinkProtoStateBcpState OBJECT-TYPE
    SYNTAX PppProtocolState
    ACCESS read-only
    STATUS mandatory
    DESCRIPTION "BCP (Bridging Control Protocol) state. Not used for multilink
    slave links (pppLinkProtoStatePppLinkType = multilinkslave)."
    ::= {  pppLinkProtoStateEntry 6 }

pppLinkProtoStateCcpState OBJECT-TYPE
    SYNTAX PppProtocolState
    ACCESS read-only
    STATUS mandatory
    DESCRIPTION "CCP (Compression Control Protocol) state. Not used for multilink
    slave links (pppLinkProtoStatePppLinkType = multilinkslave)."
    ::= {  pppLinkProtoStateEntry 7 }

pppLinkProtoStateEcpState OBJECT-TYPE
    SYNTAX PppProtocolState
    ACCESS read-only
    STATUS mandatory
    DESCRIPTION "ECP (Encryption Control Protocol) state. Not used for multilink
    slave links (pppLinkProtoStatePppLinkType = multilinkslave)."
    ::= {  pppLinkProtoStateEntry 8 }

pppLinkLcpTable OBJECT-TYPE
    SYNTAX SEQUENCE OF PppLinkLcpEntry
    ACCESS not-accessible
    STATUS mandatory
    DESCRIPTION "LCP (Link Control Protocol) information table. Values are
    first valid when protocol has state OPENED. Not used for multilink
    master links (pppLinkProtoStatePppLinkType = multilinkmaster)."
    ::= { pppLink 2 }

pppLinkLcpEntry OBJECT-TYPE
    SYNTAX PppLinkLcpEntry
    ACCESS not-accessible
    STATUS mandatory
    DESCRIPTION ""
    INDEX { pppLinkLcpIfIndex}
    ::= { pppLinkLcpTable 1 }

PppLinkLcpEntry ::= SEQUENCE {
    pppLinkLcpIfIndex
    INTEGER,
    pppLinkLcpMRUInc
    INTEGER,
    pppLinkLcpMRUOut
    INTEGER,
    pppLinkLcpACCMapInc
    INTEGER,
    pppLinkLcpACCMapOut
    INTEGER,
    pppLinkProtocolCompressionInc
    INTEGER,
    pppLinkProtocolCompressionOut
    INTEGER,
    pppLinkACCompressionInc
    INTEGER,
    pppLinkACCompressionOut
    INTEGER,
    pppLinkMagicNumberInc
    INTEGER,
    pppLinkMagicNumberOut
    INTEGER
}

pppLinkLcpIfIndex OBJECT-TYPE
    SYNTAX INTEGER
    ACCESS read-only
    STATUS mandatory
    DESCRIPTION "Interface index"
    ::= { pppLinkLcpEntry 1 }

pppLinkLcpMRUInc OBJECT-TYPE
    SYNTAX INTEGER
    ACCESS read-only
    STATUS mandatory
    DESCRIPTION "Local Maximum Receive Unit"
    ::= { pppLinkLcpEntry 2 }

pppLinkLcpMRUOut OBJECT-TYPE
    SYNTAX INTEGER
    ACCESS read-only
    STATUS mandatory
    DESCRIPTION "Remote Maximum Receive Unit"
    ::= { pppLinkLcpEntry 3 }

pppLinkLcpACCMapInc OBJECT-TYPE
    SYNTAX INTEGER
    ACCESS read-only
    STATUS mandatory
    DESCRIPTION "Local to peer ACCM map"
    ::= { pppLinkLcpEntry 4 }

pppLinkLcpACCMapOut OBJECT-TYPE
    SYNTAX INTEGER
    ACCESS read-only
    STATUS mandatory
    DESCRIPTION "Peer to local ACCM map"
    ::= { pppLinkLcpEntry 5 }

pppLinkProtocolCompressionInc OBJECT-TYPE
    SYNTAX INTEGER {
        disabled(1),
        enabled(2)
        }
    ACCESS read-only
    STATUS mandatory
    DESCRIPTION "Local to remote protocol field compression"
    ::= { pppLinkLcpEntry 6 }

pppLinkProtocolCompressionOut OBJECT-TYPE
    SYNTAX INTEGER {
        disabled(1),
        enabled(2)
        }
    ACCESS read-only
    STATUS mandatory
    DESCRIPTION "Remote to local protocol field compression"
    ::= { pppLinkLcpEntry 7 }

pppLinkACCompressionInc OBJECT-TYPE
    SYNTAX INTEGER {
        disabled(1),
        enabled(2)
        }
    ACCESS read-only
    STATUS mandatory
    DESCRIPTION "Local to remote address and control field compression"
    ::= { pppLinkLcpEntry 8 }

pppLinkACCompressionOut OBJECT-TYPE
    SYNTAX INTEGER {
        disabled(1),
        enabled(2)
        }
    ACCESS read-only
    STATUS mandatory
    DESCRIPTION "Remote to local address and control field compression"
    ::= { pppLinkLcpEntry 9 }

pppLinkMagicNumberInc OBJECT-TYPE
    SYNTAX INTEGER
    ACCESS read-only
    STATUS mandatory
    DESCRIPTION "Local magic number"
    ::= { pppLinkLcpEntry 10 }

pppLinkMagicNumberOut OBJECT-TYPE
    SYNTAX INTEGER
    ACCESS read-only
    STATUS mandatory
    DESCRIPTION "Remote magic number"
    ::= { pppLinkLcpEntry 11 }

pppLinkBcpTable OBJECT-TYPE
    SYNTAX SEQUENCE OF PppLinkBcpEntry
    ACCESS not-accessible
    STATUS mandatory
    DESCRIPTION "BCP (Bridging Control Protocol) information table. Values are
    first valid when protocol has state OPENED. Not used for multilink
    slave links (pppLinkProtoStatePppLinkType = multilinkslave)."
    ::= { pppLink 3 }

pppLinkBcpEntry OBJECT-TYPE
    SYNTAX PppLinkBcpEntry
    ACCESS not-accessible
    STATUS mandatory
    DESCRIPTION ""
    INDEX { pppLinkBcpIfIndex}
    ::= { pppLinkBcpTable 1 }

PppLinkBcpEntry ::= SEQUENCE {
    pppLinkBcpIfIndex
    INTEGER,
    pppLinkBcpMACTypeInc
    INTEGER,
    pppLinkBcpMACTypeOut
    INTEGER,
    pppLinkBcpBridgingProtInc
    INTEGER,
    pppLinkBcpBridgingProtOut
    INTEGER
}

pppLinkBcpIfIndex OBJECT-TYPE
    SYNTAX INTEGER
    ACCESS read-only
    STATUS mandatory
    DESCRIPTION "Interface index"
    ::= { pppLinkBcpEntry 1 }

pppLinkBcpMACTypeInc OBJECT-TYPE
    SYNTAX INTEGER {
        notnegotiated(1), ethernet(2)}
    ACCESS read-only
    STATUS mandatory
    DESCRIPTION "Frame type (incoming)"
    ::= { pppLinkBcpEntry 2 }

pppLinkBcpMACTypeOut OBJECT-TYPE
    SYNTAX INTEGER {
        notnegotiated(1), ethernet(2)}
    ACCESS read-only
    STATUS mandatory
    DESCRIPTION "Frame type (outgoing)"
    ::= { pppLinkBcpEntry 3 }

pppLinkBcpBridgingProtInc OBJECT-TYPE
    SYNTAX INTEGER {
        notnegotiated(1), spanningtree(2)}
    ACCESS read-only
    STATUS mandatory
    DESCRIPTION "Bridging protocol used (incoming)."
    ::= { pppLinkBcpEntry 4 }

pppLinkBcpBridgingProtOut OBJECT-TYPE
    SYNTAX INTEGER {
         notnegotiated(1), spanningtree(2)}
    ACCESS read-only
    STATUS mandatory
    DESCRIPTION "Bridging protocol used (outgoing)."
    ::= { pppLinkBcpEntry 5 }


pppLinkCcpTable OBJECT-TYPE
    SYNTAX SEQUENCE OF PppLinkCcpEntry
    ACCESS not-accessible
    STATUS mandatory
    DESCRIPTION "CCP (Compression Control Protocol) information table. Not used for multilink
    slave links (pppLinkProtoStatePppLinkType = multilinkslave)."
    ::= { pppLink 4 }

pppLinkCcpEntry OBJECT-TYPE
    SYNTAX PppLinkCcpEntry
    ACCESS not-accessible
    STATUS mandatory
    DESCRIPTION ""
    INDEX { pppLinkCcpIfIndex}
    ::= { pppLinkCcpTable 1 }

PppLinkCcpEntry ::= SEQUENCE {
    pppLinkCcpIfIndex
    INTEGER,
    pppLinkCcpHistorySizeIncoming
    INTEGER,
    pppLinkCcpHistorySizeOutgoing
    INTEGER,
    pppLinkCcpCheckTypeIncoming
    INTEGER,
    pppLinkCcpCheckTypeOutgoing
    INTEGER
}

pppLinkCcpIfIndex OBJECT-TYPE
    SYNTAX INTEGER
    ACCESS read-only
    STATUS mandatory
    DESCRIPTION "Interface index."
    ::= { pppLinkCcpEntry 1 }

pppLinkCcpHistorySizeIncoming OBJECT-TYPE
    SYNTAX INTEGER
    ACCESS read-only
    STATUS mandatory
    DESCRIPTION "Number of compression histories (incoming)."
    ::= { pppLinkCcpEntry 2 }

pppLinkCcpHistorySizeOutgoing OBJECT-TYPE
    SYNTAX INTEGER
    ACCESS read-only
    STATUS mandatory
    DESCRIPTION "Number of compression histories (outgoing)."
    ::= { pppLinkCcpEntry 3 }

pppLinkCcpCheckTypeIncoming OBJECT-TYPE
    SYNTAX INTEGER {
        none(1),
        sequenceno(2)
        }
    ACCESS read-only
    STATUS mandatory
    DESCRIPTION "How compression history synchronization is handled (incoming)."
    ::= { pppLinkCcpEntry 4 }

pppLinkCcpCheckTypeOutgoing OBJECT-TYPE
    SYNTAX INTEGER {
        none(1),
        sequenceno(2)
        }
    ACCESS read-only
    STATUS mandatory
    DESCRIPTION "How compression history synchronization is handled."
    ::= { pppLinkCcpEntry 5 }

pppLinkEcpTable OBJECT-TYPE
    SYNTAX SEQUENCE OF PppLinkEcpEntry
    ACCESS not-accessible
    STATUS mandatory
    DESCRIPTION "ECP (Encryption Control Protocol) information table. Not used for multilink
    slave links (pppLinkProtoStatePppLinkType = multilinkslave)."
    ::= { pppLink 5 }

pppLinkEcpEntry OBJECT-TYPE
    SYNTAX PppLinkEcpEntry
    ACCESS not-accessible
    STATUS mandatory
    DESCRIPTION ""
    INDEX { pppLinkEcpIfIndex}
    ::= { pppLinkEcpTable 1 }

PppLinkEcpEntry ::= SEQUENCE {
    pppLinkEcpIfIndex
    INTEGER,
    pppLinkEcpResetRequestsRx
    Counter,
    pppLinkEcpResetRequestsTx
    Counter,
    pppLinkEcpResetAcksRx
    Counter,
    pppLinkEcpResetAcksTx
    Counter,
    pppLinkEcpRxDiscarded
    Counter,
    pppLinkEcpTxDiscarded
    Counter,
    pppLinkEcpReceiverState
    INTEGER
}

pppLinkEcpIfIndex OBJECT-TYPE
    SYNTAX INTEGER
    ACCESS read-only
    STATUS mandatory
    DESCRIPTION "Interface index"
    ::= { pppLinkEcpEntry 1 }

pppLinkEcpResetRequestsRx OBJECT-TYPE
    SYNTAX Counter
    ACCESS read-only
    STATUS mandatory
    DESCRIPTION "Number of encryption history reset requests received."
    ::= { pppLinkEcpEntry 2 }

pppLinkEcpResetRequestsTx OBJECT-TYPE
    SYNTAX Counter
    ACCESS read-only
    STATUS mandatory
    DESCRIPTION "Number of encryption history reset requests sent."
    ::= { pppLinkEcpEntry 3 }

pppLinkEcpResetAcksRx OBJECT-TYPE
    SYNTAX Counter
    ACCESS read-only
    STATUS mandatory
    DESCRIPTION "Number of encryption history reset acknowledgments received."
    ::= { pppLinkEcpEntry 4 }

pppLinkEcpResetAcksTx OBJECT-TYPE
    SYNTAX Counter
    ACCESS read-only
    STATUS mandatory
    DESCRIPTION "Number of encryption history reset acknowledgments sent."
    ::= { pppLinkEcpEntry 5 }

pppLinkEcpRxDiscarded OBJECT-TYPE
    SYNTAX Counter
    ACCESS read-only
    STATUS mandatory
    DESCRIPTION "Number of packets discarded due to lack of
    synchronization, buffer lacks or packet errors."
    ::= { pppLinkEcpEntry 6 }

pppLinkEcpTxDiscarded OBJECT-TYPE
    SYNTAX Counter
    ACCESS read-only
    STATUS mandatory
    DESCRIPTION "Number of packets discarded due to buffer lacks or
    transmit queue overflows"
    ::= { pppLinkEcpEntry 7 }

pppLinkEcpReceiverState OBJECT-TYPE
    SYNTAX INTEGER {
        ok(1),
        error(2)
        }
    ACCESS read-only
    STATUS mandatory
    DESCRIPTION "State of receiver. Error state means waiting for reset acknowledgment"
    ::= { pppLinkEcpEntry 8 }


pppLinkCompTable OBJECT-TYPE
    SYNTAX SEQUENCE OF PppLinkCompEntry
    ACCESS not-accessible
    STATUS mandatory
    DESCRIPTION "Compression information table. Not used for multilink
    slave links (pppLinkProtoStatePppLinkType = multilinkslave)."
    ::= { pppLink 6 }

pppLinkCompEntry OBJECT-TYPE
    SYNTAX PppLinkCompEntry
    ACCESS not-accessible
    STATUS mandatory
    DESCRIPTION ""
    INDEX { pppLinkCompIfIndex}
    ::= { pppLinkCompTable 1 }

PppLinkCompEntry ::= SEQUENCE {
    pppLinkCompIfIndex
    INTEGER,
    pppLinkCompDecoderBytesIn
    Counter,
    pppLinkCompDecoderDecompBytesOut
    Counter,
    pppLinkCompDecoderUncompBytesOut
    Counter,
    pppLinkCompDecoderCompPacketsIn
    Counter,
    pppLinkCompDecoderUncompPacketsIn
    Counter,
    pppLinkCompDecoderDecompQueueLength
    Counter,
    pppLinkCompDecoderCompressionRatio
    Counter,
    pppLinkCompDecoderResetRequestTx
    Counter,
    pppLinkCompDecoderResetAcksRx
    Counter,
    pppLinkCompDecoderRxDiscarded
    Counter,
    pppLinkCompDecoderState
    INTEGER,
    pppLinkCompEncoderBytesIn
    Counter,
    pppLinkCompEncoderCompBytesOut
    Counter,
    pppLinkCompEncoderUncompBytesOut
    Counter,
    pppLinkCompEncoderCompPacketsOut
    Counter,
    pppLinkCompEncoderUncompPacketsOut
    Counter,
    pppLinkCompEncoderCompQueueLength
    Counter,
    pppLinkCompEncoderCompressionRation
    Counter,
    pppLinkCompEncoderResetRequestRx
    Counter,
    pppLinkCompEncoderResetAckTx
    Counter,
    pppLinkCompEncoderTxDiscarded
    Counter
}

pppLinkCompIfIndex OBJECT-TYPE
    SYNTAX INTEGER
    ACCESS read-only
    STATUS mandatory
    DESCRIPTION "Interface index."
    ::= { pppLinkCompEntry 1 }

pppLinkCompDecoderBytesIn OBJECT-TYPE
    SYNTAX Counter
    ACCESS read-only
    STATUS mandatory
    DESCRIPTION "Total number of bytes received by the decoder."
    ::= { pppLinkCompEntry 2 }

pppLinkCompDecoderDecompBytesOut OBJECT-TYPE
    SYNTAX Counter
    ACCESS read-only
    STATUS mandatory
    DESCRIPTION "Decompressed bytes from the decoder."
    ::= { pppLinkCompEntry 3 }

pppLinkCompDecoderUncompBytesOut OBJECT-TYPE
    SYNTAX Counter
    ACCESS read-only
    STATUS mandatory
    DESCRIPTION "Uncompressed bytes received by the decoder."
    ::= { pppLinkCompEntry 4 }

pppLinkCompDecoderCompPacketsIn OBJECT-TYPE
    SYNTAX Counter
    ACCESS read-only
    STATUS mandatory
    DESCRIPTION "Compressed packets received by the decoder."
    ::= { pppLinkCompEntry 5 }

pppLinkCompDecoderUncompPacketsIn OBJECT-TYPE
    SYNTAX Counter
    ACCESS read-only
    STATUS mandatory
    DESCRIPTION "Uncompressed packets received by the decoder."
    ::= { pppLinkCompEntry 6 }

pppLinkCompDecoderDecompQueueLength OBJECT-TYPE
    SYNTAX Counter
    ACCESS read-only
    STATUS mandatory
    DESCRIPTION "Number of packets waiting to be decompressed."
    ::= { pppLinkCompEntry 7 }

pppLinkCompDecoderCompressionRatio OBJECT-TYPE
    SYNTAX Counter
    ACCESS read-only
    STATUS mandatory
    DESCRIPTION "Receive compression ratio (multiplied by 100)."
    ::= { pppLinkCompEntry 8 }

pppLinkCompDecoderResetRequestTx OBJECT-TYPE
    SYNTAX Counter
    ACCESS read-only
    STATUS mandatory
    DESCRIPTION "The number of times the decoder requested
    re-initialization og the compression history."
    ::= { pppLinkCompEntry 9 }

pppLinkCompDecoderResetAcksRx OBJECT-TYPE
    SYNTAX Counter
    ACCESS read-only
    STATUS mandatory
    DESCRIPTION "The number of acknowledgments to reset requests received
    by the router."
    ::= { pppLinkCompEntry 10 }

pppLinkCompDecoderRxDiscarded OBJECT-TYPE
    SYNTAX Counter
    ACCESS read-only
    STATUS mandatory
    DESCRIPTION "Number of packets discarded by the decoder due to buffer
    lacks or synchronization problems."
    ::= { pppLinkCompEntry 11 }

pppLinkCompDecoderState OBJECT-TYPE
    SYNTAX INTEGER {
        ok(1),
        error(2)
        }
    ACCESS read-only
    STATUS mandatory
    DESCRIPTION "State of decoder. Error state means waiting for reset acknowledgment"
    ::= { pppLinkCompEntry 12 }

pppLinkCompEncoderBytesIn OBJECT-TYPE
    SYNTAX Counter
    ACCESS read-only
    STATUS mandatory
    DESCRIPTION "Total number of bytes received by the encoder."
    ::= { pppLinkCompEntry 13 }

pppLinkCompEncoderCompBytesOut OBJECT-TYPE
    SYNTAX Counter
    ACCESS read-only
    STATUS mandatory
    DESCRIPTION "Number of compressed bytes leaving the encoder."
    ::= { pppLinkCompEntry 14 }

pppLinkCompEncoderUncompBytesOut OBJECT-TYPE
    SYNTAX Counter
    ACCESS read-only
    STATUS mandatory
    DESCRIPTION "Number of uncompressed bytes leaving the encoder."
    ::= { pppLinkCompEntry 15 }

pppLinkCompEncoderCompPacketsOut OBJECT-TYPE
    SYNTAX Counter
    ACCESS read-only
    STATUS mandatory
    DESCRIPTION "Number of compressed packets leaving the encoder."
    ::= { pppLinkCompEntry 16 }

pppLinkCompEncoderUncompPacketsOut OBJECT-TYPE
    SYNTAX Counter
    ACCESS read-only
    STATUS mandatory
    DESCRIPTION "Number of uncompressed packets leaving the encoder."
    ::= { pppLinkCompEntry 17 }

pppLinkCompEncoderCompQueueLength OBJECT-TYPE
    SYNTAX Counter
    ACCESS read-only
    STATUS mandatory
    DESCRIPTION "Number of packets waiting to be compressed."
    ::= { pppLinkCompEntry 18 }

pppLinkCompEncoderCompressionRation OBJECT-TYPE
    SYNTAX Counter
    ACCESS read-only
    STATUS mandatory
    DESCRIPTION "Transmit compression ratio (multiplied by 100)."
    ::= { pppLinkCompEntry 19 }

pppLinkCompEncoderResetRequestRx OBJECT-TYPE
    SYNTAX Counter
    ACCESS read-only
    STATUS mandatory
    DESCRIPTION "The number of times the remote end requested
    re-initialization og the compression history."
    ::= { pppLinkCompEntry 20 }

pppLinkCompEncoderResetAckTx OBJECT-TYPE
    SYNTAX Counter
    ACCESS read-only
    STATUS mandatory
    DESCRIPTION "The number of acknowledgments to reset requests transmitted
    by the router."
    ::= { pppLinkCompEntry 21 }

pppLinkCompEncoderTxDiscarded OBJECT-TYPE
    SYNTAX Counter
    ACCESS read-only
    STATUS mandatory
    DESCRIPTION "Number of packets discarded by the encoder due to buffer
    lacks or transmit queue overflows."
    ::= { pppLinkCompEntry 22 }


pppLinkChapTable OBJECT-TYPE
    SYNTAX SEQUENCE OF PppLinkChapEntry
    ACCESS not-accessible
    STATUS mandatory
    DESCRIPTION "Table containing CHAP information. Not used for
    multilink master links (pppLinkProtoStatePppLinkType = multilinkmaster)."
    ::= { pppLink 7 }

pppLinkChapEntry OBJECT-TYPE
    SYNTAX PppLinkChapEntry
    ACCESS not-accessible
    STATUS mandatory
    DESCRIPTION ""
    INDEX { pppLinkChapIfIndex}
    ::= { pppLinkChapTable 1 }

PppLinkChapEntry ::= SEQUENCE {
        pppLinkChapIfIndex
        INTEGER,
        pppLinkChapIncoming
        INTEGER,
        pppLinkChapOutgoing
        INTEGER,
        pppLinkChapChallengeRx
        Counter,
        pppLinkChapChallengeTx
        Counter,
        pppLinkChapResponseRx
        Counter,
        pppLinkChapResponseTx
        Counter,
        pppLinkChapSuccesRx
        Counter,
        pppLinkChapSuccesTx
        Counter,
        pppLinkChapFailureRx
        Counter,
        pppLinkChapFailureTx
        Counter
}

pppLinkChapIfIndex OBJECT-TYPE
    SYNTAX INTEGER
    ACCESS read-only
    STATUS mandatory
    DESCRIPTION "Interface index."
    ::= {  pppLinkChapEntry 1 }

pppLinkChapIncoming OBJECT-TYPE
    SYNTAX INTEGER {
        notnegotiated(1), yes(2)}
    ACCESS read-only
    STATUS mandatory
    DESCRIPTION "Is this router authenticated by the remote end using CHAP."
    ::= {  pppLinkChapEntry 2 }

pppLinkChapOutgoing OBJECT-TYPE
    SYNTAX INTEGER {
        notnegotiated(1), yes(2)}
    ACCESS read-only
    STATUS mandatory
    DESCRIPTION "Is the remote router authenticated using CHAP."
    ::= {  pppLinkChapEntry 3 }

pppLinkChapChallengeRx OBJECT-TYPE
    SYNTAX Counter
    ACCESS read-only
    STATUS mandatory
    DESCRIPTION "Authentication challenges received from remote end"
    ::= {  pppLinkChapEntry 4 }

pppLinkChapChallengeTx OBJECT-TYPE
    SYNTAX Counter
    ACCESS read-only
    STATUS mandatory
    DESCRIPTION "Authentication challenges transmitted to remote end"
    ::= {  pppLinkChapEntry 5 }

pppLinkChapResponseRx OBJECT-TYPE
    SYNTAX Counter
    ACCESS read-only
    STATUS mandatory
    DESCRIPTION "Authentication responses received from remote end."
    ::= {  pppLinkChapEntry 6 }

pppLinkChapResponseTx OBJECT-TYPE
    SYNTAX Counter
    ACCESS read-only
    STATUS mandatory
    DESCRIPTION "Authentication responses transmitted to remote end."
    ::= {  pppLinkChapEntry 7 }

pppLinkChapSuccesRx OBJECT-TYPE
    SYNTAX Counter
    ACCESS read-only
    STATUS mandatory
    DESCRIPTION "Number of authentication succes replies received from
    remote end."
    ::= {  pppLinkChapEntry 8 }

pppLinkChapSuccesTx OBJECT-TYPE
    SYNTAX Counter
    ACCESS read-only
    STATUS mandatory
    DESCRIPTION "Number of authentication succes replies transmitted to
    remote end."
    ::= {  pppLinkChapEntry 9 }

pppLinkChapFailureRx OBJECT-TYPE
    SYNTAX Counter
    ACCESS read-only
    STATUS mandatory
    DESCRIPTION "Number of authentication failure replies received from
    remote end."
    ::= {  pppLinkChapEntry 10 }

pppLinkChapFailureTx OBJECT-TYPE
    SYNTAX Counter
    ACCESS read-only
    STATUS mandatory
    DESCRIPTION "Number of authentication failure replies transmitted to
    remote end."
    ::= {  pppLinkChapEntry 11 }


pppLinkPapTable OBJECT-TYPE
    SYNTAX SEQUENCE OF PppLinkPapEntry
    ACCESS not-accessible
    STATUS mandatory
    DESCRIPTION "Table containing CHAP information. Not used for
    multilink master links (pppLinkProtoStatePppLinkType = multilinkmaster)."
    ::= { pppLink 8 }

pppLinkPapEntry OBJECT-TYPE
    SYNTAX PppLinkPapEntry
    ACCESS not-accessible
    STATUS mandatory
    DESCRIPTION ""
    INDEX { pppLinkPapIfIndex}
    ::= { pppLinkPapTable 1 }

PppLinkPapEntry ::= SEQUENCE {
        pppLinkPapIfIndex
        INTEGER,
        pppLinkPapIncoming
        INTEGER,
        pppLinkPapOutgoing
        INTEGER,
        pppLinkPapAuthReqRx
        Counter,
        pppLinkPapAuthReqTx
        Counter,
        pppLinkPapAuthAckRx
        Counter,
        pppLinkPapAuthAckTx
        Counter,
        pppLinkPapAuthNackRx
        Counter,
        pppLinkPapAuthNackTx
        Counter
}

pppLinkPapIfIndex OBJECT-TYPE
    SYNTAX INTEGER
    ACCESS read-only
    STATUS mandatory
    DESCRIPTION "Interface index."
    ::= {  pppLinkPapEntry 1 }

pppLinkPapIncoming OBJECT-TYPE
    SYNTAX INTEGER {
        notnegotiated(1), yes(2)}
    ACCESS read-only
    STATUS mandatory
    DESCRIPTION "Is this router authenticated by the remote end using PAP."
    ::= {  pppLinkPapEntry 2 }

pppLinkPapOutgoing OBJECT-TYPE
    SYNTAX INTEGER {
        notnegotiated(1), yes(2)}
    ACCESS read-only
    STATUS mandatory
    DESCRIPTION "Is the remote router authenticated using PAP."
    ::= {  pppLinkPapEntry 3 }

pppLinkPapAuthReqRx OBJECT-TYPE
    SYNTAX Counter
    ACCESS read-only
    STATUS mandatory
    DESCRIPTION "Number of authentication requests received from remote end."
    ::= {  pppLinkPapEntry 4 }

pppLinkPapAuthReqTx OBJECT-TYPE
    SYNTAX Counter
    ACCESS read-only
    STATUS mandatory
    DESCRIPTION "Number of authentication requests transmitted to remote end."
    ::= {  pppLinkPapEntry 5 }

pppLinkPapAuthAckRx OBJECT-TYPE
    SYNTAX Counter
    ACCESS read-only
    STATUS mandatory
    DESCRIPTION "Number of authentication succes replies received from
    remote end."
    ::= {  pppLinkPapEntry 6 }

pppLinkPapAuthAckTx OBJECT-TYPE
    SYNTAX Counter
    ACCESS read-only
    STATUS mandatory
    DESCRIPTION "Number of authentication succes replies transmitted to
    remote end."
    ::= {  pppLinkPapEntry 7 }

pppLinkPapAuthNackRx OBJECT-TYPE
    SYNTAX Counter
    ACCESS read-only
    STATUS mandatory
    DESCRIPTION "Number of authentication succes replies transmitted to
    remote end."
    ::= {  pppLinkPapEntry 8 }

pppLinkPapAuthNackTx OBJECT-TYPE
    SYNTAX Counter
    ACCESS read-only
    STATUS mandatory
    DESCRIPTION "Number of authentication failure replies received from
    remote end."
    ::= {  pppLinkPapEntry 9 }



pppLinkMlMasterTable OBJECT-TYPE
    SYNTAX SEQUENCE OF PppLinkMlMasterEntry
    ACCESS not-accessible
    STATUS mandatory
    DESCRIPTION "Table containing multilink master information. Only used
    when pppLinkProtoStatePppLinkType = multilinkmaster."
    ::= { pppLink 9 }

pppLinkMlMasterEntry OBJECT-TYPE
    SYNTAX PppLinkMlMasterEntry
    ACCESS not-accessible
    STATUS mandatory
    DESCRIPTION ""
    INDEX { pppLinkMlMasterIfIndex}
    ::= { pppLinkMlMasterTable 1 }

PppLinkMlMasterEntry ::= SEQUENCE {
        pppLinkMlMasterIfIndex
        INTEGER,
        pppLinkMlMasterSlaveCount
        Counter,
        pppLinkMlMasterTxUtilization
        Counter,
        pppLinkMlMasterRxUtilization
        Counter,
        pppLinkMlMasterSlavesForwarding
         Counter
}

pppLinkMlMasterIfIndex OBJECT-TYPE
    SYNTAX INTEGER
    ACCESS read-only
    STATUS mandatory
    DESCRIPTION "Interface index."
    ::= {  pppLinkMlMasterEntry 1 }

pppLinkMlMasterSlaveCount OBJECT-TYPE
    SYNTAX Counter
    ACCESS read-only
    STATUS mandatory
    DESCRIPTION "Number of slave links in multilink bundle."
    ::= {  pppLinkMlMasterEntry 2 }

pppLinkMlMasterTxUtilization OBJECT-TYPE
    SYNTAX Counter
    ACCESS read-only
    STATUS mandatory
    DESCRIPTION "Transmit utilization of current bundle measured in percent."
    ::= {  pppLinkMlMasterEntry 3 }

pppLinkMlMasterRxUtilization OBJECT-TYPE
    SYNTAX Counter
    ACCESS read-only
    STATUS mandatory
    DESCRIPTION "Receive utilization of current bundle measured in percent."
    ::= {  pppLinkMlMasterEntry 4 }

pppLinkMlMasterSlavesForwarding OBJECT-TYPE
    SYNTAX Counter
    ACCESS read-only
    STATUS mandatory
    DESCRIPTION "Number of forwarding slave links in bundle."
    ::= {  pppLinkMlMasterEntry 5 }


pppLinkMlSlaveTable OBJECT-TYPE
    SYNTAX SEQUENCE OF PppLinkMlSlaveEntry
    ACCESS not-accessible
    STATUS mandatory
    DESCRIPTION "Table containing multilink slave information. Only used
    when pppLinkProtoStatePppLinkType = multilinkslave."
    ::= { pppLink 10 }

pppLinkMlSlaveEntry OBJECT-TYPE
    SYNTAX PppLinkMlSlaveEntry
    ACCESS not-accessible
    STATUS mandatory
    DESCRIPTION ""
    INDEX { pppLinkMlSlaveIfIndex}
    ::= { pppLinkMlSlaveTable 1 }

PppLinkMlSlaveEntry ::= SEQUENCE {
        pppLinkMlSlaveIfIndex
        INTEGER,
        pppLinkMlSlaveBodEnabled
        INTEGER,
        pppLinkMlSlaveMasterIfIndex
        INTEGER
}

pppLinkMlSlaveIfIndex OBJECT-TYPE
    SYNTAX INTEGER
    ACCESS read-only
    STATUS mandatory
    DESCRIPTION "Interface index."
    ::= {  pppLinkMlSlaveEntry 1 }

pppLinkMlSlaveBodEnabled OBJECT-TYPE
    SYNTAX INTEGER {
        true(1), false(2) }
    ACCESS read-only
    STATUS mandatory
    DESCRIPTION "Bandwidth on demand enabled for this slave link."
    ::= {  pppLinkMlSlaveEntry 2 }

pppLinkMlSlaveMasterIfIndex OBJECT-TYPE
    SYNTAX INTEGER
    ACCESS read-only
    STATUS mandatory
    DESCRIPTION "Interface index of the corresponding master link."
    ::= {  pppLinkMlSlaveEntry 3 }


END
