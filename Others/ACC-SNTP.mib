ACC-SNTP DEFINITIONS ::= BEGIN

    IMPORTS
		OBJECT-TYPE, IpAddress, TimeTicks, Gauge, Counter FROM RFC1155-SMI
		TRAP-TYPE FROM RFC-1215
      accTrapLogSeqNum FROM ACC-SYSTEM
accBRG, DisplayString, RowStatus, IfIndex, SmdsAddress
             FROM ACC-MIB;

-- SNTP Group
    -- ACC SNTP branch
    accSntp 			OBJECT IDENTIFIER ::= { accBRG 88 }
    accSntpGeneralScalars	OBJECT IDENTIFIER ::= { accSntp 1 }
    accSntpSever		OBJECT IDENTIFIER ::= { accSntp 2 }
    accSntpTraps 		OBJECT IDENTIFIER ::= { accSntp 3 }
    --
    --  ACC SNTP objects
    --
    accSntpAdminState OBJECT-TYPE
	SYNTAX  INTEGER {
		    enabled(1),
		    disabled(2)
		}
	ACCESS  read-write
	STATUS  mandatory
	DESCRIPTION
	     "SNTP Adminstrative state."
	DEFVAL { disabled }
	::= { accSntpGeneralScalars 1 }
    accSntpBroadcastMode OBJECT-TYPE
	SYNTAX  INTEGER {
		    enabled(1),
		    disabled(2)
		}
	ACCESS  read-write
	STATUS  mandatory
	DESCRIPTION
	     "SNTP Broadcast Mode."
	DEFVAL { disabled }
	::= { accSntpGeneralScalars 2 }
    accSntpMessageLevel OBJECT-TYPE
        SYNTAX  INTEGER (1..7)
	ACCESS  read-write
	STATUS  mandatory
	DESCRIPTION
	     "SNTP Message Level"
	DEFVAL { 1 }
	::= { accSntpGeneralScalars 3 }
    accSntpDebugMask OBJECT-TYPE
        SYNTAX  INTEGER (0..255)
	ACCESS  read-write
	STATUS  mandatory
	DESCRIPTION
	     "SNTP Debug Mask "
	DEFVAL { 255 }
	::= { accSntpGeneralScalars 4 }
    accSntpStatInPackets OBJECT-TYPE
        SYNTAX  Counter
        ACCESS  read-only
        STATUS  mandatory
        DESCRIPTION
             "Indicates the total number of SNTP packets received from 
	     all SNTP server ,both unicast and multicast packets."
	::= { accSntpGeneralScalars 5 }
    accSntpStatOutPackets OBJECT-TYPE
        SYNTAX  Counter
        ACCESS  read-only
        STATUS  mandatory
        DESCRIPTION
             "Indicates the total number of SNTP Unicast packets sent to 
	     all SNTP server."
	::= { accSntpGeneralScalars 6 }
    accSntpStatInDiscards OBJECT-TYPE
        SYNTAX  Counter
        ACCESS  read-only
        STATUS  mandatory
        DESCRIPTION
             "Indicates the total number of SNTP packets discarded from 
	     all SNTP server ,both unicast and multicast packets."
	::= { accSntpGeneralScalars 7 }
    accSntpStatInBcastPackets OBJECT-TYPE
        SYNTAX  Counter
        ACCESS  read-only
        STATUS  mandatory
        DESCRIPTION
             "Indicates the total number of SNTP packets recvd from 
	     all SNTP server ,only multicast/broadcast packets."
	::= { accSntpGeneralScalars 8 }
    accSntpLastBcastPacTime OBJECT-TYPE
        SYNTAX  OCTET STRING
        ACCESS  read-only
        STATUS  mandatory
        DESCRIPTION
		" The Time at which the Last Sntp Broadcast message was recieved."
	::= { accSntpGeneralScalars 9 }
    accSntpLastBcastPacSrcAddr OBJECT-TYPE
        SYNTAX  IpAddress
        ACCESS  read-only
        STATUS  mandatory
        DESCRIPTION
		" The Source Address from which the 
		  Last Sntp Broadcast message was recieved."
	::= { accSntpGeneralScalars 10 }
    accSntpStatQueryTimeouts OBJECT-TYPE
        SYNTAX  Counter
        ACCESS  read-only
        STATUS  mandatory
        DESCRIPTION
             "Indicates the total number of failed SNTP Unicast packets sent to  
	     all SNTP server. "
	::= { accSntpGeneralScalars 11 }
    --
    --		The SNTP Neighbor Table
    --
    accSntpSeverTable OBJECT-TYPE
        SYNTAX  SEQUENCE OF AccSntpSeverEntry
        ACCESS          not-accessible
        STATUS          mandatory
        DESCRIPTION
             "Displays all Sntp Server entries."
    ::= { accSntpSever 1 }
    accSntpSeverEntry OBJECT-TYPE
        SYNTAX  AccSntpSeverEntry
        ACCESS  not-accessible
        STATUS  mandatory
        DESCRIPTION
             ""
        INDEX   { accSntpServIndex }
        ::= { accSntpSeverTable 1 }
    AccSntpSeverEntry ::= SEQUENCE {
	accSntpServIndex	INTEGER,
	accSntpServAddr		IpAddress,
	accSntpServAdminState	INTEGER,
	accSntpServPollInt	INTEGER,
	accSntpServRetryCnt	INTEGER,
	accSntpServRetryInt	INTEGER,
	accSntpServRecInt	INTEGER,
	accSntpServUdpPort	INTEGER,
	accSntpServLastResp	OCTET STRING,
	accSntpServOperState	INTEGER,
	accSntpServInPackets	Counter,
	accSntpServOutPackets	Counter,
	accSntpServInDiscards	Counter,
	accSntpServEntryStatus	RowStatus
	}
    accSntpServIndex OBJECT-TYPE
	SYNTAX  INTEGER (1..6)
	ACCESS  read-write
	STATUS  mandatory
	DESCRIPTION
	     "The Index of the Sntp Server Entry."
	::= { accSntpSeverEntry 1 }
    accSntpServAddr OBJECT-TYPE
	SYNTAX  IpAddress
	ACCESS  read-write
	STATUS  mandatory
	DESCRIPTION
	     "The remote IP Address of the Sntp Server."
	::= { accSntpSeverEntry 2 }
    accSntpServAdminState OBJECT-TYPE
	SYNTAX  INTEGER {
			enabled(1),
			disabled(2)
			}
	ACCESS  read-write
	STATUS  mandatory
	DESCRIPTION
	     "The Admin State of the remote IP Address of the Sntp Server."
	::= { accSntpSeverEntry 3 }
    accSntpServPollInt OBJECT-TYPE
        SYNTAX  INTEGER (4..16284)
	ACCESS  read-write
	STATUS  mandatory
	DESCRIPTION
	     "SNTP Server Poll Interval "
	DEFVAL { 600 }
	::= { accSntpSeverEntry 4 }
    accSntpServRetryCnt OBJECT-TYPE
        SYNTAX  INTEGER (0..10)
	ACCESS  read-write
	STATUS  mandatory
	DESCRIPTION
	     "SNTP Server Retry Count "
	DEFVAL { 5 }
	::= { accSntpSeverEntry 5 }
    accSntpServRetryInt OBJECT-TYPE
        SYNTAX  INTEGER (0..600)
	ACCESS  read-write
	STATUS  mandatory
	DESCRIPTION
	     "SNTP Server Retry Interval "
	DEFVAL { 60 }
	::= { accSntpSeverEntry 6 }
    accSntpServRecInt OBJECT-TYPE
        SYNTAX  INTEGER (100..3600)
	ACCESS  read-write
	STATUS  mandatory
	DESCRIPTION
	     "SNTP Server Recovery Interval "
	::= { accSntpSeverEntry 7 }
    accSntpServUdpPort OBJECT-TYPE
        SYNTAX  INTEGER (0..65000)
	ACCESS  read-write
	STATUS  mandatory
	DESCRIPTION
	     "SNTP Server Retry Interval "
	DEFVAL { 123 }
	::= { accSntpSeverEntry 8 }
    accSntpServLastResp OBJECT-TYPE
        SYNTAX  OCTET STRING
	ACCESS  read-only
	STATUS  mandatory
	DESCRIPTION
	     "SNTP Server Last Response Time "
	::= { accSntpSeverEntry 9 }
    accSntpServOperState OBJECT-TYPE
	SYNTAX  INTEGER {
			unknown(1),
			trying(2),
			up(3),
			down(4)
			}
	ACCESS  read-write
	STATUS  mandatory
	DESCRIPTION
	     "The Operational State of the remote IP Address of the Sntp Server."
	::= { accSntpSeverEntry 10 }
    accSntpServInPackets OBJECT-TYPE
	SYNTAX  Counter
	ACCESS read-only
	STATUS  mandatory
	DESCRIPTION
	     "The number of SNTP response packets recieved from
		Remote SNTP server"
	::= { accSntpSeverEntry 11 }
    accSntpServOutPackets OBJECT-TYPE
	SYNTAX  Counter
	ACCESS read-only
	STATUS  mandatory
	DESCRIPTION
	     "The number of SNTP requests packets sent to the
		remote SNTP server"
	::= { accSntpSeverEntry 12 }
    accSntpServInDiscards OBJECT-TYPE
	SYNTAX  Counter
	ACCESS read-only
	STATUS  mandatory
	DESCRIPTION
	     "The number of packets discarded packets from the SNTP server"
	::= { accSntpSeverEntry 13 }
    accSntpServEntryStatus OBJECT-TYPE
	SYNTAX  RowStatus
	ACCESS  read-write
	STATUS  mandatory
	DESCRIPTION
	     "The  Row Status of the remote IP Address of the Sntp Server."
	::= { accSntpSeverEntry 14 }
-- START CFG_TRAP_ENHANCEMENTS
-- Sntp Traps Branch Enterprise
       accSntpTrapMsg     OBJECT-TYPE
        SYNTAX          DisplayString
        ACCESS          read-only
        STATUS          mandatory
        DESCRIPTION
        " Enterprise Trap Message for Sntp"
        ::= { accSntpTraps 1 }
-- END CFG_TRAP_ENHANCEMENTS 

        accSntpUdpBindFailTrap1 TRAP-TYPE
        ENTERPRISE   accSntpTraps 
        VARIABLES  { accSntpTrapMsg,
                      accTrapLogSeqNum}
        DESCRIPTION
                   "When the Sntp UDP binding to port 123 is
                   attempted, if this fails then this trap is generated.
SEVERITY-DEFAULT: Minor 
EVENTTYPE-DEFAULT: 2 
ADDITIONAL-TEXT-VARIABLES: { accTrapLogSeqNum,accSntpTrapMsg }
PCAUSE-DEFAULT: 4 " 
 
        ::= 1
        accSntpUdpUnBindFailTrap2 TRAP-TYPE
        ENTERPRISE   accSntpTraps 
        VARIABLES  { accSntpTrapMsg,
                      accTrapLogSeqNum}
        DESCRIPTION
                   "When the Sntp UDP unbinding to port 123 is
                   attempted, if this fails then this trap is generated.
SEVERITY-DEFAULT: Minor 
EVENTTYPE-DEFAULT: 2 
ADDITIONAL-TEXT-VARIABLES: { accTrapLogSeqNum,accSntpTrapMsg }
PCAUSE-DEFAULT: 46 " 
 
        ::= 2
        accSntpServerDownTrap3 TRAP-TYPE
        ENTERPRISE   accSntpTraps 
        VARIABLES  { accSntpTrapMsg,
                     accSntpServAddr ,
                      accTrapLogSeqNum}
        DESCRIPTION
		"If the Sntp serve configured fails to respond of a a particular 
		 number of failed retries attempts this server is set to DOWN
		 state and this trap is generated
SEVERITY-DEFAULT: Minor 
EVENTTYPE-DEFAULT: 2 
ADDITIONAL-TEXT-VARIABLES: { accTrapLogSeqNum,accSntpTrapMsg }
PCAUSE-DEFAULT: 44 "  
 
         ::= 3
END
