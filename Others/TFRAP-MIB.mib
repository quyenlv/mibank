-- Sync Research Enterprise MIB for TFRAP                     =
--                                                            =
--                                                            =
--                      MIB VERSION 4.00                      =
--                                                            =
--                                                            =
-- internal version 4.00.15
--                                                            =
--                                                            =
-- This file contains MIB Definitions for extended management =
-- of Sync TFRAP Product (T1 product with integral agent).    =
--                                                            =
-- This MIB is copyrighted by Sync Research (1997, 1998).     =
-- Permission is granted to the general public to use this    =
-- file for management of Sync Research Products.             =
--                                                            =
-- Updates to this Enterprise MIB may be obtained from        =
-- Sync Customer Service 1-800-828-2780.                      =
--                                                            =

TFRAP-MIB DEFINITIONS ::= BEGIN

   IMPORTS

      DisplayString
         FROM SNMPv2-TC
      Counter, TimeTicks, IpAddress, internet, Gauge
         FROM RFC1155-SMI
      TRAP-TYPE
         FROM RFC-1215
      OBJECT-TYPE
         FROM RFC-1212;

   --   This MIB module uses the extended OBJECT-TYPE macro.

   private     OBJECT IDENTIFIER ::= { internet 4 }
   enterprises OBJECT IDENTIFIER ::= { private 1 }
   sync        OBJECT IDENTIFIER ::= { enterprises 485 }
   tfrap       OBJECT IDENTIFIER ::= { sync 5 }

   -- textual conventions

       --DisplayString ::=
       --    OCTET STRING
       -- This data type is used to model textual information taken
       -- from the NVT ASCII character set.  By convention, objects
       -- with this syntax are declared as having
       --
       --      SIZE (0..255)


-- *********************************************************************
--                     TFRAP ENTERPRISE SPECIFIC MIB
-- *********************************************************************


-- ======================================================================
--
--  The TFRAP MIB Tree
--      This MIB covers the Sync Research TFRAP, a T1 CSU for dedicated
--      or switched (T1) applications.  This product is managed via an
--      integral agent.
--
--  The TFRAP MIB Consists of five groups (plus Traps):
--      The SYSTEM group
--      The CONFIGURATION group
--      The DIAGNOSTICS group
--      The STATUS group
--      The PERFORMANCE group
--
--  The SYSTEM group
--      This group provides system level attributes of the node.
--
--      The group consists of the following tables:
--          tfrapSysTable           - System level attributes
--          tfrapSysFeatureTable    - System level features
--
--  The CONFIGURATION group
--      This group provides for configuration of the node.
--
--      The group consists of the following tables:
--          tfrapCfgMgmtTable     - Configuration of management features
--             tfrapCfgIpTable        - IP configuration
--             tfrapCfgTftpTable      - TFTP configuration
--             tfrapCfgSnmpTable      - SNMP configuration
--                tfrapCfgSnmpMgrTable    - SNMP managers (TRAP destinations)
--             tfrapCfgCommTable      - Communication port configuration
--             tfrapCfgFrDLCITable    - DLCI configuration
--          tfrapCfgAppTable      - Application level configuration
--          tfrapCfgT1Table       - T1 port configuration
--          tfrapCfgDteTable      - DTE port configuration
--          tfrapCfgFrTable       - Frame Relay configuration
--          tfrapCfgVnipTable     - VNIP configuration
--          tfrapCfgFrPerfTable   - Frame Relay performance configuration
--             tfrapCfgFrPerfDlciNamesTable        - Table of DLCI names
--             tfrapCfgFrPerfUserProtocolsTable    - User-specified protocols
--             tfrapCfgFrPerfLTDlciFilterTable     - LT stats: DLCI filter
--             tfrapCfgFrPerfLTProtocolFilterTable - LT stats: protocol filter
--          tfrapCfgSecurityTable - Security configuration
--          
--  The DIAGNOSTICS group
--      This group provides for run-time control of the node.
--
--      The group consists of the following tables:
--          tfrapDiagUnitTable  - Unit level Diagnostics
--          tfrapDiagT1Table    - T1 Port Diagnostics
--          tfrapDiagDteTable   - DTE port diagnostics
--          
--  The STATUS group
--      This group provides status information.
--
--      The group consists of the following tables:
--          tfrapStatusIntfTable   - DTE and T1 status
--          tfrapStatusLedTable    - LED status
--          tfrapVnipTopologyTable - VNIP topology
--          tfrapStatusMgmtTable   - Status of management channel
--          
--  The PERFORMANCE group
--      This group provides statistical information.
--
--      The group consists of the following tables:
--          tfrapPerfPhysicalIntf     - Physical interface statistics
--             tfrapPerfT1CurrentTable     - T1 current statistics
--             tfrapPerfT1IntervalTable    - T1 interval statistics
--             tfrapPerfT1TotalTable       - T1 total statistics
--             tfrapT1PerfCmdTypeTable     - T1 statistics commands
--          tfrapPerfMgmtIp           - IP protocol stack statistics
--             tfrapPerfMgmtIpIFStatsTable   - Interface statistics
--             tfrapPerfMgmtIpIPStatsTable   - IP statistics
--             tfrapPerfMgmtIpICMPStatsTable - ICMP statistics
--             tfrapPerfMgmtIpUDPStatsTable  - UDP statistics
--             tfrapPerfMgmtIpTCPStatsTable  - TCP statistics
--          tfrapPerfThruput          - Thruput statistics
--             tfrapPerfThruputPerIntfTable  - Thruput per interface
--             tfrapPerfThruputPerDlciTable  - Thruput per DLCI
--          tfrapPerfCirPercentUtilization - CIR percentage stats
--          tfrapPerfNetworkShortTerm - Short term DLCI statistics
--             tfrapPerfNetwProtoPerDlciTable   - Network protocol stats per DLCI
--             tfrapPerfNetwProtoTotalTable     - Total network protocol stats
--             tfrapPerfIpPerDlciTable          - IP stats per DLCI
--             tfrapPerfIpTotalTable            - Total IP stats
--             tfrapPerfIcmpPerDlciTable        - ICMP stats per DLCI
--             tfrapPerfIcmpTotalTable          - Total ICMP stats
--             tfrapPerfApplicationPerDlciTable - Application stats per DLCI
--             tfrapPerfApplicationTotalTable   - Total application stats
--             tfrapPerfRoutingPerDlciTable     - Routing stats per DLCI
--             tfrapPerfRoutingTotalTable       - Total Routing stats
--             tfrapPerfIpxPerDlciTable         - IPX stats per DLCI
--             tfrapPerfIpxTotalTable           - Total IPX stats
--             tfrapPerfSnaPerDlciTable         - SNA stats per DLCI
--             tfrapPerfSnaTotalTable           - Total SNA stats
--             tfrapPerfArpPerDlciTable         - ARP stats per DLCI
--             tfrapPerfArpTotalTable           - Total ARP stats
--          tfrapPerfNetworkLongTerm  - Long term DLCI statistics
--             tfrapPerfNetwLongTermTable       - Long term stats
--             tfrapPerfNetwLongTermAltTable    - Alternate format LTS
--
--  The MIB also contains enterprise trap information:
--          tfrapTrap
--
-- =======================================================================



-- ========================
-- ==   SYSTEM group     ==
-- ========================

tfrapSystem      OBJECT IDENTIFIER ::= { tfrap 1 }


--
--       The tfrapSysTable
--              This table contains the system attributes of the TFRAP 
--              CSU with enhanced support for Frame Relay Networking.
      
tfrapSysTable      OBJECT IDENTIFIER ::= { tfrapSystem 1 }

tfrapSysType       OBJECT-TYPE
          SYNTAX      DisplayString (SIZE (0..255))
          ACCESS      read-only
          STATUS      mandatory
          DESCRIPTION
             "A textual description of the system model identifier.
              for example: SYNC-TFRAP"
          ::= { tfrapSysTable 1 }

tfrapSysSoftRev    OBJECT-TYPE
          SYNTAX      DisplayString (SIZE (0..10))
          ACCESS      read-only
          STATUS      mandatory
          DESCRIPTION
             "Displays the Software Revision of the application code 
              installed in this node."
          ::= { tfrapSysTable 2 }

tfrapSysHardRev    OBJECT-TYPE
          SYNTAX      DisplayString (SIZE (0..10))
          ACCESS      read-only
          STATUS      mandatory
          DESCRIPTION
             "Displays the Hardware Revision of the node."
          ::= { tfrapSysTable 3 }

tfrapSysNumT1Installed    OBJECT-TYPE
          SYNTAX      INTEGER (0..1)
          ACCESS      read-only
          STATUS      mandatory
          DESCRIPTION
             "The number of Wide Area Network (T1) ports that are
              installed.  There is 1 on the TFRAP."
          ::= { tfrapSysTable 4 }

tfrapSysNumDteInstalled    OBJECT-TYPE
          SYNTAX      INTEGER (0..1)
          ACCESS      read-only
          STATUS      mandatory
          DESCRIPTION
             "The number of user serial date channels (DTE) that are
              installed.  There is 1 on the TFRAP."
          ::= { tfrapSysTable 5 }

tfrapSysNumMaintInstalled    OBJECT-TYPE
          SYNTAX      INTEGER (0..2)
          ACCESS      read-only
          STATUS      mandatory
          DESCRIPTION
             "The number of Async Maintenance/Comm (console) ports 
              that are installed.  There is 1 dual-purpose comm port 
              on the TFRAP which may configured as either a VT-100 
              console or a SLIP management port."
          ::= { tfrapSysTable 6 }

tfrapSysName       OBJECT-TYPE
          SYNTAX      DisplayString (SIZE (0..16))
          ACCESS      read-write
          STATUS      mandatory
          DESCRIPTION
             "The user supplied name of the node.  This object
              does not affect operation, but may be useful
              for network management."
          ::= { tfrapSysTable 7 }

tfrapSysSerialNo      OBJECT-TYPE
          SYNTAX      DisplayString (SIZE (0..10))
          ACCESS      read-only
          STATUS      mandatory
          DESCRIPTION
             "The serial number of the board."
          ::= { tfrapSysTable 8 }

tfrapSysResetNode    OBJECT-TYPE
          SYNTAX      INTEGER
          {
               reset-node (321)
          }
          ACCESS      write-only
          STATUS      mandatory
          DESCRIPTION
            "Command to reset the node. NODE WILL BE OFF-LINE AND 
             USER DATA WILL BE INTERRUPTED FOR APPROXIMATELY 15 
             SECONDS. Full network recovery may take longer "
          ::= { tfrapSysTable 9 }

tfrapSysAmtMemoryInstalled    OBJECT-TYPE
          SYNTAX      INTEGER
          ACCESS      read-only
          STATUS      mandatory
          DESCRIPTION
             "The amount of memory (RAM) installed (in megabytes)."
          ::= { tfrapSysTable 10 }

tfrapSysLocation       OBJECT-TYPE
          SYNTAX  DisplayString (SIZE (0..16))
          ACCESS  read-write
          STATUS  mandatory
          DESCRIPTION
             "The user supplied location of the node.  This
              object does not affect operation, but may be
              useful for network management."
          ::= { tfrapSysTable 12 }

tfrapSysContact        OBJECT-TYPE
          SYNTAX      DisplayString (SIZE (0..16))
          ACCESS      read-write
          STATUS      mandatory
          DESCRIPTION
             "The user supplied contact information for the
              node.  This object does not affect operation,
              but may be useful for network management."
          ::= { tfrapSysTable 13 }                                

tfrapSysPrompt        OBJECT-TYPE
          SYNTAX      DisplayString (SIZE (0..8))
          ACCESS      read-write
          STATUS      mandatory
          DESCRIPTION
             "Configurable Command Line Interface (CLI) prompt. CLI
              is the User Interface protocol used for directly 
              attached VT100 terminal access and for remote
              access via Telnet."
          ::= { tfrapSysTable 15 }                                

tfrapSysBootRev       OBJECT-TYPE
          SYNTAX      DisplayString (SIZE (0..10))
          ACCESS      read-only
          STATUS      mandatory
          DESCRIPTION
             "Displays the Software Revision of the Bootstrapping
         code installed in this node."
          ::= { tfrapSysTable 16 }

tfrapSysFeatureTable      OBJECT IDENTIFIER ::= { tfrapSystem 2 }

tfrapSysSLIPSupported     OBJECT-TYPE
     SYNTAX      DisplayString (SIZE (0..10))
     ACCESS      read-only
     STATUS      mandatory
     DESCRIPTION
        "Shows whether the unit has SLIP (Serial Line IP) capability.
         SLIP is a method for out-of-band management that connects
         through the asynchronous terminal port."
     ::= { tfrapSysFeatureTable 1 }

tfrapSysPPPSupported     OBJECT-TYPE
     SYNTAX      DisplayString (SIZE (0..10))
     ACCESS      read-only
     STATUS      mandatory
     DESCRIPTION
        "Shows whether the unit has PPP (Point to Point protocol)
         capability. PPP is a method for out-of-band management 
         that connects through the asynchronous terminal port."
     ::= { tfrapSysFeatureTable 2 }

tfrapSysRDOSupported     OBJECT-TYPE
     SYNTAX      DisplayString (SIZE (0..10))
     ACCESS      read-only
     STATUS      mandatory
     DESCRIPTION
        "Shows whether the unit has Remote Dial Out capability."
     ::= { tfrapSysFeatureTable 3 }

tfrapSysETHSupported     OBJECT-TYPE
     SYNTAX      DisplayString (SIZE (0..10))
     ACCESS      read-only
     STATUS      mandatory
     DESCRIPTION
        "Shows whether the unit has Ethernet capability."
     ::= { tfrapSysFeatureTable 4 }

tfrapSysTKRSupported     OBJECT-TYPE
     SYNTAX      DisplayString (SIZE (0..10))
     ACCESS      read-only
     STATUS      mandatory
     DESCRIPTION
        "Shows whether the unit has Token Ring capability."
     ::= { tfrapSysFeatureTable 5 }

tfrapSysExtTimSupported     OBJECT-TYPE
     SYNTAX      DisplayString (SIZE (0..10))
     ACCESS      read-only
     STATUS      mandatory
     DESCRIPTION
        "Shows whether the unit has External Timing capability.
         This is the ability to derive WAN timing from the DTE port."
     ::= { tfrapSysFeatureTable 6 }

tfrapSysBRISupported     OBJECT-TYPE
     SYNTAX      DisplayString (SIZE (0..10))
     ACCESS      read-only
     STATUS      mandatory
     DESCRIPTION
        "Shows whether the unit has BRI (ISDN Basic Rate) capability."
     ::= { tfrapSysFeatureTable 7 }

tfrapSysSelDTESupported     OBJECT-TYPE
     SYNTAX      DisplayString (SIZE (0..10))
     ACCESS      read-only
     STATUS      mandatory
     DESCRIPTION
        "Shows whether the unit has a Selectable DTE interface.
         This being the ability to select amongst various electrical 
         interface formats (V.35, RS449, RS232, etc.) via software."
     ::= { tfrapSysFeatureTable 8 }

tfrapSysMLSupported     OBJECT-TYPE
     SYNTAX      DisplayString (SIZE (0..10))
     ACCESS      read-only
     STATUS      mandatory
     DESCRIPTION
        "Shows whether the unit supports MLs (out-of-band management 
         links). N/A to frame relay networks."
     ::= { tfrapSysFeatureTable 9 }

tfrapSysNumDlcisSupported     OBJECT-TYPE
     SYNTAX      INTEGER
     ACCESS      read-only
     STATUS      mandatory
     DESCRIPTION
        "Shows how many DLCIs can be monitored for frame-based 
         statistics. The unit will pass an unlimited number of 
         DLCIs but will only collect statistics on this number 
         (first come first served)."
     ::= { tfrapSysFeatureTable 10 }

tfrapSysLTFNumDlcis     OBJECT-TYPE
     SYNTAX      INTEGER
     ACCESS      read-only
     STATUS      mandatory
     DESCRIPTION
        "Shows how many DLCIs can be specified
         in the Long Term Statistics Filter."
     ::= { tfrapSysFeatureTable 11 }

tfrapSysLTFNumProtocols     OBJECT-TYPE
     SYNTAX      INTEGER
     ACCESS      read-only
     STATUS      mandatory
     DESCRIPTION
        "Shows how many protocols can be specified
         in the Long Term Statistics Filter."
     ::= { tfrapSysFeatureTable 12 }

tfrapSysNumUserProtocols     OBJECT-TYPE
     SYNTAX      INTEGER
     ACCESS      read-only
     STATUS      mandatory
     DESCRIPTION
        "Shows how many protocols can be defined by the user.
         The user configures TCP/UDP ports which can be monitored
         as protocols.  They are available for short term or
         long term statistics monitoring."
     ::= { tfrapSysFeatureTable 13 }

tfrapSysNumSnmpMgrs     OBJECT-TYPE
     SYNTAX      INTEGER
     ACCESS      read-only
     STATUS      mandatory
     DESCRIPTION
        "Shows how many SNMP managers can be programmed in the
         table tfrapCfgSnmpMngrTable. These managers are sent 
         TRAPs if configured to do so."
     ::= { tfrapSysFeatureTable 14 }

tfrapSysNumDlciNames     OBJECT-TYPE
     SYNTAX      INTEGER
     ACCESS      read-only
     STATUS      mandatory
     DESCRIPTION
        "Shows how many DLCI names can be defined by the user
         in the table tfrapCfgFrPerfDlciNamesTable."
     ::= { tfrapSysFeatureTable 15 }



-- =========================
-- == CONFIGURATION group ==
-- =========================

tfrapConfiguration   OBJECT IDENTIFIER ::= { tfrap 2 }


--
--       The Management Configuration Table
--              This table contains the management-related
--             Configuration information for the TFRAP T1 DSU.

tfrapCfgMgmtTable   OBJECT IDENTIFIER ::= { tfrapConfiguration 1 }

--
--       The IP Configuration Table
--              This table contains the Configuration for Internet Protocol
--              parameters for device management. These parameters include 
--              IP addressing and any configurable IP-based support options 
--              (such as Telnet).
--              

tfrapCfgIpTable OBJECT IDENTIFIER ::= { tfrapCfgMgmtTable 1 }
 
tfrapCfgIpMyIP   OBJECT-TYPE
          SYNTAX      IpAddress
          ACCESS      read-write
          STATUS      mandatory
          DESCRIPTION
             "The IP address for this node. This address will be unique to
              the IP network and is required for in-band or out-of-band
              ip and SNMP management."
          ::= { tfrapCfgIpTable 1 }
 
tfrapCfgIpPeerIP   OBJECT-TYPE
          SYNTAX      IpAddress
          ACCESS      read-write
          STATUS      mandatory
          DESCRIPTION
             "This parameter is not used internally by
              the unit. It is intended to identify either
              the device directly connected to the SLIP
              port or, in Frame Relay applications, the
              address of the primary network management 
              station. This should always be non-zero."
          ::= {tfrapCfgIpTable 2 }
 
tfrapCfgIpMask   OBJECT-TYPE
          SYNTAX      IpAddress
          ACCESS      read-write
          STATUS      mandatory
          DESCRIPTION
             "The IP Subnet Mask (eg 255.255.255.0). This
              parameter should be consisent with the IP
              subnet address setting of the external
              internetworking equipment (router/frad)."
          ::= { tfrapCfgIpTable 3 }
 
tfrapCfgIpMaxMTU OBJECT-TYPE
          SYNTAX      INTEGER  (1..1024)
          ACCESS      read-write
          STATUS      mandatory
          DESCRIPTION
             "The Maximum Transmission Unit is the size of the
              largest IP packet supported (including header).
              This value should be set to the lowest value supported 
              by any equipment in the transmission path.
              For Frame Relay management the typical value is 1500. 
              For SLIP management the typical value is 1006."
          ::= { tfrapCfgIpTable 4 }

tfrapCfgIpChannel   OBJECT-TYPE
          SYNTAX      INTEGER
          {
              none           (1),
              slip-port      (2),
              in-band-dlci   (3)
          }
          ACCESS      read-only
          STATUS      mandatory
          DESCRIPTION
             "This is the method by which IP traffic is being carried.
              Either via the SLIP port or a DLCI.  This reflects how
              your Management scheme is configured (read only)."
          ::= { tfrapCfgIpTable 5 }

tfrapCfgIpTelnetEnable   OBJECT-TYPE
          SYNTAX      INTEGER
          {
              enable-telnet  (1),
              disable-telnet (2)
          }
          ACCESS      read-write
          STATUS      mandatory
          DESCRIPTION
             "Enables/Disables the telnet feature.
              (1) enable-telnet
              (2) disable-telnet"
          ::= { tfrapCfgIpTable 6 }

tfrapCfgIpTelnetAutoLogOut   OBJECT-TYPE
          SYNTAX      INTEGER
          {
              autologout-at-15-minutes (1),
              disable-autologout       (2),
              autologout-at-3-minutes  (3),
              autologout-at-5-minutes  (5),
              autologout-at-10-minutes (10),
              autologout-at-30-minutes (30),
              autologout-at-60-minutes (60)
          }
          ACCESS      read-write
          STATUS      mandatory
          DESCRIPTION
             "If Telnet Auto logout is enabled the unit
              will automatically disconnect from a Telnet
              session after a period of inactivity (absence 
              of key strokes from remote terminal). 
              (2) disables this feature
              (1) auto logout after 15 minutes inactivity
              (3) auto logout after 3 minutes inactivity
              (5) auto logout after 5 minutes inactivity
              (10) auto logout after 10 minutes inactivity
              (30) auto logout after 30 minutes inactivity
              (60) auto logout after 60 minutes inactivity"
          ::= { tfrapCfgIpTable 7 }


--
--       The TFTP Configuration Table
--              This table contains the Configuration for the TFTP
--              (Trivial File Transfer Protocol) support on the unit. 
--              TFTP is an ip-based protocol used by the unit for 
--              software upgrades.

tfrapCfgTftpTable OBJECT IDENTIFIER ::= { tfrapCfgMgmtTable 2 }

tfrapCfgTftpInitiate OBJECT-TYPE
          SYNTAX DisplayString (SIZE (0..8))
          ACCESS write-only
          STATUS mandatory
          DESCRIPTION
             "Setting this object to a value that matches
              the TFTP Password will command the unit to
              attempt a TFTP file transfer. A TFTP profile
              including host ip address, dlci value, interface, 
              and file name must first be configured."
          ::= {tfrapCfgTftpTable 1}

tfrapCfgTftpIpAddress   OBJECT-TYPE
          SYNTAX     IpAddress
          ACCESS     read-write
          STATUS     mandatory
          DESCRIPTION
             "The IP address of the TFTP host with which
              the unit will attempt to establish a TFTP
              session when initiated."
          ::= {tfrapCfgTftpTable 2}
   
tfrapCfgTftpFilename OBJECT-TYPE
          SYNTAX DisplayString (SIZE (0..80))
          ACCESS read-write
          STATUS mandatory
          DESCRIPTION
             "The name of the file located on the TFTP host
              that will be transferred to the unit. Typically 
              this is a product-specific software image that
              will be programmed into unit FLASH. The unit 
              provides several levels of checking to verify 
              the validity and integrity of this file. 
              Note - depending upon the host, this file name 
              may be case sensitive."
          ::= {tfrapCfgTftpTable 3}

tfrapCfgTftpInterface OBJECT-TYPE
          SYNTAX      INTEGER
          {
              dte-interface  (1),
              t1-interface   (2),
              slip-interface (3)
          }
          ACCESS read-write
          STATUS mandatory
          DESCRIPTION
             "The physical interface out which the TFTP host
              is located. This parameter is only required for
              Piggyback and Bi-directional in-band frame relay
              managed applications. With Local and Remote in-band 
              and SLIP-based applications the interface is known
              and Sets to this will be ignored."
          ::= {tfrapCfgTftpTable 4}

tfrapCfgTftpDlci OBJECT-TYPE
          SYNTAX INTEGER (-1..63487)
          ACCESS read-write
          STATUS mandatory
          DESCRIPTION
            "The local DLCI value on which the TFTP host can be 
             reached. This DLCI should be active prior to 
             initiating the TFTP session. This parameter is only 
             required for Piggyback in-band frame relay managed 
             applications. With Private management (Local, Remote 
             or Bi-directional in-band applications) the DLCI is
             known and will be reported here (Sets will be ignored). 
             In SLIP-based applications the DLCI value is not 
             applicable and a value of -1 is reported (Sets will 
             be ignored)."
          ::= {tfrapCfgTftpTable 5}

tfrapCfgTftpStatus OBJECT-TYPE
          SYNTAX INTEGER
          {
              inactive          (1),
              requested         (2),
              transferring      (3),
              programming       (4),
              transfer-aborted  (5),
              host-no-reply     (6),
              file-not-found    (7),
              invalid-file      (8),
              corrupt-file      (9),
              successful        (10)
          }
          ACCESS read-write
          STATUS mandatory
          DESCRIPTION
             "The status of current or most recent TFTP operation.
              (1) TFTP inactive, sets to this value will abort the session
              (2) TFTP requested
              (3) TFTP transferring
              (4) TFTP programming FLASH - unit will reset 
              (5) TFTP fail: session aborted by user or error condition
              (6) TFTP fail: host no reply -  verify TFTP profile and host
              (7) TFTP fail: file not found - verify file name and location
              (8) TFTP fail: invalid file - file rejected by unit as inappropriate
              (9) TFTP fail: corrupt file - session terminated due to checksum error
              (10) TFTP transfer successful and file has been verified"
          ::= {tfrapCfgTftpTable 6}


tfrapCfgTftpNumBytes OBJECT-TYPE
          SYNTAX Counter
          ACCESS      read-only
          STATUS      mandatory
          DESCRIPTION
            "The number of Bytes from the ROM image that have been 
             TFTP'd to the unit"
          ::= {tfrapCfgTftpTable 7}


--
--       The SNMP Configuration Table
--              This table contains the Configuration for the SNMP
--              support on the TFRAP T1 CSU. This includes Trap
--              destinations and any other Trap-related parameters.

tfrapCfgSnmpTable OBJECT IDENTIFIER ::= { tfrapCfgMgmtTable 3 }

tfrapCfgSnmpFrTrap   OBJECT-TYPE
          SYNTAX      INTEGER
          {
              enabled        (1),
              disabled       (2)
          }
          ACCESS      read-write
          STATUS      mandatory
          DESCRIPTION
             "Controls whether or not the Frame Relay DLCI
              status change traps are issued.  These traps are
              tfrapDLCIActiveTrap and tfrapDLCIInactiveTrap.
              (1) FR Trap enabled - a trap will be sent each time 
                  an individual DLCI changes status between active 
                  and inactive. 
              (2) FR Trap disabled -  DLCI state change traps are not sent."
          ::= { tfrapCfgSnmpTable 1 }

tfrapCfgSnmpTrapMuting    OBJECT-TYPE
          SYNTAX      INTEGER (0..10080)
          ACCESS      read-write
          STATUS      mandatory
          DESCRIPTION
             "Controls whether Traps are Sent or Muted. If traps
              are Muted then a single trap (#75) will be periodically
              issued by the unit at the programmed frequency. If Muting
              is Disabled then the full set of Trap events are reported
              accordingly.
              (0) Disable Trap Muting
              (30-10080) Trap Muting frequency in minutes."
         ::= { tfrapCfgSnmpTable 3 }
 
tfrapCfgSnmpUtilTrapEnable  OBJECT-TYPE
        SYNTAX  INTEGER
       {
           enable  (1),
           disable (2)
       }
        ACCESS  read-write
        STATUS  mandatory
        DESCRIPTION
           "Enables or disables the sending of per-DLCI
            utilization traps.
            (1) enable utilization traps
            (2) disable utilization traps "
        ::= { tfrapCfgSnmpTable 6 }
     
tfrapCfgSnmpMgrClearN   OBJECT-TYPE
        SYNTAX  INTEGER
        ACCESS  write-only
        STATUS  mandatory
        DESCRIPTION
           " Deletes the number of entries in the tfrapCfgSnmpMgrTable
             indicated by the value.  If the value is a positive number
             the entries will be deleted starting from the first entry.
             If the value is negative the entries will be deleted 
             starting from the last entry. "
        ::= { tfrapCfgSnmpTable 7 }
         
tfrapCfgSnmpMgrTable   OBJECT-TYPE
         SYNTAX   SEQUENCE OF TfrapCfgSnmpMgrEntry
         ACCESS   not-accessible
         STATUS   mandatory
         DESCRIPTION
            "The table of SNMP manager profiles to which
             traps are sent. In all managed modes an SNMP
             trap mangager's ip address is required as a 
             minimum. Additionally for Piggyback managed
             units the DLCI and interface must also be 
             configured appropriately. For Local, Remote
             and SLIP-based management, the DLCI and
             interface are implied and need not be 
             configured as part of this profile."
          ::= { tfrapCfgSnmpTable 2 }

tfrapCfgSnmpMgrEntry   OBJECT-TYPE
         SYNTAX   TfrapCfgSnmpMgrEntry
         ACCESS   not-accessible
         STATUS   mandatory
         DESCRIPTION
            "The SNMP trap manager profiles to which the unit
             sends TRAPs."
         INDEX { tfrapCfgSnmpMgrIndex }
            ::= { tfrapCfgSnmpMgrTable 1 }

TfrapCfgSnmpMgrEntry ::=
         SEQUENCE {
             tfrapCfgSnmpMgrIndex       INTEGER,
             tfrapCfgSnmpMgrIP          IpAddress,
             tfrapCfgSnmpMgrInterface   INTEGER,
             tfrapCfgSnmpMgrDlci        INTEGER
         }

tfrapCfgSnmpMgrIndex OBJECT-TYPE
         SYNTAX   INTEGER
         ACCESS   read-only
         STATUS   mandatory
         DESCRIPTION
            "The index to the list of SNMP managers receiving TRAPs."
         ::= { tfrapCfgSnmpMgrEntry 1 }

tfrapCfgSnmpMgrIP   OBJECT-TYPE
         SYNTAX      IpAddress
         ACCESS      read-write
         STATUS      mandatory
         DESCRIPTION
            "The IP address of a SNMP manager to receive this node's TRAPs.
             Setting this value to 0.0.0.0 will disable the issuance of
             traps to the indexed manager."
         ::= { tfrapCfgSnmpMgrEntry 2 }

tfrapCfgSnmpMgrInterface OBJECT-TYPE
         SYNTAX      INTEGER
         {
              dte-interface  (1),
              t1-interface   (2),
              slip-interface (3)
         }
         ACCESS      read-write
         STATUS      mandatory
         DESCRIPTION
            "The interface out which the indexed trap manager can be
             reached. This entry is required in Piggyback and Bi-directional 
             in-band managed applications. In Local, Remote and SLIP-based
             applications, the interface is known and this parameter is
             ignored.
             (1) Traps sent out DTE interface for this manager
             (2) Traps sent out T1 interface for this manager
             (3) Traps sent out SLIP interface (async maint port)

             When the node is configured for SLIP, a GET on this MIB
             object will return slip-interface(3) and a SET of this MIB
             object to slip-interface(3) is allowed but unnecessary.

             When the node is not configured for SLIP, this MIB
             object can be SET to dte-interface(1) or t1-interface(2);
             slip-interface(3) would be rejected."
         ::= { tfrapCfgSnmpMgrEntry 3 }

tfrapCfgSnmpMgrDlci OBJECT-TYPE
         SYNTAX      INTEGER
         ACCESS      read-write
         STATUS      mandatory
         DESCRIPTION
            "The DLCI out which the indexed trap manager can be
             reached. This entry is required in Piggyback in-band 
             managed applications. In Private in-band applications
             the DLCI is known and Sets to this parameter will be 
             ignored. In SLIP mode the DLCI is not applicable,
             Sets will be ignored and a -1 will be returned as the 
             DLCI value."
         ::= { tfrapCfgSnmpMgrEntry 4 }

--
--       The Communication Port Configuration Table
--              This table contains the Communications Port Configuration
--              information for the TFRAP T1 CSU. 

tfrapCfgCommTable OBJECT IDENTIFIER ::= { tfrapCfgMgmtTable 4 }

   --    DESCRIPTION   
   --       "The Communication Port Configuration table contains
   --        parameters for the RS232/RJ48 Maint/Console port on the
   --        TFRAP. 

tfrapCfgCommMode      OBJECT-TYPE
     SYNTAX      INTEGER
          {
              vt100     (1),
              slip      (2)
          }
     ACCESS      read-write
     STATUS      mandatory
     DESCRIPTION
        "The protocol running on the Maintenance/Comm port (console).
         Setting this to SLIP mode will automatically disable
         in-band management if it's enabled.
         (1) VT100 for directly attached async terminal
         (2) SLIP - Serial Line IP out-of-band management"
     ::= { tfrapCfgCommTable 1 }

tfrapCfgCommBaud OBJECT-TYPE
     SYNTAX      INTEGER
     {
         baud-2400   (2),
         baud-9600   (4),
         baud-19200  (5),
         baud-38400  (6)
     }
     ACCESS      read-write
     STATUS      mandatory
     DESCRIPTION
        "Asynchronous baud rate for the Maintenance/Comm port 
         (Console). This must be configured to match either the 
         VT100 compatible terminal, MODEM support or the SLIP Terminal  
         Server depending upon the Comm port mode. 
         (2) baud-2400 
         (4) baud-9600
         (5) baud-19200
         (6) baud-38400"
     ::= { tfrapCfgCommTable 2 }

tfrapCfgCommDataBits OBJECT-TYPE
     SYNTAX      INTEGER
     {
         databits-7 (1),
         databits-8 (2)
     }
     ACCESS      read-write
     STATUS      mandatory
     DESCRIPTION
        "Asynchronous data format for the Maintenance/Comm port 
         (Console). This must be configured to match either the 
         VT100 compatible terminal or the SLIP Terminal Server 
         depending upon the Comm port mode.
         (1) 7 databits per character
         (2) 8 databits per character"
     ::= { tfrapCfgCommTable 3 }

tfrapCfgCommStopBits OBJECT-TYPE
     SYNTAX      INTEGER
     {
         stopbits-1 (1),
         stopbits-1-5 (2),
         stopbits-2 (3)
     }
     ACCESS      read-write
     STATUS      mandatory
     DESCRIPTION
        "Asynchronous intercharacter protocol for the Maintenance/Comm 
         port (Console). This must be configured to match either the 
         VT100 compatible terminal or the SLIP Terminal Server 
         depending upon the Comm port mode.
         (1) 1 stopbit 
         (2) 1.5 stopbits 
         (3) 3 stopbits"
     ::= { tfrapCfgCommTable 4 }

tfrapCfgCommParity OBJECT-TYPE
     SYNTAX      INTEGER
     {
         no-parity   (1),
         odd-parity  (2),
         even-parity (3)
     }
     ACCESS      read-write
     STATUS      mandatory
     DESCRIPTION
        "Asynchronous parity checking protocol for the 
         Maintenance/Comm port (Console). This must be configured 
         to match either the VT100 compatible terminal or the SLIP 
         Terminal Server depending upon the Comm port mode.  
         (1) no parity
         (2) odd-parity 
         (3) even-parity"
     ::= { tfrapCfgCommTable 5 }

tfrapCfgCommFlowCtrl OBJECT-TYPE
     SYNTAX      INTEGER
     {
         no-flow-control (1)
     }
     ACCESS      read-write
     STATUS      mandatory
     DESCRIPTION
        "Flow Control for this Communication port.  Values
         are no-flow-control (1)."
     ::= { tfrapCfgCommTable 6 }

--
--       The DLCI Management Configuration Table
--              This table contains the Configuration for in-band
--              Frame Relay management. This includes in-band mode,
--              the management PVC's local DLCI address, format and 
--              parameters related to Frame Relay management frame
--              format.


tfrapCfgFrDLCITable OBJECT IDENTIFIER ::= { tfrapCfgMgmtTable 5 }

tfrapCfgFrDLCIMode  OBJECT-TYPE
          SYNTAX      INTEGER
          {
              inactive        (1),
              local           (2),
              remote          (3),
              bidirectional   (4),
              piggyback       (5),
              fixedDCE        (6)
          }
          ACCESS      read-write
          STATUS      mandatory
          DESCRIPTION
             "In-band Frame Relay management mode. A variety of options
              exist which are differentiated by how PVCs can be provisioned
              to manage the unit and the resulting impact to the logical
              processing of Link Management Protocol messages (LMI spoofing 
              and sourcing). The unit is designed to support these management 
              modes even in non-provisioned or failed frame relay networks.
              This setting also has implications upon how networking protocols 
              such as ARP and InARP are handled by the unit. 
              (1) inactive: in-band management is not enabled
              (2) local DLCI mode: in-band managed using a private dedicated DLCI 
                  accessible via the DTE port only. A DLCI value is configured 
                  which, through LMI spoofing, will only be visible to the DTE 
                  equipment and need not be provisioned on the WAN. All traffic on
                  this DLCI will be terminated by the unit.
              (3) remote DLCI mode: in-band managed using a private dedicated DLCI 
                  accessible via the WAN port only. A DLCI value is configured 
                  which, through LMI spoofing, will only be visible from the WAN 
                  side and will not be seen by any DTE equipment. All traffic on
                  this DLCI will be terminated by the unit.
              (4) bidirectional mode: in-band managed using a private dedicated DLCI 
                  accessible through either port. A DLCI value is configured 
                  which is expected to be fully provisioned in the frame relay 
                  network but dedicated to the management function of this particular 
                  unit. All traffic on this DLCI will be terminated by the unit.
              (5) piggyback mode: in-band managed using any DLCI on any interface. A
                  DLCI value is defined that becomes the default DLCI that will be
                  maintained by the unit during network or LMI failure conditions. 
                  The unit will terminate and respond accordingly to management and
                  networking data while transparently passing on user data.
              (6) fixed DCE mode: special mode of operation to support frame relay
                  applications that do not include a switch (frame relay DCE). The 
                  unit will independently respond to LMI requests on each interface
                  and will provision the configured DLCI to each Frame Relay DTE device.
                  Except for this, the unit behaves like piggyback."
          ::= { tfrapCfgFrDLCITable 1 }

tfrapCfgFrDLCIValue  OBJECT-TYPE
          SYNTAX      INTEGER (16..63487)
          ACCESS      read-write
          STATUS      mandatory
          DESCRIPTION
             "If in-band management is being used this DLCI value should be defined. 
              In all modes of in-band management with the LMI Sourcing feature enabled 
              the unit may provision this DLCI during LMI failure to facilitate management 
              access. In Private modes (Local, Remote, and Bidirectional) this is the 
              dedicated DLCI for management data and address resolution protocols - all 
              other traffic on this DLCI will be discarded. In Piggyback mode this DLCI 
              is treated like all others except during LMI failure sourcing when it may
              be provisioned by the unit. In Piggyback mode if InARP is enabled on a single 
              DLCI then this value defines that DLCI."
          ::= { tfrapCfgFrDLCITable 2 }

tfrapCfgFrDLCIEncap   OBJECT-TYPE
          SYNTAX      INTEGER
          {
              rfc1490        (1),
              rfc1490snap    (2),
              auto           (3),
              cisco          (4)
          }
          ACCESS      read-write
          STATUS      mandatory
          DESCRIPTION
             "This is the protocol used for enacapsulating and formatting
              ip data for Frame Relay transmission. This setting is specific
              to management data to and from the unit.
              (1) RFC1490 - per IETF standard with Network Level 
                  Protocol ID (NLPID) set for IP encapsulation.
              (2) RFC1490 SNAP/IP - per IETF standard with NLPID set 
                  for Sub-Network Access Protocol (SNAP).
              (3) auto - adjusts to either of these encapsulation techniques
                  as required. 
              (4) Cisco - proprietary encapsulation (4-byte header)."
          ::= { tfrapCfgFrDLCITable 3 }

tfrapCfgFrDLCIMgmtDE   OBJECT-TYPE
          SYNTAX      INTEGER
          {
              no-DE-bit-0     (1),
              yes-DE-bit-1    (2)
          }
          ACCESS      read-write
          STATUS      mandatory
          DESCRIPTION
             "Provides user control over the state of the Frame Relay Discard
              Eligibility bit of all management frames generated by
              the unit. Frames marked DE=1 are more likely to be dropped in a 
              congested Frame Relay network than those that are DE=0. Heavily 
              congested circumstances can cause both to be dropped. Additionally,
              frames marked DE=0 may get re-marked to DE=1 by intervening
              equipment.
              (1) DE bit cleared to 0: frame is not discard eligible
              (2) DE bit set to 1: frame is discard eligible"
          ::= { tfrapCfgFrDLCITable 4 }

--
--       The Application Configuration Table
--              This table contains the Application (system) Configuration
--              information for the TFRAP T1 CSU. This includes system
--              timing and user-application type.

tfrapCfgAppTable   OBJECT IDENTIFIER ::= { tfrapConfiguration 2 }

tfrapCfgAppClockSource OBJECT-TYPE
          SYNTAX      INTEGER
          {
               internal (1),
               network  (2),
               dte      (3)
          }
          ACCESS      read-write
          STATUS      mandatory
          DESCRIPTION
             "Timing source for transmission of data towards the WAN
              and for the generation of DTE clocking. There should be 
              only one source per end-to-end WAN link.  Unit is typically
              network timed in a point-to-network application.
              (1) internal: derive timing from a high-stability on-board
                  crystal oscillator.
              (2) network: or Loop timing, derive timing from the signal
                  received at the WAN interface
              (3) dte: derive timing from the clock presented by the DTE
                  equipment on the Terminal Timing(TT)/Transmit Clock 
                  External (TCE) leads. This setting expects the DTE timing 
                  mode to be Loop 1 and the DTE device to be generating a 
                  clock at the DTE data rate."  
          ::= { tfrapCfgAppTable 1 }

tfrapCfgAppCircuitId    OBJECT-TYPE
          SYNTAX      DisplayString (SIZE (0..30))
          ACCESS      read-write
          STATUS      mandatory
          DESCRIPTION
             "Alphanumeric circuit identifier may be provided by the service 
              provider for reference or assigned arbitrarily per user
              requirements."
          ::= { tfrapCfgAppTable 2 }

tfrapCfgAppType    OBJECT-TYPE
          SYNTAX      INTEGER
          {
               dedicated   (1),
               frame-relay (2)   
          } 
          ACCESS      read-write
          STATUS      mandatory
          DESCRIPTION
             "This unit provides many features specifically adapted 
              to Frame Relay transmission links; this includes diagnostic 
              utilities, statistical analysis, protocol trends, quality of 
              service reporting, and in-band SNMP management. If the unit 
              will be operating in a Frame Relay network the Application Type
              must be set to Frame Relay to enable these features. To 
              operate in a non-Frame Relay network or to bypass this feature
              set the unit may be placed in Dedicated mode and will emulate a
              more familiar DSU/CSU. Note - changing this value will 
              automatically change the Application Format setting and vice 
              versa.
              (1) dedicated: protocol-independent transparent DSU/CSU
              (2) Frame Relay: Frame and protocol aware DSU/CSU"
          ::= { tfrapCfgAppTable 3 }

tfrapCfgAppFormat OBJECT-TYPE
          SYNTAX      INTEGER
          {
               cbo         (1),
               hdlc        (2)
          }
          ACCESS      read-write
          STATUS      mandatory
          DESCRIPTION
              "Refer to Application Type. Frame Relay is based upon
               HDLC framing. To operate in a Frame Relay application
               the Format must be set for HDLC. To operate in a
               protocol-independent application the Format must be 
               set for Constant Bit Operation (CBO). Note - changing 
               this value will automatically change the Application 
               Type setting and vice versa
               (1) CBO: protocol-independent transparent DSU/CSU
               (2) HDLC: Frame and protocol aware DSU/CSU"
          ::= { tfrapCfgAppTable 4 }

tfrapCfgAppLpbkTimeout OBJECT-TYPE
          SYNTAX      INTEGER (0..1440)
          ACCESS      read-write
          STATUS      mandatory
          DESCRIPTION
             "The length of time a service-impacting loopback
              or diagnostic utility may run before automatically 
              returning to normal operation. This setting will
              override any alternatively timed tests (such as 
              VBERT).
              (0) Loopbak Timeout Disabled
              (1-1440) Loopback Timeout"
          ::= { tfrapCfgAppTable 5 }

tfrapCfgAppPerfBuffLimit OBJECT-TYPE
          SYNTAX      INTEGER (0..512)
          ACCESS      read-write
          STATUS      mandatory
          DESCRIPTION
             "This value controls the throttling mechanism
              used to determine the optimum level of statistical
              processing versus manageability of the unit. The
              lower the value (1 - 128), the unit becomes more
              responsive to management commands during very heavy
              utilization at the possible expense of statistical 
              accuracy.  The larger the value (129 - 512), the more 
              accurate the TFRAP performs statistical analysis of the 
              frames but management may seem slow or unresponsive 
              during periods of very heavy link utilization.
              NOTE: A value of 0 disables statistical processing entirely."
          ::= { tfrapCfgAppTable 10 }


--
--       The T1 Configuration Table
--              This table contains the T1 port Configuration
--              information for the TFRAP CSU.

tfrapCfgT1Table   OBJECT IDENTIFIER ::= { tfrapConfiguration 3 }

   --     DESCRIPTION
   --        "The T1 Port Configuration table contains
   --         parameters for the Framed TDM (T1) port on the
   --         TFRAP. "

tfrapCfgT1Framing    OBJECT-TYPE
     SYNTAX      INTEGER 
     {
        d4              (1),
        esf-54016       (2),
        esf-ansi        (3)
     }
     ACCESS        read-write
     STATUS        mandatory
     DESCRIPTION
        "Type of Framing on this T1 Line.  Check with your service 
         provider to determine value.  
         (1) D4 -  also known as Superframe or SF.
         (2) ESF 54016 - Extended Superframe supporting the Facility Data 
             Link per AT&T pub 54016.  ESF provides enhanced performance
             monitoring capabilities over the FDL. 
         (3) ESF ANSI - Extended SuperFrame supporting the Facility Data 
             Link per ANSI T1.403 standard. ESF provides enhanced performance
             monitoring capabilities over the FDL."
     ::= { tfrapCfgT1Table 1 }

tfrapCfgT1LineEncoding    OBJECT-TYPE
     SYNTAX      INTEGER 
     {
        ami             (1),
        b8zs            (2)
     }
     ACCESS        read-write
     STATUS        mandatory
     DESCRIPTION
        "T1 interface bipolar encoding scheme.  Check with your 
         service provider to determine value. B8ZS, which inherently 
         provides ample 'ones-density', is recommended. AMI users 
         must pay special attention to the 'ones-density' requirements
         of the service provider.
         (1) B8ZS -  intercepts and encodes streams of 8 consecutive zeros
             and transmits them as a special pattern including Bipolar or 
             Line Code Violations. Function not supported on certain networks.
         (2) AMI - Alternate Mark Inversion - sends the user data without
             introducing controlled BPVs."
     ::= { tfrapCfgT1Table 2 }

tfrapCfgT1Density    OBJECT-TYPE
     SYNTAX      INTEGER 
     {
        no-density              (1),
        twelve-half-percent     (2),
        one-in-16               (3),
        one-in-64               (4)
     }
     ACCESS        read-write
     STATUS        mandatory
     DESCRIPTION
        "CSU 'ones density' monitor. Defines the maximum number of
         consecutive zeros that can be transmitted to the WAN. 
         If density monitoring is enabled, the composite signal 
         is guaranteed to meet the selected density threshhold at 
         the expense of user data.
         (1) No Density Monitoring - unit will transparently transmit
             user data without regard for ones density. Recommended for
             use in B8ZS applications, in nx56K applications where
             bit-7 stuffing is configured for DTE Channel Density, and 
             when an external CSU is used.
         (2) 12.5% - unit will maintain a sliding window and will assure
             a minumum of 12.5% or an average of 1 in 8 ones. 
         (3) 1 in 16 - unit will guarantee that no more than 15 consecutive
             zeros will be transmit to the WAN.
         (4) 1 in 64 - unit will guarantee that no more than 63 consecutive
             zeros will be transmit to the WAN."
     ::= { tfrapCfgT1Table 3 }

tfrapCfgT1Interface    OBJECT-TYPE
     SYNTAX      INTEGER 
     {
        dsx-1           (1),
        csu             (2)  
     }
     ACCESS        read-write
     STATUS        mandatory
     DESCRIPTION
        "Enables the unit's internal CSU functionality. Typical 
         network access requires a CSU to condition the WAN signal,
         guard against network hazards, and provide access to 
         service personnel for network maintenance.
         (1) Disables internal CSU and unit operates as a DSX-1 cross
             connect device. This should be the setting if the unit is
             cabled to an external CSU device providing network acces.
             CSU.
         (2) Enables internal CSU and corresponding feature set which 
             includes density monitoring, line build-out pulse shaping,
             ESF facility data link, and certain diagnostic functions.
             This should be the seting if the unit is directly cabled
             to the service provider's equipment (such as a smart jack)."
     ::= { tfrapCfgT1Table 4 }

tfrapCfgT1LboSetting    OBJECT-TYPE
     SYNTAX      INTEGER 
     {
        zero-db         (1),
        n7-5-db         (2),
        n15-db          (3)
     }
     ACCESS        read-write
     STATUS        mandatory
     DESCRIPTION
        "CSU Line Build Out (LBO). This feature provides selectable output
         signal strength. Consult service provider for proper setting. Signal
         may require attenuation to equalize it with neighboring equipment
         or under certain cabled access conditions. Not applicable if CSU
         functions are diabled (interface type = dsx-1)
         (1) 0dB - standard output signal
         (2) -7.5dB - standard output signal attenuated by 7.5dB
         (3) -15dB - standard output signal attenuated by 15 dB."
     ::= { tfrapCfgT1Table 5 }


--
--       The DTE Configuration Table
--              This table contains the DTE port Configuration
--              information for the TFRAP CSU/DSU.

tfrapCfgDteTable   OBJECT IDENTIFIER ::= { tfrapConfiguration 4 }

   --   DESCRIPTION
   --      "The Dte Port Configuration table contains
   --       parameters for the Serial (DTE) port's 
   --       physical link. The DTE port typically connects
   --       to a customer's equipment such as a Router/FRAD and
   --       formats this data for appropriate WAN transmission."
     
tfrapCfgDteIntfType    OBJECT-TYPE
     SYNTAX      INTEGER  
      {
         intf-v35       (3)
--         intf-rs449     (4)
      }
     ACCESS        read-only
     STATUS        mandatory
     DESCRIPTION
        "The electrical interface for the DTE port
         (3) V.35 interface
         (4) RS-449 interface (not supported)"
     ::= { tfrapCfgDteTable 1 }

tfrapCfgDteDataMode    OBJECT-TYPE
     SYNTAX      INTEGER  
     {
         data-normal     (1),
         data-invert     (2)
     }
     ACCESS        read-write
     STATUS        mandatory
     DESCRIPTION
        "Inverts the DTE data for transfer across the WAN. Can make 
         some applications, particularly HDLC-based protocols, meet 
         density requirements even across clear channel DS0s in AMI 
         mode."
     ::= { tfrapCfgDteTable 2 }

tfrapCfgDteClockMode    OBJECT-TYPE
     SYNTAX      INTEGER  
     {
        clock-normal    (1),
        clock-invert    (2)
     }
     ACCESS        read-write
     STATUS        mandatory
     DESCRIPTION
        "This selection controls how the unit internally latches 
         the transmit data from the DTE. Normal will sample
         data with the rising edge of the selected TX Clock, 
         Invert will sample data with the falling edge of the 
         selected TX Clock. The TX Clock is selected using 
         CfgDteTiming. This clock invertion is most useful when 
         loop-2 timing is used - particularly at higher rates 
         and with long cable runs. Only in rare circumstances 
         will clock-invert be used with loop-1 timing. If the 
         DTE Interface TX statistics are indicating excessive 
         crc errors or aborts then changing this setting may have
         some benefit.
         (1) normal
         (2) invert"
     ::= { tfrapCfgDteTable 3 }

tfrapCfgDteTiming    OBJECT-TYPE
     SYNTAX      INTEGER  
     {
        loop-1  (1),
        loop-2  (2)
     }
     ACCESS        read-write
     STATUS        mandatory
     DESCRIPTION
        "Serial DTE Transmit Timing mode. Loop-1 (1) uses the clock  
         returned from the DTE (TT/TCE) to sample tx data, Loop-2 (2) 
         uses the clock (ST/TC) generated by the node to sample tx 
         data. Loop-1 is the preferred mode. Loop-2 timing could experience
         data errors at high rates or due to long DTE cable runs - may
         need to Invert the clock (see CfgDteClockMode).
         (1) Loop 1: external clock returned from DTE with data
         (2) Loop 2: internal clock used to sample incoming data"
     ::= { tfrapCfgDteTable 4 }

tfrapCfgDteLineRate    OBJECT-TYPE
     SYNTAX      INTEGER  (0..1536000)
     ACCESS        read-only
     STATUS        mandatory
     DESCRIPTION
        "Serial DTE Data Rate in bits per second. Valid
         rates depend upon channel density selection: nX56K for 
         bit-7-stuffing, and nX64K for clear-channel (n is an 
         integer 1-24 inclusive). This read-only value is the
         value which was most recently set through CfgDteConnRate; 
         in the event of a connection failure, this field should be
         examined along with CfgDteChannelDensity and CfgDteStartDso 
         to determine the parameter mismatch that caused the connection 
         failure."
     ::= { tfrapCfgDteTable 5 }

tfrapCfgDteChannelDensity    OBJECT-TYPE
     SYNTAX      INTEGER  
     {
        bit-7-stuff     (56),
        clear-channel   (64)
     }
     ACCESS        read-only
     STATUS        mandatory
     DESCRIPTION
        "Packing of serial data into T1 DS0's. Bit-7-stuff 
         supports DTE rates of nX56Kb/s (from 56K to 1344K) and 
         provides sufficient ones-density on any circuit. 
         Clear-channel allows DTE rates of nX64Kb/s (from 64K
         to 1.536M) and may require an additional means 
         of density enforcement (eg, B8ZS). This read-only value 
         is the value which was most recently set through CfgDteConnDensity; 
         in the event of a connection failure, this field should be 
         examined along with CfgDteLineRate and CfgDteStartDso to 
         determine the parameter mismatch that caused the connection 
         failure."
     ::= { tfrapCfgDteTable 6 }

tfrapCfgDteStartDs0            OBJECT-TYPE
     SYNTAX        INTEGER
     {
         ds0-01        (1),
         ds0-02        (2),
         ds0-03        (3),
         ds0-04        (4),
         ds0-05        (5),
         ds0-06        (6),
         ds0-07        (7),
         ds0-08        (8),
         ds0-09        (9),
         ds0-10        (10),
         ds0-11        (11),
         ds0-12        (12),
         ds0-13        (13),
         ds0-14        (14),
         ds0-15        (15),
         ds0-16        (16),
         ds0-17        (17),
         ds0-18        (18),
         ds0-19        (19),
         ds0-20        (20),
         ds0-21        (21),
         ds0-22        (22),
         ds0-23        (23),
         ds0-24        (24),
         no-current-connections (40),
         non-continuous-ds0s (41)
     }
     ACCESS        read-only
     STATUS        mandatory
     DESCRIPTION
        "T1 WAN includes 24 DS0's available for user data. Each DS0
         carries either 56Kbit/sec (bit-7-stuffing) or 64KBit/sec 
         (clear-channel). This value is the starting DS0 used by the 
         node to allocate DS0s to match the DTE's data rate. Sequential, 
         contiguous DS0s are assigned as required. The number of DS0s 
         required is based upon the DTE Data Rate and DTE Channel Mapping. 
         This read-only value is the value which was most recently set 
         through DteCfgConnStartDs0; in the event of a connection failure, 
         this field should be examined along with CfgDteLineRate and 
         CfgDteChanelDensity to determine the parameter mismatch that 
         caused the connection failure."
     ::= { tfrapCfgDteTable 7 }

tfrapCfgDteConnStatus         OBJECT-TYPE  
     SYNTAX       INTEGER
     {
        connections-valid      (1),
--      incorrect-bandwidth    (2),
--      bandwidth-conflict     (3),
        no-current-connections (4)
     }
     ACCESS       read-only
     STATUS       mandatory
     DESCRIPTION
        "The current status of the WAN to DTE mappings.
         (1) connections valid and DS0s allocated to DTE data.
         (4) no connections configured between WAN and DTE."
     ::= { tfrapCfgDteTable 8 }

tfrapCfgDteConnStartDs0            OBJECT-TYPE
     SYNTAX        INTEGER
     {
         ds0-01        (1),
         ds0-02        (2),
         ds0-03        (3),
         ds0-04        (4),
         ds0-05        (5),
         ds0-06        (6),
         ds0-07        (7),
         ds0-08        (8),
         ds0-09        (9),
         ds0-10        (10),
         ds0-11        (11),
         ds0-12        (12),
         ds0-13        (13),
         ds0-14        (14),
         ds0-15        (15),
         ds0-16        (16),
         ds0-17        (17),
         ds0-18        (18),
         ds0-19        (19),
         ds0-20        (20),
         ds0-21        (21),
         ds0-22        (22),
         ds0-23        (23),
         ds0-24        (24),
         no-current-connections (40),
         non-continuous-ds0s (41)
     }
     ACCESS        read-write
     STATUS        mandatory
     DESCRIPTION
        "T1 WAN includes 24 DS0's available for user data. Each DS0
         carries either 56Kbit/sec (bit-7-stuffing) or 64KBit/sec 
         (clear-channel). This value is the starting DS0 used by the 
         node to allocate DS0s to match the DTE's data rate. Sequential, 
         contiguous DS0s are assigned as required. The number of DS0s 
         required is based upon the DTE Data Rate and DTE Channel Mapping. 
         Consult WAN service provider for the appropriate setting here in 
         a fractional T1 application."
     ::= { tfrapCfgDteTable 9 }

tfrapCfgDteConnRate             OBJECT-TYPE
     SYNTAX        INTEGER (0..1536000)
     ACCESS        read-write
     STATUS        mandatory
     DESCRIPTION
        "Serial DTE Data Rate in bits per second. Valid
         rates depend upon channel density selection: nX56K for 
         bit-7-stuffing, and nX64K for clear-channel (n is an 
         integer 1-24 inclusive). Rates are entered in bits/sec, 
         for example, 128000 for a 128Kbit/sec DTE data rate."
     ::= { tfrapCfgDteTable 10 }

tfrapCfgDteConnDensity          OBJECT-TYPE
     SYNTAX        INTEGER 
     {
         bit-7-stuff     (56),
         clear-channel   (64)
     }
     ACCESS        read-write
     STATUS        mandatory
     DESCRIPTION
        "Packing of serial data into T1 DS0's. Bit-7-stuff 
         supports DTE rates of nX56Kb/s (from 56K to 1344K) and 
         provides sufficient ones-density on any circuit. 
         Clear-channel supports DTE rates of nX64Kb/s (from 64K
         to 1.536M) and may require an additional means 
         of density enforcement (eg, B8ZS).
         (56) Bit 7 Stuffing (nx56K data rate, n=1-24)
         (64) Clear Channel (nx64K data rate, n=1-24)"
     ::= { tfrapCfgDteTable 11 }

tfrapCfgDteConnDs0Required         OBJECT-TYPE
     SYNTAX        INTEGER (0..24)
     ACCESS        read-only
     STATUS        mandatory
     DESCRIPTION
      "The number of DS0s required by the node's DTE port. 
      This is based upon the DTE data rate and channel density 
      selections."
      ::= { tfrapCfgDteTable 12 }

tfrapCfgDteConnAutoStatus         OBJECT-TYPE  
     SYNTAX       INTEGER
     {
         configuration-valid   (1),
         configuration-invalid (2),
         valid-config-updated  (3),
         invalid-cfg-no-update (4)
     }
     ACCESS       read-only
     STATUS       mandatory
     DESCRIPTION
        "There's a tight correlation among DTE data rate, starting
         DS0, and channel density. This read-only parameter reports
         the status of the most recent change to any of these connection
         parameters. If the connection request is not valid a mismatch
         among DteLineRate, DteStartDs0, and DteChannelDensity must be
         resolved
         (1) and (3) configuration valid - the previous connections profile is 
             accepted and activated
         (2) and (4) connections profile invalid, previous configuration 
             remains."
     ::= { tfrapCfgDteTable 13 }             

tfrapCfgDteConnAutoUpdate         OBJECT-TYPE  
     SYNTAX       INTEGER
     {
         config-and-connect (1)
     }
     ACCESS       write-only
     STATUS       mandatory
     DESCRIPTION
        "Updates the connection-critical parameters: line rate,
         channel density and starting ds0; drops the current
         connection; and initiate the new connection. Following
         the issuance of this command, DteAutoStatus should be 
         queried to verify the update was successful."
     ::= { tfrapCfgDteTable 14 }

tfrapCfgDteRts         OBJECT-TYPE  
     SYNTAX       INTEGER
     {
         internal-held-active (1),
         external-from-dte (2)
     }
     ACCESS       read-write
     STATUS       mandatory
     DESCRIPTION
        "Controls the reporting of the status of the DTE's Request 
         to Send (RTS) control signal, specifically the generation 
         of traps in response to control signal state changes. If
         Internally Held Active, the unit will ignore the actual 
         status and always report this signal Active. If External, 
         the unit will reflect the status as driven by the DTE; as
         such, Traps will be generated due to change of state (these
         may be useful for a network manager's assessment of interface 
         status.
         (1) Internally Held Active     
         (2) Externally Presented from DTE"
     ::= { tfrapCfgDteTable 15 }

tfrapCfgDteDtr         OBJECT-TYPE  
     SYNTAX       INTEGER
     {
         internal-held-active (1),
         external-from-dte (2)
     }
     ACCESS       read-write
     STATUS       mandatory
     DESCRIPTION
        "Controls the reporting of the status of the DTE's Data 
         Terminal Ready (DTR) control signal, specifically the 
         generation of traps in response to control signal state 
         changes. If Internally Held Active, the unit will ignore 
         the actual status and always report this signal Active. If 
         External, the unit will reflect the status as driven by the 
         DTE; as such, Traps will be generated due to change of state 
         (these may be useful for a network manager's assessment of 
         interface status.
         (1) Internally Held Active     
         (2) Externally Presented from DTE"
     ::= { tfrapCfgDteTable 16 }

tfrapCfgDteDcdOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
        "Specifies the behavior of the Data Carrier Detect (DCD)
         control signal generated by the unit towards the DTE.
         (1) inactive always: signal is permanently INACTIVE.
         (2) active always: signal is permanently ACTIVE.
         (3) reflect WAN carrier: signal echoes the received signal status 
             from the WAN.
         (4) inactive with test mode: signal is ACTIVE during normal 
             data transfer and INACTIVE during diagnostic conditions 
             that interfere with data transfer from the DTE to the WAN.
         (5) follow RTS: signal echoes the status of RTS as processed 
             from the DTE. 
         (6) reflect carrier and RTS: signal is a logical AND between 
             RTS processed from the DTE and the received signal status 
             from the WAN. No signal received from the WAN or RTS INACTIVE 
             will cause this control signal to be asserted INACTIVE.
         (7) reflect sync and RTS: signal is a logical AND between RTS 
             processed from the DTE and the frame synchronization with the WAN. 
             Red Alarm defines the threshold for declaring synchronization.
         (8) reflect LMI and carrier and RTS: signal is a logical AND 
             between RTS processed from the DTE and the carrier signal
             status from the WAN and LMI. If the unit is in an LMI 
             passthrough state then LMI is considered Active.
             LMI Inactivity timer must be non-zero for LMI to be declared 
             Inactive. In non-Frame Relay applications (type = dedicated)
             LMI will be presumed ACTIVE so this will setting is equivalent
             to (6).
         Note that there is a separate parameter for how the unit processes 
         RTS that is related to this function if options (4), (5), (6), or (7) 
         is selected, see CfgDteRts."
      ::= { tfrapCfgDteTable 18 }
 
tfrapCfgDteDsrOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
        "Specifies  the behavior of the Data Set Ready (DSR)
         control signal generated by the unit towards the DTE.
         (1) inactive always: signal is permanently INACTIVE.
         (2) active always: signal is permanently ACTIVE.
         (3) reflect WAN carrier: signal echoes the received signal status 
             from the WAN.
         (4) inactive with test mode: signal is ACTIVE during normal 
             data transfer and INACTIVE during diagnostic conditions 
             that interfere with data transfer from the DTE to the WAN.
         (5) follow RTS: signal echoes the status of RTS as processed 
             from the DTE. 
         (6) reflect carrier and RTS: signal is a logical AND between 
             RTS processed from the DTE and the received signal status 
             from the WAN. No signal received from the WAN or RTS INACTIVE 
             will cause this control signal to be asserted INACTIVE.
         (7) reflect sync and RTS: signal is a logical AND between RTS 
             processed from the DTE and the frame synchronization with the WAN. 
             Frame Red Alarm defines the threshold for declaring synchronization.
         (8) reflect LMI and carrier and RTS: signal is a logical AND 
             between RTS processed from the DTE and the carrier signal
             status from the WAN and LMI. If the unit is in an LMI 
             passthrough state then LMI is considered Active.
             LMI Inactivity timer must be non-zero for LMI to be declared 
             Inactive. In non-Frame Relay applications (type = dedicated)
             LMI will be presumed ACTIVE so this will setting is equivalent
             to (6).
         Note that there is a separate parameter for how the unit processes 
         RTS that is related to this function if options (4), (5), (6), or (7) 
         is selected, see CfgDteRts."
     ::= { tfrapCfgDteTable 19 }
 
tfrapCfgDteCtsOutput OBJECT-TYPE
     SYNTAX      INTEGER
     {
          signal-off          (1),
          signal-on           (2),
          follow-carrier      (3),
          follow-test         (4),
          follow-rts          (5),
          follow-carrier-rts  (6),
          follow-sync-rts     (7),
          follow-lmi-carr-rts (8)
     }
     ACCESS      read-write
     STATUS      mandatory
     DESCRIPTION
     "Specifies the behavior of the Clear to Send (CTS)
         control signal generated by the unit towards the DTE.
         (1) inactive always: signal is permanently INACTIVE.
         (2) active always: signal is permanently ACTIVE.
         (3) reflect WAN carrier: signal echoes the received signal status 
             from the WAN.
         (4) inactive with test mode: signal is ACTIVE during normal 
             data transfer and INACTIVE during diagnostic conditions 
             that interfere with data transfer from the DTE to the WAN.
         (5) follow RTS: signal echoes the status of RTS as processed 
             from the DTE. 
         (6) reflect carrier and RTS: signal is a logical AND between 
             RTS processed from the DTE and the received signal status 
             from the WAN. No signal received from the WAN or RTS INACTIVE 
             will cause this control signal to be asserted INACTIVE.
         (7) reflect sync and RTS: signal is a logical AND between RTS 
             processed from the DTE and the frame synchronization with the WAN. 
             Red Alarm defines the threshold for declaring synchronization.
         (8) reflect LMI and carrier and RTS: signal is a logical AND 
             between RTS processed from the DTE and the carrier signal
             status from the WAN and LMI. If the unit is in an LMI 
             passthrough state then LMI is considered Active.
             LMI Inactivity timer must be non-zero for LMI to be declared 
             Inactive. In non-Frame Relay applications (type = dedicated)
             LMI will be presumed ACTIVE so this will setting is equivalent
             to (6).
         Note that there is a separate parameter for how the unit processes 
         RTS that is related to this function if options (4), (5), (6), or (7) 
         is selected, see CfgDteRts."
     ::= { tfrapCfgDteTable 20 }

--
--       The Frame Relay and LMI Configuration Table
--              This table contains the Configuration for Frame Relay 
--              applications. This includes format, address resolution
--              and parameters associated with the unit's support of 
--              the Link Management Protocol (LMI).
--             

tfrapCfgFrTable OBJECT IDENTIFIER ::= { tfrapConfiguration 5 }

tfrapCfgFrAddrLen  OBJECT-TYPE
          SYNTAX      INTEGER
          {
              twobytes       (1),
              threebytes     (2),
              fourbytes      (3)
          }
          ACCESS      read-write
          STATUS      mandatory
          DESCRIPTION
             "Defines the size of the DLCI address field of the Frame Relay
              header. This setting must correspond to the Frame Relay 
              transmission format; typically Two bytes.
              (1) two byte DLCI address field
              (2) three byte DLCI address field
              (3) four byte DLCI address field"         
          ::= { tfrapCfgFrTable 1 }
 
tfrapCfgFrCrcMode  OBJECT-TYPE
          SYNTAX      INTEGER
          {
              discard        (1),
              passthru       (2)
          }
          ACCESS      read-write
          STATUS      mandatory
          DESCRIPTION
             "This defines the manner in which the unit handles HDLC
              protocol errors (crc errors) in a Frame Relay application. 
              If Discard is selected the unit will respond to an errored 
              frame by aborting the frame if transmission has begun; or 
              simply discarding it if transmission has not begun. If 
              Passthru is selected the unit will transmit the entire frame 
              but will place an incorrect crc in it to preserve the error 
              indication.
              (1) discard
              (2) passthru"
          ::= { tfrapCfgFrTable 2 }

tfrapCfgFrLmiType  OBJECT-TYPE
          SYNTAX      INTEGER
          {
              annexd         (1),
              annexa         (2),
              type1          (3),
              autosense      (4)
          }
          ACCESS      read-write
          STATUS      mandatory
          DESCRIPTION
             "The LMI type used in a Frame Relay application. This setting
              must match the attached Frame Relay device configuration. 
              Annex-A and Annex-D use DLCI 0, and Type 1 uses DLCI 1023.
              Type 1 is alternatively referred to as Cisco, Group of four, 
              or simply LMI. Annex-D may be referred to as ANSI T1.617.
              Annex-A may be referred to as ITU or CCITT Q.933. Auto-sense
              will either use the most recently detected LMI type or, in 
              the absence of any LMI, will attempt to instigate LMI 
              communications using each protocol.     
              (1) Annnex-A: conforms to ITU (CCITT) Q.933 annex A
              (2) Annnex-D: conforms to ANSI T1.617 annex D
              (3) Type 1: conforms to the original LMI as developed by 
                  the Group of Four
              (4) Auto-sense: unit will attempt to detect and synchronize
                  to the LMI type of the attached equipment."
          ::= { tfrapCfgFrTable 3 }

tfrapCfgFrLmiInactivityTimeout  OBJECT-TYPE
          SYNTAX      INTEGER (0..255)
          ACCESS      read-write
          STATUS      mandatory
          DESCRIPTION
             "Timer used by the unit to determine that an attached device is
              not participating in the LMI protocol and that the unit should 
              attempt to source LMI. This timer also controls the length of 
              time that the LMI sourcing state machine remains in a particular 
              state as it attempts to locate an LMI peer.
              (0) LMI Sourcing disabled
              (2-255) LMI Inactivity timeout"
          ::= { tfrapCfgFrTable 4 }

tfrapCfgFrLmiKeepaliveTimeout  OBJECT-TYPE
          SYNTAX      INTEGER (2..255)
          ACCESS      read-write
          STATUS      mandatory
          DESCRIPTION
             "Timer used by the unit to determine the frequency at which Status
              Enquiries are issued during LMI sourcing states where the unit is 
              emulating a Frame Relay DTE device.
             (2-255) length of time between sending enquiries (in seconds)"
          ::= { tfrapCfgFrTable 5 }


tfrapCfgFrAddrResMode OBJECT-TYPE
         SYNTAX      INTEGER
         {
              inactive (1),
              arp      (2),
              inarp    (3),
              both     (4)
         }
         ACCESS      read-write
         STATUS      mandatory
         DESCRIPTION
            "Enable ARP (2), INARP (3), both (4), or neither (1)."
         ::= { tfrapCfgFrTable 6 }

tfrapCfgFrAddrResDlcis OBJECT-TYPE
         SYNTAX      INTEGER
         {
              single        (1),
              multiple      (2),
              t1multi       (3),
              dtemulti      (4)
         }
         ACCESS      read-write
         STATUS      mandatory
         DESCRIPTION
            "Address Resolution Dlcis determines which dlcis are
             used for address resolution. Multiple DLCI support 
             only applies to piggyback mode; in other management 
             modes, only the configured default dlci is used  
             (1) Support the configured Address Resolution protocol(s)
                 out both ports on the single configured default DLCI 
                 only (CfgFrDLCIValue). 
             (2) Support the configured Address Resolution protocol(s)
                 out both ports on all active DLCIs (per LMI).
             (3) Support the configured Address Resolution protocol(s)
                 out the WAN on all active DLCIs (per LMI) and out the 
                 DTE on only the single default DLCI (CfgFrDLCIValue).
             (4) Support the configured Address Resolution protocol(s)
                 out the DTE on all active DLCIs (per LMI) and out the 
                 WAN on only the single default DLCI (CfgFrDLCIValue)."
         ::= { tfrapCfgFrTable 9 }


tfrapCfgFrAddrResInarpTimer OBJECT-TYPE
         SYNTAX      INTEGER (5..86400)
         ACCESS      read-write
         STATUS      mandatory
         DESCRIPTION
            "The frequency at which the unit issues INARP 
             requests (in seconds) from 5 to 86400 (24 hours)."
         ::= { tfrapCfgFrTable 7 }

tfrapCfgFrLmiFullStatus  OBJECT-TYPE
          SYNTAX      INTEGER (0..3600)
          ACCESS      read-write
          STATUS      mandatory
          DESCRIPTION
             "Timer used by the unit to determine if an LMI Full Status
              Report is missing. In the absence of a Full Status report
              for the duration defined by this timer, the unit will
              declare all DLCI's status INACTIVE and begin logging
              down time. Data passage is not interfered with.
              (0) Full Status Timer is disabled
              (20-3600) Full Status Report Timeout in seconds."
          ::= { tfrapCfgFrTable 8 }



--
--       The VNIP Configuration Table
--              This table contains the Configuration for the VNIP
--              protocol support on the TFRAP T1 CSU. 


tfrapCfgVnipTable OBJECT IDENTIFIER ::= { tfrapConfiguration 6 }

   tfrapCfgVnipMode OBJECT-TYPE
         SYNTAX      INTEGER
         {
              inactive (1),
              dte      (2),
              t1      (3),
              both     (4)
         }
         ACCESS      read-write
         STATUS      mandatory
         DESCRIPTION
            "This setting configures the unit for VNIP topology support on
             a per-interface basis. Establishing a VNIP topology is a
             fundamental prerequisite to applying the VNIP feature set which 
             includes PVC-based delay measurement, diagnostics, and congestion
             monitoring. With VNIP enabled on an interface the unit
             will attempt to locate VNIP peers out that port. As peers are 
             discovered and logged the unit will report the topology it has 
             learned on its opposite interface. If VNIP is inactive on one
             interface it will not engage in any VNIP dialog; however it will 
             continue to listen for topology messages on the inactive interface
             and will reflect these messages out the opposite interface if VNIP 
             is enabled. With VNIP inactive on both interfaces the unit will 
             transparently pass all VNIP messages. The topology database includes
             ip addresses, DLCI values, and the number of VNIP hops in between.
             (1) Topology Inactive: VNIP messages pass through unit
             (2) Topology Enabled on DTE only: unit logs VNIP peers seen
                 out the DTE interface. Unit listens for topology reports
                 from the WAN but doesn't generate any towards the WAN. Will 
                 report learned WAN topology towards the DTE.
             (3) Topology Enabled on WAN only: unit logs VNIP peers seen
                 out the WAN interface. Unit listens for topology reports
                 from the DTE but doesn't generate any towards the DTE. Will 
                 report learned DTE topology towards the WAN.
             (4) Topolgy Enabled on Both DTE and WAN: Unit logs VNIP peers
                 seen out both interfaces and generates DTE topolgy reports 
                 towards the WAN and vice versa."
         ::= { tfrapCfgVnipTable 1 }

   tfrapCfgVnipInitTimer OBJECT-TYPE
         SYNTAX      INTEGER (5..86400)
         ACCESS      read-write
         STATUS      mandatory
         DESCRIPTION
           "VNIP peer to peer communications are initiated following
            the detection of a VNIP Hello message. The unit will
            periodically issue this message out interfaces that have 
            VNIP enabled until a Hello response is received. Following 
            the reception of the Hello response, the unit will stop 
            issuing Hello messahges on that DLCI/interface and generate 
            periodic topology reports at the VNIP Keep Alive frequency. 
            The unit will generate periodic Hello messages, at the 
            InitTimer frequency if no Hello responses are ever detected 
            or a topology message not been detected within the time period 
            defined by the VNIP Inactivity timer.
            (5-86400) VNIP Hello frequency (in seconds)"
         ::= { tfrapCfgVnipTable 2 }

   tfrapCfgVnipKeepAliveTimer OBJECT-TYPE
         SYNTAX      INTEGER (5..86400)
         ACCESS      read-write
         STATUS      mandatory
         DESCRIPTION
            "This is the frequency that topology reports are issued out 
             any interface that has VNIP enabled. Once a Hello exchange
             occurs, the unit will periodically issue a VNIP message which 
             reflects the topology it has learned on the opposite interface.
             This Keep Alive timer must be less than any peer unit's Inactivity
             timer.
             (5-86400) VNIP Topology Update frequency (in seconds)"
         ::= { tfrapCfgVnipTable 3 }

   tfrapCfgVnipInactivityTimer OBJECT-TYPE
         SYNTAX      INTEGER (5..86400)
         ACCESS      read-write
         STATUS      mandatory
         DESCRIPTION
            "The length of time to wait before dropping a VNIP
             peer from the database and attempting tp reestablish
             communications by issuing the VNIP Hello message. If
             this timer expires then the entire topology database
             is reset. The Inactivity timers of any unit participating
             in a VNIP topology must be greater than the highest Keep 
             Alive timer in the topology.
             (5- 86400) VNIP Hello frequency (in seconds)"
         ::= { tfrapCfgVnipTable 4 }

   tfrapCfgVnipTransitDelayFrequency OBJECT-TYPE
         SYNTAX      INTEGER (15..86400)
         ACCESS      read-write
         STATUS      mandatory
         DESCRIPTION
            "Transit Delay measurements may be enabled between any DLCI
             peers that have been logged through the topology protocol.
             Delay messages are issued at this frequency and results are
             recorded. Transit delay measures the round-trip network
             delay between two VNIP peers (internal unit latencies are
             not part of the measurement). Traps may be optionally generated 
             if a delay threshold is exceeded.
             (15-86400): Transit Delay message frequency (in seconds)"
         ::= { tfrapCfgVnipTable 5 }


   tfrapCfgTransitDelayTable   OBJECT-TYPE
         SYNTAX   SEQUENCE OF TfrapCfgTransitDelayEntry
         ACCESS   not-accessible
         STATUS   mandatory
         DESCRIPTION
            "The table defining the transit delay measurement profile for
             each of the learned VNIP peers. As peers are located and 
             logged into the topology database, a default transit delay
             profile is assumed. The default is to enable transit delay
             to all hops located out the interface. A DLCI's transit
             delay profile cannot be modified unless the DLCI has been
             discovered through the VNIP topology protocol."
         ::= { tfrapCfgVnipTable 20 }

      tfrapCfgTransitDelayEntry OBJECT-TYPE
          SYNTAX      TfrapCfgTransitDelayEntry
          ACCESS      not-accessible
          STATUS      mandatory
          DESCRIPTION
             "A VNIP Transit Delay configuration entry for a particular 
              DLCI on a particular interface. A DLCI's transit delay 
              profile cannot be modified unless the DLCI has been
              discovered through the VNIP topology protocol"
          INDEX { tfrapCfgTransitDelayInterface, tfrapCfgTransitDelayDlciValue }
          ::= { tfrapCfgTransitDelayTable 1 }

      TfrapCfgTransitDelayEntry ::=
          SEQUENCE
          {
               tfrapCfgTransitDelayInterface         INTEGER,
               tfrapCfgTransitDelayDlciValue         INTEGER,
               tfrapCfgTransitDelayNumHops           INTEGER,
               tfrapCfgTransitDelayRcvSummaryCancel  INTEGER,
               tfrapCfgTransitDelayThreshold         INTEGER
          }

      tfrapCfgTransitDelayInterface OBJECT-TYPE
         SYNTAX      INTEGER
         {
              dte-interface (1),
              t1-interface (2)
         }
         ACCESS      read-write
         STATUS      mandatory
         DESCRIPTION
            "This is the interface being configured for VNIP Transit 
             Delay. If topology is enabled, each interface will contain 
             a database of VNIP peers organized by DLCI value and 
             Number of Hops.
             (1) DTE Interface
             (2) DDS Interface"
         ::= { tfrapCfgTransitDelayEntry 1 }

      tfrapCfgTransitDelayDlciValue    OBJECT-TYPE
          SYNTAX      INTEGER 
          ACCESS      read-write
          STATUS      mandatory
          DESCRIPTION
             "This is the DLCI being configured for VNIP Transit 
              Delay. If topology is enabled, each interface will contain 
              a database of VNIP peers organized by DLCI value and 
              Number of Hops."
          ::= { tfrapCfgTransitDelayEntry 2 }

      tfrapCfgTransitDelayNumHops    OBJECT-TYPE
          SYNTAX      INTEGER (0..255)
          ACCESS      read-write
          STATUS      mandatory
          DESCRIPTION
             "VNIP topolgy may include multiple units on a given
              DLCI/interface. The topology logs the number of 
              intermediate VNIP peers between units (Hops). This 
              setting determines which peers on a DLCI are participating
              in delay measurements.
              (0)     All hops
              (1-254) Individually addressable delay measurement
                         between any two peers.
              (255)   Furthest hop only"
          ::= { tfrapCfgTransitDelayEntry 4 }

      tfrapCfgTransitDelayRcvSummaryCancel    OBJECT-TYPE
          SYNTAX      INTEGER 
          {
               enable-rsc  (1),
               disable-rsc (2)
          }
          ACCESS      read-write
          STATUS      mandatory
          DESCRIPTION
             "Controls the Receive Summary Cancellation feature of VNIP 
              Transit Delay on this interface/DLCI. Every Transit Delay
              measurement exchange includes a follow-up message from the 
              initiator with the delay results. If RSC is enabled, a unit
              will log results based upon this summary message and will 
              not issue its next scheduled delay measurement. With RSC 
              disabled, the unit will not use the summary message and 
              will always issue its regularly scheduled message based on
              the delay frequency timer. The purpose of this feature is to
              reduce traffic introduced by VNIP. In a typical peer-to-peer
              transit delay measurement where both ends are concurrently
              conducting transit delay measurements it's recommended that 
              one end have RSC enabled and one end disabled."
          ::= { tfrapCfgTransitDelayEntry 5 }

      tfrapCfgTransitDelayThreshold    OBJECT-TYPE
          SYNTAX      INTEGER (0..86400000)
          ACCESS      read-write
          STATUS      mandatory
          DESCRIPTION
             "Specifies a transit delay threshold for this DLCI/interface.
              When the transit delay exceeds the threshold, a TRAP is sent. 
              The threshold may be set from one millisecond to 24 hours.
              A value of 0 will prevent a TRAP from being sent.
              (0): Transit delay threshold trap disabled for this DLCI/interface
              (1-86400000): delay threshhold. Any delay measurements exceeding
                  this result will generate a trap."
          ::= { tfrapCfgTransitDelayEntry 6 }


   tfrapCfgTDDeleteTable   OBJECT-TYPE
         SYNTAX   SEQUENCE OF TfrapCfgTDDeleteEntry
         ACCESS   not-accessible
         STATUS   mandatory
         DESCRIPTION
            "The table allows the user to disable transit delay measurements
             for a specific DLCI on a particular interface."
         ::= { tfrapCfgVnipTable 21 }

      tfrapCfgTDDeleteEntry OBJECT-TYPE
          SYNTAX      TfrapCfgTDDeleteEntry
          ACCESS      not-accessible
          STATUS      mandatory
          DESCRIPTION
             "Disables VNIP Transit Delay for a particular interface and DLCI." 
          INDEX { tfrapCfgTDDeleteInterface }
          ::= { tfrapCfgTDDeleteTable 1 }

      TfrapCfgTDDeleteEntry ::=
          SEQUENCE
          {
               tfrapCfgTDDeleteInterface    INTEGER,
               tfrapCfgTDDeleteDlciValue    INTEGER
          }

      tfrapCfgTDDeleteInterface OBJECT-TYPE
         SYNTAX      INTEGER
         {
              dte-interface (1),
              t1-interface (2)
         }
         ACCESS      not-accessible
         STATUS      mandatory
         DESCRIPTION
            "Transit delay can be disabled for a given DLCI on
             either interface. This indexes the interface. 
             Setting this index and the associated DLCI index
             will disable transit delay on that combination."
         ::= { tfrapCfgTDDeleteEntry 1 }

      tfrapCfgTDDeleteDlciValue    OBJECT-TYPE
         SYNTAX      INTEGER 
         ACCESS      write-only
         STATUS      mandatory
         DESCRIPTION
            "Transit delay can be disabled for a given DLCI on
             either interface. This indexes the DLCI. Setting 
             this index and the associated interface index will
             disable transit delay on that combination."
         ::= { tfrapCfgTDDeleteEntry 2 }


   tfrapCfgTransitDelayTableClear  OBJECT-TYPE
         SYNTAX      INTEGER
         {
               clear-table   (1)
         }
         ACCESS      write-only
         STATUS      mandatory
         DESCRIPTION
              " The tfrapCfgTransitDelayTable is cleared.
                (1) clear the table "
         ::= { tfrapCfgVnipTable 22 }




--       The Frame Relay Performance Configuration
--              A group of configuration tables supporting frame relay
--              performance measurements on the TFRAP T1 CSU.

tfrapCfgFrPerf OBJECT IDENTIFIER ::= { tfrapConfiguration 7 }

  tfrapCfgFrPerfDlciNamesTable   OBJECT-TYPE
          SYNTAX      SEQUENCE OF TFRAPCfgFrPerfDlciNamesEntry
          ACCESS      not-accessible
          STATUS      mandatory
          DESCRIPTION
             "This table allows the user to configure DLCI
              specific parameters such as Names, CIR, and EIR.
              Additionally, any DLCIs configured with these
              parameters will be added into the Short Term 
              statistics database next time its cleared."
          ::= { tfrapCfgFrPerf 1 }

      tfrapCfgFrPerfDlciNamesEntry OBJECT-TYPE
          SYNTAX      TFRAPCfgFrPerfDlciNamesEntry
          ACCESS      not-accessible
          STATUS      mandatory
          DESCRIPTION
             "A table entry indexed by DLCI, containing
              a DLCI, a DLCI name, a CIR, how the
              CIR value was obtained, and EIR."
          INDEX { tfrapCfgFrPerfDlciNamesDlciValue }
          ::= { tfrapCfgFrPerfDlciNamesTable 1 }

      TFRAPCfgFrPerfDlciNamesEntry ::=
          SEQUENCE
          {
             tfrapCfgFrPerfDlciNamesDlciValue   INTEGER,
             tfrapCfgFrPerfDlciNamesDlciName    DisplayString (SIZE (0..15)),
             tfrapCfgFrPerfDlciNamesCirValue    INTEGER,
             tfrapCfgFrPerfDlciNamesCirType     INTEGER,
             tfrapCfgFrPerfDlciNamesUtilThreshold INTEGER,
             tfrapCfgFrPerfDlciNamesEirValue    INTEGER
          } 

      tfrapCfgFrPerfDlciNamesDlciValue    OBJECT-TYPE
          SYNTAX      INTEGER 
          ACCESS      read-write
          STATUS      mandatory
          DESCRIPTION
             "A DLCI selected for customized configuration and to 
              be added to short term statistics collection (if it
              wasn't already there)."
          ::= { tfrapCfgFrPerfDlciNamesEntry 1 }

      tfrapCfgFrPerfDlciNamesDlciName   OBJECT-TYPE
          SYNTAX      DisplayString (SIZE (0..15))
          ACCESS      read-write
          STATUS      mandatory
          DESCRIPTION
             "A user-specifiable name for an individual DLCI."
          ::= { tfrapCfgFrPerfDlciNamesEntry 2 }

      tfrapCfgFrPerfDlciNamesCirValue    OBJECT-TYPE
          SYNTAX      INTEGER 
          ACCESS      read-write
          STATUS      mandatory
          DESCRIPTION
             "The CIR value for an individual DLCI. This
              value is used in the calculation utilization
              as a percentage of CIR. If the CIR is reported 
              in the LMI message then the reported value will
              override this configured entry. In the absence
              of LMI CIR and a configured CIR, the unit will
              assume that the CIR is the DTE Line Rate."
          ::= { tfrapCfgFrPerfDlciNamesEntry 3 }

      tfrapCfgFrPerfDlciNamesCirType    OBJECT-TYPE
          SYNTAX      INTEGER 
          {
               cir-acquired-from-lmi  (1),
               cir-configured-by-user (2),
               cir-is-datarate        (3)
          }
          ACCESS      read-only
          STATUS      mandatory
          DESCRIPTION
             "The source of the CIR value for this DLCI.
              If CIR for a DLCI is part of the LMI message
              then this LMI supplied CIR will override any 
              defined CIR. If CIR is not part of LMI and
              has not been explicitly defined by the user
              it will default to the DTE Line Rate.
              (1) CIR reported in LMI Full Status message
              (2) CIR configured by user
              (3) CIR defaulted to DTE Line Rate"
          ::= { tfrapCfgFrPerfDlciNamesEntry 4 }

   tfrapCfgFrPerfDlciNamesUtilThreshold  OBJECT-TYPE
          SYNTAX      INTEGER  (0..100) 
          ACCESS      read-write
          STATUS      mandatory
          DESCRIPTION
             "The threshold for generating a utilization 
              threshold trap as a percentage of the CIR.  
              If the utilization percentage is above this 
              threshold for more than 
              tfrapCfgFrPerfDlciUtilThreshold number of
              tfrapCfgFrPerfTimersSTInterval's a
              tfrapPvc(Rx/Tx)UtilizationExceeded trap
              will be issued.  If the If the utilization 
              percentage falls below this threshold for 
              more than tfrapCfgFrPerfDlciUtilThreshold 
              number of tfrapCfgFrPerfTimersSTInterval's a
              tfrapPvc(Rx/Tx)UtilizationExceeded trap
              will be issued."
          ::= { tfrapCfgFrPerfDlciNamesEntry 5}

      tfrapCfgFrPerfDlciNamesEirValue    OBJECT-TYPE
          SYNTAX      INTEGER 
          ACCESS      read-write
          STATUS      mandatory
          DESCRIPTION
             "The EIR value for an individual DLCI. In the 
              absence of a configured EIR, the unit will
              assume that the EIR is the DTE Line Rate."
          ::= { tfrapCfgFrPerfDlciNamesEntry 6 }

         
   tfrapCfgFrPerfDlciNamesDelete   OBJECT-TYPE
          SYNTAX      INTEGER 
          ACCESS      write-only
          STATUS      mandatory
          DESCRIPTION
             "Setting this object with a specific DLCI value
              will remove the DLCI form the DLCI-specific
              parameters database."
          ::= { tfrapCfgFrPerf 2 }

  tfrapCfgFrPerfTimers OBJECT IDENTIFIER ::= { tfrapCfgFrPerf 3 }

      tfrapCfgFrPerfTimersSTInterval   OBJECT-TYPE
          SYNTAX      INTEGER (3..60)
          ACCESS      read-write
          STATUS      mandatory
          DESCRIPTION
             "Short term statistics maintain cumulative counts, and
              counts for the current and previous short term windows.
              This value is the  window size for the short term statistics
              intervals.
              (3-60): short term statistics collection interval"
          ::= { tfrapCfgFrPerfTimers 1 }

      tfrapCfgFrPerfTimersLTInterval   OBJECT-TYPE
          SYNTAX      INTEGER (4..3600)
          ACCESS      read-write
          STATUS      mandatory
          DESCRIPTION
             "Long term statistics maintain 96 contiguous intervals
              of configurable protocol per DLCI statistics. This value
              is the window size of each interval. Adjusting this value
              will change the overall length of time that the 96 intervals
              will span.
             (4-3600): long term statsistics collection interval"
          ::= { tfrapCfgFrPerfTimers 2 }

   tfrapCfgFrPerfUserProtocolsTable   OBJECT-TYPE
          SYNTAX      SEQUENCE OF TFRAPCfgFrPerfUserProtocolsEntry
          ACCESS      not-accessible
          STATUS      mandatory
          DESCRIPTION
             "This table allows the user to select TCP/UDP ports 
              for statistics collection.  Tx and Rx byte counts
              will collected on the specified ports.  These ports
              are selectable as protocols in the long term
              statistics filter and are displayed with the other
              protocols in the short term statistics."
          ::= { tfrapCfgFrPerf 4 }

      tfrapCfgFrPerfUserProtocolsEntry OBJECT-TYPE
          SYNTAX      TFRAPCfgFrPerfUserProtocolsEntry
          ACCESS      not-accessible
          STATUS      mandatory
          DESCRIPTION
             "An index and TCP/UDP port number pair." 
          INDEX { tfrapCfgFrPerfUserProtocolsIndex }
          ::= { tfrapCfgFrPerfUserProtocolsTable 1 }

      TFRAPCfgFrPerfUserProtocolsEntry ::=
          SEQUENCE
          {
               tfrapCfgFrPerfUserProtocolsIndex     INTEGER,
               tfrapCfgFrPerfUserProtocolsPortNum   INTEGER
          } 

      tfrapCfgFrPerfUserProtocolsIndex    OBJECT-TYPE
          SYNTAX      INTEGER 
          ACCESS      read-only
          STATUS      mandatory
          DESCRIPTION
             "An index. Beginning with index 1, the range is defined 
              in SysNumUserProtocols"
          ::= { tfrapCfgFrPerfUserProtocolsEntry 1 }

      tfrapCfgFrPerfUserProtocolsPortNum   OBJECT-TYPE
          SYNTAX      INTEGER
          ACCESS      read-write
          STATUS      mandatory
          DESCRIPTION
            "Tx and Rx byte counts will be collected on
             the user-specifiable TCP/UDP port number.
             (0) port not defined
             (1-65535): IP TCP/UDP protocol port number."
          ::= { tfrapCfgFrPerfUserProtocolsEntry 2 }

   tfrapCfgFrPerfLTDlciFilterTable       OBJECT-TYPE
          SYNTAX      SEQUENCE OF TFRAPCfgFrPerfLTDlciFilterEntry
          ACCESS      not-accessible
          STATUS      mandatory
          DESCRIPTION
             "Long term statistics can only be collected
              on a limited number of DLCIs. The value of
              SysLTFNumDlcis defines the maximum number of
              DLCIs that can be included in the Long Term
              Statistics. Once one or more DLCIs are added
              to Long Term Stats, the user may assign a 
              set of protocols that will be monitored across
              all of the Long Term DLCIs."
          ::= { tfrapCfgFrPerf 5 }

      tfrapCfgFrPerfLTDlciFilterEntry OBJECT-TYPE
          SYNTAX      TFRAPCfgFrPerfLTDlciFilterEntry
          ACCESS      not-accessible
          STATUS      mandatory
          DESCRIPTION
             "An index and DLCI number pair." 
          INDEX { tfrapCfgFrPerfLTDlciFilterIndex }
          ::= { tfrapCfgFrPerfLTDlciFilterTable 1 }

      TFRAPCfgFrPerfLTDlciFilterEntry ::=
          SEQUENCE
          {
               tfrapCfgFrPerfLTDlciFilterIndex     INTEGER,
               tfrapCfgFrPerfLTDlciFilterDlciNum   INTEGER
          } 

      tfrapCfgFrPerfLTDlciFilterIndex    OBJECT-TYPE
          SYNTAX      INTEGER 
          ACCESS      read-only
          STATUS      mandatory
          DESCRIPTION
             "An index. Beginning with index 1, the maximum is 
              defined by the value of SysLTFNumDlcis."
          ::= { tfrapCfgFrPerfLTDlciFilterEntry 1 }

      tfrapCfgFrPerfLTDlciFilterDlciNum   OBJECT-TYPE
          SYNTAX      INTEGER
          ACCESS      read-write
          STATUS      mandatory
          DESCRIPTION
             "Setting a DLCI value here will add that DLCI into
              the Long term statistics database (associated with 
              its index) and it will be monitored for the protocol 
              activity defined in the Long Term Protocol filter."
          ::= { tfrapCfgFrPerfLTDlciFilterEntry 2 }


   tfrapCfgFrPerfLTProtocolFilterTable   OBJECT-TYPE
          SYNTAX      SEQUENCE OF TFRAPCfgFrPerfLTProtocolFilterEntry
          ACCESS      not-accessible
          STATUS      mandatory
          DESCRIPTION
             "Long term statistics can only be collected
              on a limited number of protocols. The maximum
              number of Long Term Protoocls are defined by 
              SysLTFNumProtocols. This table allows the user to 
              configure those protocols."
          ::= { tfrapCfgFrPerf 6 }

      tfrapCfgFrPerfLTProtocolFilterEntry OBJECT-TYPE
          SYNTAX      TFRAPCfgFrPerfLTProtocolFilterEntry
          ACCESS      not-accessible
          STATUS      mandatory
          DESCRIPTION
             "An index and protocol pair." 
          INDEX { tfrapCfgFrPerfLTProtocolFilterIndex }
          ::= { tfrapCfgFrPerfLTProtocolFilterTable 1 }

      TFRAPCfgFrPerfLTProtocolFilterEntry ::=
          SEQUENCE
          {
               tfrapCfgFrPerfLTProtocolFilterIndex      INTEGER,
               tfrapCfgFrPerfLTProtocolFilterProtocol   INTEGER
          } 

      tfrapCfgFrPerfLTProtocolFilterIndex    OBJECT-TYPE
          SYNTAX      INTEGER 
          ACCESS      read-only
          STATUS      mandatory
          DESCRIPTION
             "An index. Beginning with index 1, the maximum is 
              defined by the value of SysLTFNumProtocols."
          ::= { tfrapCfgFrPerfLTProtocolFilterEntry 1 }

      tfrapCfgFrPerfLTProtocolFilterProtocol   OBJECT-TYPE
          SYNTAX      INTEGER
          {
            ip-tx-bc                    (1),
            ip-rx-bc                    (2),
            tcp-ip-tx-bc                (3),
            tcp-ip-rx-bc                (4),
            ftp-tcp-ip-tx-bc            (5),
            ftp-tcp-ip-rx-bc            (6),
            telnet-tcp-ip-tx-bc         (7),
            telnet-tcp-ip-rx-bc         (8),
            smtp-tcp-ip-tx-bc           (9),
            smtp-tcp-ip-rx-bc           (10),
--          tftp-tcp-ip-tx-bc           (11),
--          tftp-tcp-ip-rx-bc           (12),
            http-tcp-ip-tx-bc           (13),
            http-tcp-ip-rx-bc           (14),
            netbios-ssn-tcp-ip-tx-bc    (15),
            netbios-ssn-tcp-ip-rx-bc    (16),
--          snmp-tcp-ip-tx-bc           (17),
--          snmp-tcp-ip-rx-bc           (18),
--          snmptrap-tcp-ip-tx-bc       (19),
--          snmptrap-tcp-ip-rx-bc       (20),
            udp-ip-tx-bc                (21),
            udp-ip-rx-bc                (22),
--          ftp-udp-ip-tx-bc            (23),
--          ftp-udp-ip-rx-bc            (24),
--          telnet-udp-ip-tx-bc         (25),
--          telnet-udp-ip-rx-bc         (26),
--          smtp-udp-ip-tx-bc           (27),
--          smtp-udp-ip-rx-bc           (28),
            tftp-udp-ip-tx-bc           (29),
            tftp-udp-ip-rx-bc           (30),
--          http-udp-ip-tx-bc           (31),
--          http-udp-ip-rx-bc           (32),
            netbios-dgm-udp-ip-tx-bc    (33),
            netbios-dgm-udp-ip-rx-bc    (34),
            snmp-udp-ip-tx-bc           (35),
            snmp-udp-ip-rx-bc           (36),
            snmptrap-udp-ip-tx-bc       (37),
            snmptrap-udp-ip-rx-bc       (38),
            rip-udp-ip-tx-bc            (39),
            rip-udp-ip-rx-bc            (40),
            icmp-ip-tx-bc               (41),
            icmp-ip-rx-bc               (42),
            echorep-icmp-ip-tx-bc       (43),
            echorep-icmp-ip-rx-bc       (44),
            dest-unr-icmp-ip-tx-bc      (45),
            dest-unr-icmp-ip-rx-bc      (46),
            src-quench-icmp-ip-tx-bc    (47),
            src-quench-icmp-ip-rx-bc    (48),
            redirect-icmp-ip-tx-bc      (49),
            redirect-icmp-ip-rx-bc      (50),
            echoreq-icmp-ip-tx-bc       (51),
            echoreq-icmp-ip-rx-bc       (52),
            time-excd-icmp-ip-tx-bc     (53),
            time-excd-icmp-ip-rx-bc     (54),
            param-prob-icmp-ip-tx-bc    (55),
            param-prob-icmp-ip-rx-bc    (56),
            timestamp-req-icmp-ip-tx-bc (57),
            timestamp-req-icmp-ip-rx-bc (58),
            timestamp-rep-icmp-ip-tx-bc (59),
            timestamp-rep-icmp-ip-rx-bc (60),
            addr-mask-req-icmp-ip-tx-bc (61),
            addr-mask-req-icmp-ip-rx-bc (62),
            addr-mask-rep-icmp-ip-tx-bc (63),
            addr-mask-rep-icmp-ip-rx-bc (64),
            pkt-too-big-icmp-ip-tx-bc   (65),
            pkt-too-big-icmp-ip-rx-bc   (66),
            gp-mem-query-icmp-ip-tx-bc  (67),
            gp-mem-query-icmp-ip-rx-bc  (68),
            gp-mem-report-icmp-ip-tx-bc (69),
            gp-mem-report-icmp-ip-rx-bc (70),
            gp-mem-reduct-icmp-ip-tx-bc (71),
            gp-mem-reduct-icmp-ip-rx-bc (72),
            ospf-ip-tx-bc               (73),
            ospf-ip-rx-bc               (74),
            other-ip-tx-bc              (75),
            other-ip-rx-bc              (76),
            ipx-tx-bc                   (77),
            ipx-rx-bc                   (78),
            spx-ipx-tx-bc               (79),
            spx-ipx-rx-bc               (80),
            ncp-ipx-tx-bc               (81),
            ncp-ipx-rx-bc               (82),
            sap-ipx-tx-bc               (83),
            sap-ipx-rx-bc               (84),
            rip-ipx-tx-bc               (85),
            rip-ipx-rx-bc               (86),
            netbios-ipx-tx-bc           (87),
            netbios-ipx-rx-bc           (88),
            other-ipx-tx-bc             (89),
            other-ipx-rx-bc             (90),
            arp-tx-bc                   (91),
            arp-rx-bc                   (92),
            arp-req-tx-bc               (93),
            arp-req-rx-bc               (94),
            arp-rep-tx-bc               (95),
            arp-rep-rx-bc               (96),
            rarp-req-tx-bc              (97),
            rarp-req-rx-bc              (98),
            rarp-rep-tx-bc              (99),
            rarp-rep-rx-bc              (100),
            inarp-req-tx-bc             (101),
            inarp-req-rx-bc             (102),
            inarp-rep-tx-bc             (103),
            inarp-rep-rx-bc             (104),
            sna-tx-bc                   (105),
            sna-rx-bc                   (106),
            sna-subarea-tx-bc           (107),
            sna-subarea-rx-bc           (108),
            sna-periph-tx-bc            (109),
            sna-periph-rx-bc            (110),
            sna-appn-tx-bc              (111),
            sna-appn-rx-bc              (112),
            sna-netbios-tx-bc           (113),
            sna-netbios-rx-bc           (114),
            cisco-tx-bc                 (115),
            cisco-rx-bc                 (116),
            other-tx-bc                 (117),
            other-rx-bc                 (118),
            user-defined-1-tx-bc        (119),
            user-defined-1-rx-bc        (120),
            user-defined-2-tx-bc        (121),
            user-defined-2-rx-bc        (122),
            user-defined-3-tx-bc        (123),
            user-defined-3-rx-bc        (124),
            user-defined-4-tx-bc        (125),
            user-defined-4-rx-bc        (126),
            thru-byte-tx-bc             (127),
            thru-byte-rx-bc             (128),
            thru-frame-tx-bc            (129),
            thru-frame-rx-bc            (130),
            thru-fecn-tx-bc             (131),
            thru-fecn-rx-bc             (132),
            thru-becn-tx-bc             (133),
            thru-becn-rx-bc             (134),
            thru-de-tx-bc               (135),
            thru-de-rx-bc               (136),
            cir-percent-range1-tx-bc    (137),
            cir-percent-range1-rx-bc    (138),
            cir-percent-range2-tx-bc    (139),
            cir-percent-range2-rx-bc    (140),
            cir-percent-range3-tx-bc    (141),
            cir-percent-range3-rx-bc    (142),
            cir-percent-range4-tx-bc    (143),
            cir-percent-range4-rx-bc    (144),
            cir-percent-range5-tx-bc    (145),
            cir-percent-range5-rx-bc    (146),
            cir-percent-range6-tx-bc    (147),
            cir-percent-range6-rx-bc    (148),
            cir-percent-range7-tx-bc    (149),
            cir-percent-range7-rx-bc    (150),
            cir-percent-range8-tx-bc    (151),
            cir-percent-range8-rx-bc    (152),
            lmi-tx-bc                   (153),
            lmi-rx-bc                   (154),
            lmi-livo-enq-tx-bc          (155),
            lmi-livo-enq-rx-bc          (156),
            lmi-livo-stat-tx-bc         (157),
            lmi-livo-stat-rx-bc         (158),
            lmi-full-enq-tx-bc          (159),
            lmi-full-enq-rx-bc          (160),
            lmi-full-stat-tx-bc         (161),
            lmi-full-stat-rx-bc         (162),
            lmi-other-tx-bc             (163),
            lmi-other-rx-bc             (164),
            total-uptime                (165),
            total-downtime              (166),
            igrp-tx-bc                  (167),
            igrp-rx-bc                  (168),
            vnip-tx-bc                  (169),
            vnip-rx-bc                  (170),
            annex-g-tx-bc               (171),
            annex-g-rx-bc               (172),

            delete-entry                (-1)
          }
          ACCESS      read-write
          STATUS      mandatory
          DESCRIPTION
             "Long term statistics will be collected on
              the user-specifiable protocol. Setting a -1 
              remove the indexed protocol from the filter."
          ::= { tfrapCfgFrPerfLTProtocolFilterEntry 2 }

  tfrapCfgFrPerfDlciDefaultUtilThreshold  OBJECT-TYPE
          SYNTAX      INTEGER  (0..100) 
          ACCESS      read-write
          STATUS      mandatory
          DESCRIPTION
             "The default threshold for generating a 
              utilization threshold trap as a percentage 
              of the CIR. This value is used for 
              tfrapCfgFrPerfDlciNamesUtilThreshold when
              a DLCI is first discovered. "
          ::= { tfrapCfgFrPerf 7 }

   tfrapCfgFrPerfDlciUtilDuration  OBJECT-TYPE
          SYNTAX      INTEGER (0..65535) 
          ACCESS      read-write
          STATUS      mandatory
          DESCRIPTION
             "The number of Short Term Intervals that a
              DLCI's utilization as a percentage of CIR
              must be above or below the value of
           tfrapCfgFrPerfDlciUtilThreshold before a
              tfrapPvc(Rx/Tx)UtilizationExceededTrap or
              tfrapPvc(Rx/Tx)UtilizationClearedTrap is
              issued. "
          ::= { tfrapCfgFrPerf 8 }

  tfrapCfgFrPerfDlciNamesTableClear  OBJECT-TYPE
         SYNTAX       INTEGER
         {            
            clear-table                (1),
            clear-table-keep-stats     (2)
         }
         ACCESS      write-only
         STATUS      mandatory
         DESCRIPTION
             "Clears the smperCfgFrPerfDlciNamesTable
              (1) clear the table or (2) clear the table
              but don't remove the dlcis from the short
              term statistics."
          ::= { tfrapCfgFrPerf 9 }
         
  tfrapCfgFrPerfUserProtocolsTableClear  OBJECT-TYPE
         SYNTAX       INTEGER
         {            
            clear-table     (1)
         }
          ACCESS      write-only
          STATUS      mandatory
          DESCRIPTION
             " Clears the tfrapCfgFrPerfUserProtocolsTable
               (1) clear the table "
          ::= { tfrapCfgFrPerf 10 }
         
  tfrapCfgFrPerfLTDlciFilterTableClear  OBJECT-TYPE
         SYNTAX       INTEGER
         {            
            clear-table     (1)
         }
          ACCESS      write-only
          STATUS      mandatory
          DESCRIPTION
             " Clears the tfrapCfgFrPerfLTDlciFilterTable
               (1) clear the table "
          ::= { tfrapCfgFrPerf 11 }
         
  tfrapCfgFrPerfLTProtocolFilterTableClear  OBJECT-TYPE
         SYNTAX       INTEGER
         {            
            clear-table     (1)
         }
          ACCESS      write-only
          STATUS      mandatory
          DESCRIPTION
             " Clears the tfrapCfgFrPerfLTProtocolFilterTable
               (1) clear the table "
          ::= { tfrapCfgFrPerf 12 }
         
  tfrapCfgFrPerfUnprovDlcisDelete  OBJECT-TYPE
         SYNTAX       INTEGER
         {            
            delete-unprov     (1)
         }
          ACCESS      write-only
          STATUS      mandatory
          DESCRIPTION
             "Delete all unprovisioned and Not-In-LMI dlcis
               (1) delete all unprovisioned "
          ::= { tfrapCfgFrPerf 13 }
         
          
  tfrapCfgSecurityTable OBJECT IDENTIFIER ::= { tfrapConfiguration 8 }

      tfrapCfgTelnetCliLcdPassword   OBJECT-TYPE
          SYNTAX      DisplayString (SIZE (0..8))
          ACCESS      read-write
          STATUS      mandatory
          DESCRIPTION
             "The password needed to start a
              CLI (Command Line Interface),
              Telnet or LCD session."
          ::= { tfrapCfgSecurityTable 1 }

      tfrapCfgTftpPassword   OBJECT-TYPE
          SYNTAX      DisplayString (SIZE (0..8))
          ACCESS      read-write
          STATUS      mandatory
          DESCRIPTION
             "The password needed to initiate a TFTP download."
          ::= { tfrapCfgSecurityTable 2 }

      tfrapCfgCliPassword   OBJECT-TYPE
          SYNTAX      DisplayString (SIZE (0..8))
          ACCESS      read-write
          STATUS      mandatory
          DESCRIPTION
             "OBSOLETE: The Telnet, CLI and LCD passwords
              are one and the same.  Use the above
              tfrapCfgTelnetCliLcdPassword to log into
              the CLI (Command Line Interface)."
          ::= { tfrapCfgSecurityTable 3 }

      tfrapCfgLcdPassword   OBJECT-TYPE
          SYNTAX      DisplayString (SIZE (0..8))
          ACCESS      read-write
          STATUS      mandatory
          DESCRIPTION
             "OBSOLETE: The Telnet, CLI and LCD passwords
              are one and the same.  Use the above
              tfrapCfgTelnetCliLcdPassword to log into
              the LCD Interface."
          ::= { tfrapCfgSecurityTable 4 }

      tfrapCfgGetCommunityString   OBJECT-TYPE
          SYNTAX      DisplayString (SIZE (0..15))
          ACCESS      read-write
          STATUS      mandatory
          DESCRIPTION
             "The community string for doing SNMP GETs. The unit
              will respond to GETs that use either this string or
              the SET community string. All others will be rejected
              and a trap will be generated. String is case sensitive."
          ::= { tfrapCfgSecurityTable 5 }

      tfrapCfgSetCommunityString   OBJECT-TYPE
          SYNTAX      DisplayString (SIZE (0..15))
          ACCESS      read-write
          STATUS      mandatory
          DESCRIPTION
             "The community string for doing SNMP SETs. The unit 
              will reject SETs with any other coimmunity string
              and will generate a trap. String is case sensitive."
          ::= { tfrapCfgSecurityTable 6 }

      tfrapCfgLcdPswdEnable   OBJECT-TYPE
          SYNTAX      INTEGER 
          {
               enable-lcd-pswd  (1),
               disable-lcd-pswd (2)
          }
          ACCESS      read-write
          STATUS      mandatory
          DESCRIPTION
             "This selection controls whether a password is
              necessary to use the LCD interface."
          ::= { tfrapCfgSecurityTable 7 }

      tfrapCfgLcdPswdTimeout   OBJECT-TYPE
          SYNTAX      INTEGER 
          ACCESS      read-write
          STATUS      mandatory
          DESCRIPTION
             "OBSOLETE."
          ::= { tfrapCfgSecurityTable 8 }

tfrapCfgLock   OBJECT-TYPE
     SYNTAX      INTEGER (1..600)
     ACCESS      write-only
     STATUS      mandatory
     DESCRIPTION
        " Request to start configuration download and lock out any 
          other means of configuring the unit. The integer passed in
          represents the time out period  in seconds between sets. 
          A set to this object will fail if the unit is already in a 
          configuration locked state."
     ::= { tfrapConfiguration 12 }

tfrapCfgLockID   OBJECT-TYPE
     SYNTAX      IpAddress
     ACCESS      read-only
     STATUS      mandatory
     DESCRIPTION
        " Returns the IP Address of  the management station currently 
          in control of configuration. A unit that is not in a 
          configuration locked state will return  0.0.0.0" 
     ::= { tfrapConfiguration 13 }

tfrapCfgID   OBJECT-TYPE
     SYNTAX      DisplayString (SIZE (0..8))
     ACCESS      read-write
     STATUS      mandatory
     DESCRIPTION
        " A read of this object returns the Current Configuration ID 
          string. A write sets  the Configuration ID string. The 
          string contains a starting character to indicate the last 
          configuration source C = Envisage N = CLI/TELNET L = LCD 
          S= other SNMP management station  and a unique 7 integer 
          value to differentiate configurations between common sources. 
          A value of *STARTUP indicates the configuration has been 
          defaulted. A write will only be accepted from the management 
          station that has successfully obtained the configuration lock" 
     ::= { tfrapConfiguration 14 }

tfrapCfgStatus   OBJECT-TYPE
     SYNTAX      INTEGER
     {
                 in-progress                (1),
                 success                    (2),
            datarate-density-conflict  (3),
                 bandwidth-allocation-error (4),
                 general-error              (5),
                 timeout                    (6),
                 aborted-by-user            (7)
     }
     ACCESS      read-only
     STATUS      mandatory
     DESCRIPTION
        " The status of a configuration install is reported here.
          On startup, a status of success will be reported.
          (1) The configuration has been locked and an update or
              unlock command has not been received.
          (2) An update command has been received and the configuration
              has been validated as consistent; .
          (3) An update command has been received but the DTE port 
              datarate is not compatible with the density.
          (4) An update command has been received but the number of
              channels to be allocated will not fit in the available
              channels.
          (5) An update command has been received but there is an
              error in the configuration that is not a 
              datarate-density-conflict or bandwidth-allocation-error.
          (6) The time between consecutive set requests exceeded the
              timeout sent with the tfrapCfgLock command.
          (7) The user sent a tfrapCfgUnlock command before a 
              tfrapCfgUpdate command.  This usually means that one
              of the sets in the configuration failed. "
     ::= { tfrapConfiguration 15 }

tfrapCfgUnlock   OBJECT-TYPE
     SYNTAX      INTEGER 
     {
           un-lock (1)
     }
     ACCESS      write-only
     STATUS      mandatory
     DESCRIPTION
        " The management station sets this variable to complete 
          the configuration install process. Un-lock (1) notifies 
          the agent to remove the lock on configuring the unit
          without updating the configuration."
     ::= { tfrapConfiguration 16 }


tfrapCfgUpdate   OBJECT-TYPE
     SYNTAX      INTEGER 
     {
           update (1)
     }
     ACCESS      write-only
     STATUS      mandatory
     DESCRIPTION
        " The management station sets this variable to complete 
        the configuration install process. Update (1) notifies 
        the agent to start the update process within the unit."
     ::= { tfrapConfiguration 17 }


-- =========================
-- ==  DIAGNOSTICS group  ==
-- =========================

tfrapDiagnostics  OBJECT IDENTIFIER ::= { tfrap 3 }


--
--       The Diagnostics/Unit Table
--              This table contains the objects for unit level diagnostics
--              on the FRAP T1 DSU.

tfrapDiagUnitTable OBJECT IDENTIFIER ::= { tfrapDiagnostics 1 }

tfrapDiagUnitLocLoop OBJECT-TYPE
          SYNTAX      INTEGER 
          {
               enable-loopback-mode  (1),
               disable-loopback-mode (2)
          }
          ACCESS      read-write
          STATUS      mandatory
          DESCRIPTION
             "Controls a bi-directional unit loopback. Data 
              is received from either interface, processed, 
              and transmitted back towards the same interface. 
              When configured for Frame Relay operation the unit 
              will preserve the LMI path and maintain managed access
              during this loopback. In Frame Relay mode, only valid 
              HDLC frames are looped back (pseudorandom test patterns
              will be dropped).
              (1) enable unit loopback
              (2) disable unit loopback"
          ::= { tfrapDiagUnitTable 1 }

tfrapDiagUnitReset OBJECT-TYPE
          SYNTAX      INTEGER 
          {
               reset-unit (1)
          }
          ACCESS      write-only
          STATUS      mandatory
          DESCRIPTION
             "Enables the operator to remotely cause a software
              reset on the unit. Using this command will cause 
              the unit to terminate all its connections and drop data.
              (1) Reset Unit."
          ::= { tfrapDiagUnitTable 2 }

tfrapDiagUnitTimeRemaining OBJECT-TYPE
          SYNTAX      TimeTicks
          ACCESS      read-only
          STATUS      mandatory
          DESCRIPTION
             "The remaining time on the active loopback
              before the loopback times out and disables
              itself. The time is in hundredths of seconds
              (TimeTicks)."
          ::= { tfrapDiagUnitTable 3 }

--       The tfrapDiagT1Table
--              This table contains the T1 level diagnostics of the TFRAP CSU.
--

tfrapDiagT1Table   OBJECT IDENTIFIER ::= { tfrapDiagnostics 2 }
--        DESCRIPTION
--           "Network (T1) Diagnostics for the Sync TFRAP. "

tfrapDiagT1LocLineLpbk OBJECT-TYPE
     SYNTAX      INTEGER
     {
        line-lpbk-disable       (1),
        line-lpbk-enable        (2)
     }
     ACCESS      read-write
     STATUS      mandatory
     DESCRIPTION
        "Controls local network loopback. All data (including
         framing and line errors) received from the WAN, 
         regardless of format or content, is transmitted back 
         out to the WAN (line interface loopback) while still 
         being passed through to the DTE. In Frame Relay 
         applications the unit will not preserve the LMI path during
         this diagnostic and in-band management may not operate.
         (1) disable line loopback
         (2) enable line loopback"
     ::= { tfrapDiagT1Table 1 }

tfrapDiagT1LocPylLpbk OBJECT-TYPE
     SYNTAX      INTEGER
     {
        pyl-lpbk-disable        (1),
        pyl-lpbk-enable         (2)
     }
     ACCESS      read-write
     STATUS      mandatory
     DESCRIPTION
        "Controls network payload loopback. All data 
         received from the WAN is terminated, reframed
         and sent back towards the WAN. Framing errors
         and Line Code Violations are corrected. 
         Network contact via ESF Facility Data Link is 
         preserved during this loopback state. All user
         data regardless of format or content, is transmitted 
         back out while all Ones are sent to the DTE. In Frame
         Relay applications the unit will not preserve the LMI
         path during this diagnostic and in-band management may
         not operate.
         (1) disable payload loopback
         (2) enable payload loopback"
     ::= { tfrapDiagT1Table 2 }

tfrapDiagT1LocAggrLpbk OBJECT-TYPE
     SYNTAX      INTEGER
     {
        aggr-lpbk-disable       (1),
        aggr-lpbk-enable        (2)
     }
     ACCESS      read-write
     STATUS      mandatory
     DESCRIPTION
        "Controls Local Aggregate Loopback. All data 
         received from the DTE is framed, formatted 
         and transmit towards the WAN while being looped
         back towards the DTE. The loopback path covers
         the entire digital data path within the device.
         In Frame Relay mode, only error-free HDLC frames
         will pass through the loopback path. Additionally,
         in Frame Relay applications the unit will not 
         preserve the LMI path during this loopback and 
         in-band management may not operate.
         (1) disable local aggregate (digital) loopback
         (2) enable local aggregate (digital) loopback "
      ::= { tfrapDiagT1Table 3 }

tfrapDiagT1RmtLpbkStatus OBJECT-TYPE
     SYNTAX      INTEGER
     {
        no-remote-lpbks         (1),
        csu-lpbk-from-remote    (2),
        dsu-lpbk-from-remote    (3),
        pyl-lpbk-from-remote    (4),
        csu-lpbk-sent-to-remote (5),
        dsu-lpbk-sent-to-remote (6)
     }
     ACCESS      read-only
     STATUS      mandatory
     DESCRIPTION
        "Status of Remote Loopback commands sent or received on the WAN.
         (1) csu loopback from remote - indicates the node is in a Network
           Line Loopback state due to the reception of the standard CSU 
           Loop-up pattern from the WAN.
         (2) dsu loopback from remote - indicates the node is in a Network
           Line Loopback state due to the reception of the Sync Research
           proprietary Loop-up pattern from a remote node.
         (3) payload loopback from remote - indicates the node is in a 
           Payload Loopback state due to the reception of the ESF Facility 
           Data Link's Loop-up pattern from the network.
         (4) csu loopback sent to remote - indicates the node has sent a csu
           loop up pattern towards the WAN. A device terminating the WAN's 
           physical link is expected to enter a Line Loopback. The initating 
           unit doesn't know if the loopback was accepted by the remote unit.
         (5) dsu loopback sent to remote - indicates the node has sent a dsu
           loop up pattern to a remote Sync unit out the WAN. A compatible 
           device detecting this pattern is expected to enter a Line Loopback. 
           The initating unit doesn't know if the loopback was accepted by 
           the remote unit."
     ::= { tfrapDiagT1Table 4 }

tfrapDiagT1RmtLpbkCmd OBJECT-TYPE
     SYNTAX      INTEGER
     {
        rmt-csu-lpbk-loopup     (1),
        rmt-csu-lpbk-loopdown   (2),
        rmt-dsu-lpbk-loopup     (3),
        rmt-dsu-lpbk-loopdown   (4)
     }
     ACCESS      write-only
     STATUS      mandatory
     DESCRIPTION
        "Remote loopback commands are intended to place compatible external
         equipment into a loopback state. The initiating unit will maintain
         normal data flows during these tests. 
         (1) csu loop up - commands the node to send a standard in-band 
           csu loop up pattern towards the WAN. This is a repetetive
           framed T1 signal consisting of four 'zeros' followed by one 'one'
           persisting for a few seconds in place of all T1 data. A 
           device terminating the WAN's physical link is expected to enter 
           a Line Loopback condition upon recognition of this pattern. 
           The initating unit doesn't know if the command was accepted by 
           the remote unit.
         (2) csu loop down - commands the node to send a standard in-band 
           csu loop down pattern towards the WAN. This is a repetetive
           framed T1 signal consisting of two 'zeros' followed by one 'one'
           persisting for a few seconds in place of all T1 data. A 
           device terminating the WAN's physical link is expected to clear 
           any Line Loopback condition upon recognition of this pattern. 
           The initating unit doesn't know if the commad was accepted by 
           the remote unit.
         (3) dsu loop up - commands the node to send a proprietary in-band 
           dsu loop up pattern towards the WAN. This is a repetetive
           framed T1 signal consisting of a pseudorandom pattern persisting 
           for a few seconds in place of all T1 data. A compatible 
           device terminating the WAN's physical link is expected to enter 
           a Line Loopback condition upon recognition of this pattern. 
           The initating unit doesn't know if the command was accepted by 
           the remote unit.
         (4) dsu loop down - commands the node to send a proprietary in-band
           dsu loop down pattern towards the WAN. This is a repetetive
           framed T1 signal consisting of a pseudorandom pattern persisting 
           for a few seconds in place of all T1 data. A compatible 
           device terminating the WAN's physical link is expected to clear 
           any Line Loopback condition upon recognition of this pattern. 
           The initating unit doesn't know if the command was accepted by 
           the remote unit."
     ::= { tfrapDiagT1Table 5 }

tfrapDiagT1TimeRemaining OBJECT-TYPE
     SYNTAX      TimeTicks
     ACCESS      read-only
     STATUS      mandatory
     DESCRIPTION
        "The remaining time on the active loopback before the loopback 
         times out and automatically clears itself to restore the unit
         to normal operation. The time is in hundredths of seconds
         (TimeTicks)."
     ::= { tfrapDiagT1Table 6 }

--
--       The tfrapDiagDteTable
--              This table contains the DTE level diagnostics of the TFRAP CSU.
--

tfrapDiagDteTable   OBJECT IDENTIFIER ::= { tfrapDiagnostics 3 }

tfrapDiagDteSigRTS OBJECT-TYPE
          SYNTAX      INTEGER 
          {
               rts-signal-on  (1),
               rts-signal-off (2)
          }
          ACCESS      read-only
          STATUS      mandatory
          DESCRIPTION
             "Status of the Request to Send (RTS) signal from the DTE port.
              (1) RTS Active
              (2) RTS Inactive"
          ::= { tfrapDiagDteTable 1 }

tfrapDiagDteSigDTR OBJECT-TYPE
          SYNTAX      INTEGER 
          {
               dtr-signal-on  (1),
               dtr-signal-off (2)
          }
          ACCESS      read-only
          STATUS      mandatory
          DESCRIPTION
             "Status of the Data Terminal Ready (DTR) signal from the DTE port.
              (1) DTR Active
              (2) DTR Inactive"
          ::= { tfrapDiagDteTable 2 }

tfrapDiagDteLclLpbk OBJECT-TYPE
          SYNTAX      INTEGER
          {
               enable-loopback-mode (1),
               disable-loopback-mode (2)
          }
          ACCESS      read-write
          STATUS      mandatory
          DESCRIPTION
             "Controls the DTE loopback state. This is a 
              bi-directional loopback state where both the
              DTE and WAN ports are placed in line loopback. 
              All data received on each interface is sent back
              out the respective interface regardless of format
              or content. In Frame Relay applications the unit 
              will not preserve the LMI path during this diagnostic 
              and in-band management will not operate.
              (1) enable payload loopback
              (2) disable payload loopback"
          ::= { tfrapDiagDteTable 3 }

tfrapDiagDteV54Lpbk   OBJECT-TYPE
          SYNTAX      INTEGER
          {
               loopback-enable (1),
               loopback-disable (2)
          }
          ACCESS      read-only
          STATUS      mandatory
          DESCRIPTION
             "This reports the status of any remote V54 testing initiated by
              this unit. Remote V54 loopback commands are intended to place
              compatible external equipment into a loopback state. The initiating 
              unit will maintain normal data flows during these tests.
              (1) V54 loop up issued - indicates the node has sent a standard
                in-band loop up pattern towards the WAN per ITU V.54. This is a
                framed T1 signal consisting of a pseudorandom signal in place of 
                all user data (that is only in the DS0s assigned to the DTE). A 
                device terminating the fractional T1 data is expected to enter 
                a bi-directional DTE Loopback condition upon recognition of this
                pattern. The initating unit doesn't know if the command was accepted
                by the remote unit. This pattern will not traverse a typical frame
                relay network and is designed for circuit-switched diagnostics.
              (2) V54 loop down issued - indicates the node has sent a standard 
                in-band loop down pattern towards the WAN per ITU V.54. This is a
                framed T1 signal consisting of a pseudorandom signal in place of 
                all user data (that is only in the DS0s assigned to the DTE). A 
                device terminating the fractional T1 data is expected to clear 
                a bi-directional DTE Loopback condition upon recognition of this
                pattern. The initating unit doesn't know if the command was accepted
                by the remote unit."
          ::= { tfrapDiagDteTable 4 }

tfrapDiagDteRmtV54Lpbk   OBJECT-TYPE
          SYNTAX      INTEGER
          {
               transmit-code-enable  (3),
               transmit-code-disable (4)
          }
          ACCESS      write-only
          STATUS      mandatory
          DESCRIPTION
             "Remote V54 loopback commands are intended to place compatible
              external equipment into a loopback state. The initiating unit
              will maintain normal data flows during these tests. 
              (3) Transmit V54 loop up - commands the node to send a standard 
                in-band loop up pattern towards the WAN per ITU V.54. This is a
                framed T1 signal consisting of a pseudorandom signal in place of 
                all user data (that is only in the DS0s assigned to the DTE). A 
                device terminating the fractional T1 data is expected to enter 
                a bi-directional DTE Loopback condition upon recognition of this
                pattern. The initating unit doesn't know if the command was accepted
                by the remote unit. This pattern will not traverse a typical frame
                relay network and is designed for circuit-switched diagnostics.
              (4) Transmit V54 loop down - commands the node to send a standard 
                in-band loop down pattern towards the WAN per ITU V.54. This is a
                framed T1 signal consisting of a pseudorandom signal in place of 
                all user data (that is only in the DS0s assigned to the DTE). A 
                device terminating the fractional T1 data is expected to clear 
                a bi-directional DTE Loopback condition upon recognition of this
                pattern. The initating unit doesn't know if the command was accepted
                by the remote unit."
          ::= { tfrapDiagDteTable 5 }
                        
tfrapDiagDteBerState   OBJECT-TYPE
          SYNTAX      INTEGER
          {
               start-bert-test-t1     (1),
               start-bert-test-dte    (2),
               stop-bert-test         (3),
               inject-error-bert-test (4),
               clear-error-bert-test  (5)
          }
          ACCESS      write-only
          STATUS      mandatory
          DESCRIPTION
             "The unit is capable of sending a pseudorandom test pattern
              (511 or QRSS) out the WAN and monitoring the WAN received 
              data for the same pattern. The BERT pattern may be selected 
              to occupy either the full T1 payload or only the bandwidth
              allocated to the DTE (fractional T1). When a unit is sending
              this BERT, the receiver will monitor and characterize the 
              incoming signal for the same BERT pattern. In Frame Relay 
              applications the unit will not preserve the LMI path during
              this diagnostic and in-band management may not operate.
              This test may be ineffective in certain frame relay environments 
              as pseudorandom data lacks appropriate framing. Refer to 
              VLOOP and VBERT for PVC-based error-rate testing in a live frame 
              relay network.
              (1) Start a BERT test on full T1 - replaces entire T1 payload with
                the configured BERT pattern while monitoring the full T1 bandwidth
                (1.536M) for the presence of the BERT pattern.
              (2) Start a BERT test on fractional T1 - replaces only the protion
                of the T1 payload that has been allocated to the DTE with the
                configured BERT pattern while monitoring the same T1 bandwidth
                (DTE Data Rate) for the presence of the BERT pattern.
              (3) Stop a BERT test.
              (4) Inject a single bit error into the outgoing pattern.
              (5) Clear current BERT results."
          ::= { tfrapDiagDteTable 6 }

tfrapDiagDteBerStatus  OBJECT-TYPE
          SYNTAX      INTEGER 
          {
               bert-off         (1),
               bert-out-of-sync (2),
               bert-in-sync     (3)
          }
          ACCESS      read-only
          STATUS      mandatory
          DESCRIPTION
             "Displays the current BERT test sync status.
             (1) BERT is not running
             (2) BERT is running but is not in sync
             (3) BERT is running and has detected a received BERT"
          ::= { tfrapDiagDteTable 7 }

tfrapDiagDteBerErrors   OBJECT-TYPE
          SYNTAX      Counter
          ACCESS      read-only
          STATUS      mandatory
          DESCRIPTION
             "Displays the number of errors detected in Bert Test."
          ::= { tfrapDiagDteTable 8 }

tfrapDiagDteBerErrSec OBJECT-TYPE
          SYNTAX      Counter
          ACCESS      read-only
          STATUS      mandatory
          DESCRIPTION
             "Displays the number of seconds containing 1 or more errors
              in BERT Test."
          ::= { tfrapDiagDteTable 9 }

tfrapDiagDteBerTimeElaps OBJECT-TYPE
          SYNTAX      TimeTicks
          ACCESS      read-only
          STATUS      mandatory
          DESCRIPTION
             "Elapsed time since BERT test was started or cleared."
          ::= { tfrapDiagDteTable 10 }

tfrapDiagDteBerResyncs OBJECT-TYPE
          SYNTAX      Counter
          ACCESS      read-only
          STATUS      mandatory
          DESCRIPTION
             "Displays the number of times BERT test has synched up
              on the pattern. The BERT will attempt to resynchronize
              in response to excessive errors. A running count here
              indicates that a clean BERT is not being received."
          ::= { tfrapDiagDteTable 11 }

tfrapDiagDteBerPattern OBJECT-TYPE
          SYNTAX      INTEGER
          {
                five11-pattern  (1),
                qrss            (2)
          }
          ACCESS      read-write
          STATUS      mandatory
          DESCRIPTION
             "The type of pseudorandom BERT pattern used. 
              (1) 511: 9-bit pseudorandom pattern
              (2) QRSS: 20-bit pseudorandom pattern with 
                no more than 14 consecutive zeros" 
          ::= { tfrapDiagDteTable 12 }

tfrapDiagDteTimeRemaining OBJECT-TYPE
          SYNTAX      TimeTicks
          ACCESS      read-only
          STATUS      mandatory
          DESCRIPTION
             "The remaining time on the active diagnostic
              before it times out and the unit returns to
              normal operation. The time is hundredths of
              seconds (TimeTicks)."
          ::= { tfrapDiagDteTable 13 }



--
--       The tfrapDiagVnipTable
--              This table contains the VNIP level diagnostics of the TFRAP CSU.
--
--
tfrapDiagVnipTable  OBJECT-TYPE
      SYNTAX   SEQUENCE OF TFRAPDiagVnipEntry
      ACCESS   not-accessible
      STATUS   mandatory
      DESCRIPTION
         " Table of Diagnostics performed with the VNIP protocol"
      ::= { tfrapDiagnostics 6 }

    tfrapDiagVnipEntry OBJECT-TYPE
        SYNTAX   TFRAPDiagVnipEntry
        ACCESS   not-accessible
        STATUS   mandatory
        DESCRIPTION
           "VNIP VLOOP and VBERT diagnostic profile. Initiating
            these tests require an established and stable VNIP topology
            on an interface. Once the topology is in place, the user
            can execute a PVC-based diagnostic between this unit and
            any indexed entry in the topology table. The index into the 
            topology table for a particular interface is required."
        INDEX {tfrapDiagVnipInterface, tfrapDiagVnipIndex}
         ::= { tfrapDiagVnipTable 1 }

    TFRAPDiagVnipEntry ::=
          SEQUENCE {
                tfrapDiagVnipInterface          INTEGER,
                tfrapDiagVnipIndex              INTEGER,
                tfrapDiagVnipDlci               INTEGER,
                tfrapDiagVnipIpAddr             IpAddress,
                tfrapDiagVLOOP                  INTEGER,
                tfrapDiagVBERT                  INTEGER,
                tfrapDiagVBERTRate              INTEGER,
                tfrapDiagVBERTSize              INTEGER,
                tfrapDiagVBERTPktPercent        INTEGER,
                tfrapDiagVBERTTestPeriod        INTEGER
          }

tfrapDiagVnipInterface OBJECT-TYPE
   SYNTAX      INTEGER
   {
        dte-interface (1),
        t1-interface (2)
   }
   ACCESS      read-write
   STATUS      mandatory
   DESCRIPTION
      "The interface out which a PVC-based VNIP diagnostic
       will be run. This must be an interface with a valid 
       and stable VNIP topology for a VNIP Diagnostic."
   ::= { tfrapDiagVnipEntry 1 }

tfrapDiagVnipIndex OBJECT-TYPE
    SYNTAX      INTEGER
    ACCESS      read-write
    STATUS      mandatory
    DESCRIPTION
       "The index to the external VNIP peer as presented by the VNIP
        topology database for the given interface. Refer to 
        VnipTopologyTable to determine the index of the remote peer."
    ::= { tfrapDiagVnipEntry 2 }

tfrapDiagVnipDlci    OBJECT-TYPE
    SYNTAX      INTEGER
    ACCESS      read-only
    STATUS      mandatory
    DESCRIPTION
       "This is the DLCI value for the given interface/index
        combination. This comes from the VniptTopologyTable."
    ::= { tfrapDiagVnipEntry 3 }

tfrapDiagVnipIpAddr   OBJECT-TYPE
    SYNTAX      IpAddress
    ACCESS      read-only
    STATUS      mandatory
    DESCRIPTION
       "This is the ip address for the given interface/index
        combination. This comes from the VniptTopologyTable."
    ::= { tfrapDiagVnipEntry 4 }

tfrapDiagVLOOP OBJECT-TYPE
    SYNTAX      INTEGER
    {
         start-test         (1),
         stop-test          (2)
    }
    ACCESS      write-only
    STATUS      mandatory
    DESCRIPTION
       "Controls execution of the Vnip Logical Loopback (VLOOP) test. 
        VLOOP is designed as an intrusive test and customer data 
        on the DLCI-under-test will be discarded. The VLOOP test includes
        a timed VBERT test and is run using the profile configured within 
        this table.
        (1) start VLOOP test 
        (2) stop VLOOP test (override VBERT test duration)"
    ::= { tfrapDiagVnipEntry 5 }

 
tfrapDiagVBERT OBJECT-TYPE
    SYNTAX      INTEGER
    {
         start     (1),
         stop      (2)
    }
    ACCESS      write-only
    STATUS      mandatory
    DESCRIPTION
       "Controls execution of the Vnip Virtual Bit Eror Rate (VBERT) test. 
        VBERT is designed to be a non-intrusive test and will attempt to
        statistically multiplex VBERT test data and customer data on the
        DLCI-under-test. However, VBERT data is given priority over customer
        data when the selected VBERT volume causes internal congestion. 
        The test is run using the profile configured within this table.
        (1) start test 
        (2) stop test (override VBERT test duration)"
    ::= { tfrapDiagVnipEntry 6 }


tfrapDiagVBERTRate  OBJECT-TYPE
    SYNTAX      INTEGER (8000..2048000)
    ACCESS      read-write
    STATUS      mandatory
    DESCRIPTION
       "Specifies the throughput bit rate applied by VBERT or 
        VLOOP to the DLCI-under-test. For DTE Rates or configured
        CIR up to 64K the maximum VBERT rate is either the DTE data
        rate or 110% of CIR (which ever is less). For DTE Rates or
        configured CIR greater than 64K, the maximum VBERT rate is 
        75% of the DTE data rate or 110% of CIR (which ever is less). 
        Note that selecting rates that approach line rate will impact 
        neighboring PVCs.
        (8000-1152000): VBERT/VLOOP data rate (in bits per second)."
    ::= { tfrapDiagVnipEntry 7 }


tfrapDiagVBERTSize  OBJECT-TYPE
    SYNTAX      INTEGER 
    {
       pkt-size-64      (64),
       pkt-size-128     (128),
       pkt-size-256     (256),
       pkt-size-512     (512),
       pkt-size-1024    (1024),
       pkt-size-2048    (2048)
    }
    ACCESS      read-write
    STATUS      mandatory
    DESCRIPTION
       "Specifies the size of framed data that will be used
        during the VBERT test, measured in Bytes.
         (64) 64-byte frames
         (128) 128-byte frames
         (256) 256-byte frames
         (512) 512-byte frames
         (1024) 1024-byte frames
         (2048) 2048-byte frames"
    ::= { tfrapDiagVnipEntry 8 }


tfrapDiagVBERTPktPercent  OBJECT-TYPE
    SYNTAX      INTEGER 
    {
       zero-percent        (0),
       twentyFive-percent  (25),
       fifty-percent       (50),
       seventyFive-percent (75),
       oneHundred-percent  (100)
    }
    ACCESS      read-write
    STATUS      mandatory
    DESCRIPTION
        "Specifies percentage of VBERT packets that will have the
         Frame Relay Discard Eligibility bit set. Frames with this
         bit set may be more likley to get dropped in a congested
         network.
         (0) 0%  of the test frames are marked discard eligible
         (25) 25% of the test frames are marked discard eligible
         (50) 50% of the test frames are marked discard eligible
         (75) 75% of the test frames are marked discard eligible
         (100) 100% of the test frames are marked discard eligible"
    ::= { tfrapDiagVnipEntry 9 }

tfrapDiagVBERTTestPeriod  OBJECT-TYPE
    SYNTAX      INTEGER (10..1440)
    ACCESS      read-write
    STATUS      mandatory
    DESCRIPTION
       "Specifies the duration of a VBERT test. Note that VBERT is 
        subjected to the unit's Loopback Timer and will be terminated 
        by whichever timer expires first.
        (10-1440): VBERT time duration in seconds"
    ::= { tfrapDiagVnipEntry 10 }



-- =========================
-- ==    STATUS group     ==
-- =========================

tfrapStatus  OBJECT IDENTIFIER ::= { tfrap 4 }


--
--      Interface Status 
--
--         The current status of the DTE and T1 ports.
--

tfrapStatusIntfTable   OBJECT IDENTIFIER ::= { tfrapStatus 1 }

tfrapIntfDteMode   OBJECT-TYPE
     SYNTAX  INTEGER
     {
        no-connections (1),
        active         (2),
        test           (3)
     }
     ACCESS  read-only
     STATUS  mandatory
     DESCRIPTION
      "Status of allocation of T1 bandwidth to the DTE port data. 
      (1) no connections - indicates the DTE port has no connections 
        to the WAN. 
      (2) Active - indicates DTE data rate has been assigned T1 DS0s
          and is in a normal data mode.
      (3) Test -  indicates DTE data rate has been assigned T1 DS0s
          but is in a diagnostic condition."
     ::= { tfrapStatusIntfTable 1 }

tfrapIntfDteRts   OBJECT-TYPE
     SYNTAX  INTEGER
     {
        on  (1),
        off (2)
     }
     ACCESS  read-only
     STATUS  mandatory
     DESCRIPTION
        "Status of the Request to Send (RTS) signal from the DTE port.
         (1) RTS Active
         (2) RTS Inactive"
     ::= { tfrapStatusIntfTable 2 }

tfrapIntfDteDtr   OBJECT-TYPE
     SYNTAX  INTEGER
     {
        on  (1),
        off (2)
     }
     ACCESS  read-only
     STATUS  mandatory
     DESCRIPTION
        "Status of the Data Terminal Ready (DTR) signal from the DTE port.
         (1) DTR Active
         (2) DTR Inactive"
     ::= { tfrapStatusIntfTable 3 }

tfrapIntfT1Mode   OBJECT-TYPE
     SYNTAX  INTEGER
     {
        no-connections (1),
        active         (2),
        test           (3)
     }
     ACCESS  read-only
     STATUS  mandatory
     DESCRIPTION
        "Status of allocation of T1 bandwidth to the DTE port data. 
         (1) no connections - indicates the DTE port has no connections 
           to the WAN. 
         (2) Active - indicates DTE data rate has been assigned T1 DS0s
           and is in a normal data mode.
         (3) Test -  indicates DTE data rate has been assigned T1 DS0s
           but is in a diagnostic condition."
     ::= { tfrapStatusIntfTable 4 }

tfrapIntfT1Status   OBJECT-TYPE
     SYNTAX  INTEGER
     {
        t1-frame-sync-okay                (1),
        t1-frame-sync-with-errors         (2),
        signal-present-without-frame-sync (3),
        signal-not-present                (4), 
        not-applicable                    (5)
     }
     ACCESS  read-only
     STATUS  mandatory
     DESCRIPTION
      "Status of the signal received from the WAN
       (1) In Sync - unit has detected a properly framed T1 signal
           and is not experiencing any error conditions.
       (2) In Sync with Errors - unit has detected a properly framed 
           T1 signal but is experiencing some error conditions. Refer to
           T1 current performance results for details.
       (3) Signal Detected without Frame Sync - while a signal is present
           from the WAN it does not contain the framing pattern defined for
           this unit. This could be either incorrectly configured T1 Frame 
           type or the presence of an alarm condition on the WAN.
       (4) No Carrier - there is no signal detected from the WAN.
       (5) Not Applicable."
     ::= { tfrapStatusIntfTable 5 }

tfrapIntfT1Alarms   OBJECT-TYPE
     SYNTAX  INTEGER
     {
        no-alarms                  (1),
        red-alarm-declared         (2), 
        yellow-alarm-detected      (3),
        unframed-all-ones-detected (4)
     }
     ACCESS  read-only
     STATUS  mandatory
     DESCRIPTION
        "Alarms present at the T1 port.
         (1) No alarm conditions present.
         (2) Red Alarm Declared - Unit has experienced loss of frame 
             synchronization with the signal received from the WAN 
             for an extended time and is reporting an alarm condition 
             that severely impairs normal operation. During this Red 
             Alarm condition the unit will transmit Yellow alarm back 
             to the WAN. If this condition persists consult your 
             service provider.
         (3) Yellow ALarm Detected - Unit is receiving a yellow alarm 
             indication from the wide area network. Detection of yellow 
             alarm implies that the attached device is in a red alarm 
             conditon. Red alarm is declared due to the extended absence 
             of a properly framed signal. If this condition persists 
             consult your service provider.
         (4) Unframe All Ones Detected - Unit is receiving unframed all 
             ones from the wide area network (AIS, blue alarm). Detection 
             of AIS implies that the attached device is reporting
             an alarm condition from an upstream device. If 
             this condition persists consult your service provider."
     ::= { tfrapStatusIntfTable 6 }

tfrapIntfDteDcd OBJECT-TYPE
     SYNTAX      INTEGER
     {
          on   (1),
          off  (2),
          na   (3)
     }
     ACCESS      read-only
     STATUS      mandatory
     DESCRIPTION
        "Status of the Data Carrier Detect (DCD) signal driven by this
         unit towards the DTE port
         (1) DCD Active
         (2) DCD Inactive"
     ::= { tfrapStatusIntfTable 7  }

tfrapIntfDteDsr OBJECT-TYPE
     SYNTAX      INTEGER
     {
          on   (1),
          off  (2),
          na   (3)
     }
     ACCESS      read-only
     STATUS      mandatory
     DESCRIPTION
        "Status of the Data Set Ready (DSR) signal driven by this
         unit towards the DTE port.
         (1) DSR Active
         (2) DSR Inactive" 
     ::= { tfrapStatusIntfTable 8 }

tfrapIntfDteCts OBJECT-TYPE
     SYNTAX      INTEGER
     {
          on   (1),
          off  (2),
          na   (3)
     }
     ACCESS      read-only
     STATUS      mandatory
     DESCRIPTION
        "Status of the Clear to Send (CTS) signal driven by this
         unit towards the DTE port
         (1) CTS Active
         (2) CTS Inactive"
     ::= { tfrapStatusIntfTable 9 }

--
--      LED Status 
--
--         The current status of the front-panel LED indicators at 
--         the TFRAP node.
--

tfrapStatusLedTable   OBJECT IDENTIFIER ::= { tfrapStatus 4 }

tfrapStatusDteModeLED   OBJECT-TYPE
     SYNTAX  INTEGER
     {
        offLED-DTE-inactive               (1),
        greenLED-normal                   (2),
        yellowLED-test-mode               (3),
        redLED-no-active-WAN-connection   (4)
     }
     ACCESS  read-only
     STATUS  mandatory
     DESCRIPTION
        "Status of the DTE Mode LED.
         (1) DTE Mode LED off: Missing control signals
         (2) DTE Mode LED green: Normal
         (3) DTE Mode LED yellow: Test Mode"
     ::= { tfrapStatusLedTable 1 }

tfrapStatusDteStatusLED   OBJECT-TYPE
     SYNTAX  INTEGER
     {
        offLED-inactive                   (1),
        greenLED-active                   (2)
     }
     ACCESS  read-only
     STATUS  mandatory
     DESCRIPTION
        "Status of the DTE Status LED.
         (1) DTE Status LED off: no connections to WAN
         (2) DTE Status LED green: normal"
     ::= { tfrapStatusLedTable 2 }

tfrapStatusDteTxLED   OBJECT-TYPE
     SYNTAX  INTEGER
     {
        offLED-inactive                   (1),
        greenLED-tx-data-transmitting     (2),
        yellowLED-disabled                (3)
     }
     ACCESS  read-only
     STATUS  mandatory
     DESCRIPTION
        "Status of the DTE Tx Data LED. In Frame Relay mode, this LED is ON 
         (green) when the DTE is not sending HDLC Flags and is OFF when
         HDLC flags are being transmit. In CBO mode, the LED is ON (green) 
         for a SPACE and OFF for a MARK.
         (1) DTE Transmit LED OFF: inactive (HDLC flags or CBO marks)
         (2) DTE Transmit LED ON: active (HDLC frames or CBO spaces)"
     ::= { tfrapStatusLedTable 3 }

tfrapStatusDteRxLED   OBJECT-TYPE
     SYNTAX  INTEGER
     {
        offLED-inactive                   (1),
        greenLED-rx-data-receiving        (2),
        yellowLED-disabled                (3)
     }
     ACCESS  read-only
     STATUS  mandatory
     DESCRIPTION
        "Status of the DTE Rx Data LED. In Frame Relay mode, this LED is ON 
         (green) when the WAN is receiving HDLC Flags and is OFF when
         HDLC flags are being received. In CBO mode, the LED is ON (green) 
         for a SPACE and OFF for a MARK.
         (1) DTE Receive LED OFF: inactive (HDLC flags or CBO marks)
         (2) DTE Receive LED ON: active (HDLC frames or CBO spaces)"
     ::= { tfrapStatusLedTable 4 }

tfrapStatusT1ModeLED   OBJECT-TYPE
     SYNTAX  INTEGER
     {
        greenLED-normal                   (2),
        yellowLED-test-mode               (3)
     }
     ACCESS  read-only
     STATUS  mandatory
     DESCRIPTION
      "Status of the WAN Mode LED.
       (1) WAN Mode LED is green: normal data mode
       (2) WAN Mode LED is yellow: test mode"

     ::= { tfrapStatusLedTable 5 }

tfrapStatusT1StatusLED   OBJECT-TYPE
     SYNTAX  INTEGER
     {
        offLED-T1-no-signal                     (1),
        greenLED-normal                         (2),
        yellowLED-remote-alarm                  (3),
        redLED-red-alarm                        (4),
        blinking-redLED-no-carrier-red-alarm    (5),
        blinking-red-greenLED-transient-error   (6),
        blinking-red-yellowLED-AIS              (7)
     }
     ACCESS  read-only
     STATUS  mandatory
     DESCRIPTION
        "Status of the WAN Status LED.
         (1) Off - no signal detected from WAN.
         (2) Green - framed signal detected with no errors (normal operation)
         (3) Yellow - remote alarm condition detected (yellow or AIS alarms)
         (4) Red - unit has declared Red Alarm due to the presence of an 
             improperly framed signal from the WAN.
         (5) Blinking Red and Off - unit has declared Red Alarm due to the
             absence of a signal from the WAN.
         (6) Blinking Green and Red - unit is receiving a properly framed signal
             from the WAN but has detected a transient error condition. Possible
             Line Code Violations or ESF CRC errors indicating errored data bits.
         (7) Blinking Red and Yellow - unit is receiving an unframed all ones (AIS)
             from the WAN. This is indicative of an upstream alarm condition on the 
             WAN."
     ::= { tfrapStatusLedTable 6 }

tfrapStatusAllLEDs   OBJECT-TYPE
     SYNTAX      DisplayString (SIZE (0..7))
     ACCESS  read-only
     STATUS  mandatory
     DESCRIPTION
      "Status of all six TFRAP LEDs, encoded in a string.
           'F'    off
           '5'    green
           '0'    yellow
           'A'    red
           '7'    blinking green and off
           '3'    blinking yellow and off
           'B'    blinking red and off
           '4'    blinking green and yellow
           '6'    blinking green and red
           '8'    blinking yellow and red

       Positionally, the 6 letters are DTE Mode, DTE status,
       Dte Tx, Dte Rx, T1 Mode, and T1 Status.  For example,
       '555556' would mean:  DTE in normal mode, active status,
       transmitting and receiving and T1 normal with transient errors."
     ::= { tfrapStatusLedTable 7 }



--
--     Table of peers discovered by VNIP
--

tfrapVnipTopologyTable   OBJECT-TYPE
      SYNTAX   SEQUENCE OF TFRAPVnipTopologyEntry
      ACCESS   not-accessible
      STATUS   mandatory
      DESCRIPTION
        "VNIP topology is a feature that, for each interface, maps all 
         compatible VNIP peers, their DLCI value, ip address and relative 
         location. The topology is a fundamental prerequisite to applying 
         the VNIP feature set which includes PVC-based delay measurement, 
         diagnostics, and congestion monitoring. With VNIP enabled on an 
         interface the unit will attempt to locate VNIP peers out that port.
         As peers are discovered and logged the unit will report the topology
         it has learned on its opposite interface. If VNIP is inactive on 
         one interface it will not engage in any VNIP dialog; however it 
         will continue to listen for topology messages on the inactive 
         interface and will reflect these messages out the opposite interface
         if VNIP is enabled. With VNIP inactive on both interfaces the unit 
         will transparently pass all VNIP messages. The topology database 
         includes the interface, local DLCI value, remote peer DLCI value, 
         remote peer ip address, and the number of VNIP hops in between.
         This table also reports the status of other VNIP features as well."
      ::= { tfrapStatus 2 }

      tfrapVnipTopologyEntry OBJECT-TYPE
          SYNTAX   TFRAPVnipTopologyEntry
          ACCESS   not-accessible
          STATUS   mandatory
          DESCRIPTION
             "The DLCI, IP address, and number of hops for a particular 
              node, discovered via VNIP off of an interface.  The entry 
              may also have transit delay measurements and VBERT diagnostic
              status to report as well."
         INDEX { tfrapVnipTopologyInterface, tfrapVnipTopologyIndex }
         ::= { tfrapVnipTopologyTable 1 }

      TFRAPVnipTopologyEntry ::=
          SEQUENCE {
              tfrapVnipTopologyInterface INTEGER,
              tfrapVnipTopologyIndex     INTEGER,
              tfrapVnipTopologyDlci      INTEGER,
              tfrapVnipTopologyIpAddr    IpAddress,
              tfrapVnipTopologyNumHops   INTEGER,
              tfrapVnipTopologyLocalDlci INTEGER,
              tfrapVnipTopoTDNumSamples  Counter,
              tfrapVnipTopoTDAvgDelay    Counter,
              tfrapVnipTopoTDMaxDelay    Counter,
              tfrapVnipTopoTDMinDelay    Counter,
              tfrapVnipTopoTDLastDelay   Counter,
              tfrapVnipTopoVLOOPStatus            INTEGER,
              tfrapVnipTopoVBERTStatus            INTEGER,
              tfrapVnipTopoVBertTxDESetFrames     Counter,
              tfrapVnipTopoVBertRxDESetFrames     Counter,
              tfrapVnipTopoVBertTxDEClrFrames     Counter,
              tfrapVnipTopoVBertRxDEClrFrames     Counter,
              tfrapVnipTopoVBertTransitDelayMax   Counter,
              tfrapVnipTopoVBertTransitDelayAvg   Counter,
              tfrapVnipTopoVBertTimeElapse        TimeTicks,
              tfrapVnipTopoVBertPerUtilCIR        INTEGER,
              tfrapVnipTopoVBertPerUtilEIR        INTEGER
          }

      tfrapVnipTopologyInterface OBJECT-TYPE
          SYNTAX      INTEGER
          {
               dte-interface (1),
               t1-interface (2)
          }
          ACCESS      read-only
          STATUS      mandatory
          DESCRIPTION
             "The interface off of which the peer was
              discovered.  Topology is discovered by
              sending VNIP messages out each interface.
              Units discovered via a particular interface
              are kept in a list associated with that
              interface.
              (1) VNIP peers and status out DTE interface
              (2) VNIP peers and status out WAN interface"
          ::= { tfrapVnipTopologyEntry 1 }

      tfrapVnipTopologyIndex OBJECT-TYPE
          SYNTAX      INTEGER
          ACCESS      read-only
          STATUS      mandatory
          DESCRIPTION
             "The number of this discovered peer in the list
              of nodes for this interface. For each interface,
              the nodes are numbered 1 through n. This index
              is required when disabling or enabling VBERT/VLOOP
              to a particular peer."
          ::= { tfrapVnipTopologyEntry 2 }

      tfrapVnipTopologyDlci    OBJECT-TYPE
          SYNTAX      INTEGER 
          ACCESS      read-only
          STATUS      mandatory
          DESCRIPTION
             "The DLCI of the discovered neighboring peer.
              This may be different from the local DLCI."
         ::= { tfrapVnipTopologyEntry 3 }

      tfrapVnipTopologyIpAddr   OBJECT-TYPE
          SYNTAX      IpAddress
          ACCESS      read-only
          STATUS      mandatory
          DESCRIPTION
             "The IP address for the discovered peer."
          ::= { tfrapVnipTopologyEntry 4 }
 
      tfrapVnipTopologyNumHops OBJECT-TYPE
          SYNTAX      INTEGER
          ACCESS      read-only
          STATUS      mandatory
          DESCRIPTION
             "The discovered peer is this number of hops away. 
              Each hop is a VNIP peer."
          ::= { tfrapVnipTopologyEntry 5 }
 
      tfrapVnipTopologyLocalDlci OBJECT-TYPE
          SYNTAX      INTEGER
          ACCESS      read-only
          STATUS      mandatory
          DESCRIPTION
             "The DLCI from this unit over which the remote peer
              was discovered."
          ::= { tfrapVnipTopologyEntry 6 }

      tfrapVnipTopoTDNumSamples  OBJECT-TYPE
          SYNTAX      Counter
          ACCESS      read-only
          STATUS      mandatory
          DESCRIPTION
            "The number of transit delay samples collected."
          ::= { tfrapVnipTopologyEntry 10 }

      tfrapVnipTopoTDAvgDelay  OBJECT-TYPE
          SYNTAX      Counter
          ACCESS      read-only
          STATUS      mandatory
          DESCRIPTION
             "The average transit delay between this
              unit and the remote peer (in milliseconds)."
          ::= { tfrapVnipTopologyEntry 11 }

      tfrapVnipTopoTDMaxDelay  OBJECT-TYPE
          SYNTAX      Counter
          ACCESS      read-only
          STATUS      mandatory
          DESCRIPTION
            "The maximum transit delay between this
             node and the remote peer (in milliseconds)."
          ::= { tfrapVnipTopologyEntry 12 }

      tfrapVnipTopoTDMinDelay  OBJECT-TYPE
          SYNTAX      Counter
          ACCESS      read-only
          STATUS      mandatory
          DESCRIPTION
            "The minimum transit delay between this
             node and the remote peer (in milliseconds)."
          ::= { tfrapVnipTopologyEntry 13 }

      tfrapVnipTopoTDLastDelay  OBJECT-TYPE
          SYNTAX      Counter
          ACCESS      read-only
          STATUS      mandatory
          DESCRIPTION
            "The most recent transit delay measured between
             this node and the remote peer (in milliseconds)."
          ::= { tfrapVnipTopologyEntry 14 }


      tfrapVnipTopoVLOOPStatus   OBJECT-TYPE
          SYNTAX      INTEGER
          {
               loopback-enable (1),
               loopback-disable (2)
          }
          ACCESS      read-only
          STATUS      mandatory
          DESCRIPTION
             "This selection displays the status of the VNIP PVC
              Loopback for this entry. This loopback is initiated 
              by the remote node through the VLOOP utility, causing 
              this node to loop data back to the remote node.
              (1) Virtual Loopback path present on this PVC due to
                  command received from remote unit. All data received
                  on this DLCI will be looped back out the same interface.
              (2) No active VLOOP test on this"
          ::= { tfrapVnipTopologyEntry  15 }
      

      tfrapVnipTopoVBERTStatus  OBJECT-TYPE
          SYNTAX      INTEGER
          {
               off            (1),
               testing        (2),
               test-failed    (3),
               test-completed (4),
               in-test        (5)
      
          }
          ACCESS      read-only
          STATUS      mandatory
          DESCRIPTION
             "Displays the current status of the VBERT/VLOOP test.
              (1) Off: no test has run or the entry has been cleared
              (2) Testing: the entry is generating VBERT test frames
              (3) Test Failed: the request for a test on this entry failed  
              (4) Test Completed: a test has run and is finished results 
                  are complete
              (5) In Test: the entry is on the receiving end of VBERT packets"
          ::= { tfrapVnipTopologyEntry 16 }
  

      tfrapVnipTopoVBertTxDESetFrames   OBJECT-TYPE
          SYNTAX      Counter
          ACCESS      read-only
          STATUS      mandatory
          DESCRIPTION
             "Displays the number of Frames transmitted during VBERT Test that
              had the Discard Eligibility indicator bit set."
          ::= { tfrapVnipTopologyEntry  17 }

     
      tfrapVnipTopoVBertRxDESetFrames OBJECT-TYPE
          SYNTAX      Counter
          ACCESS      read-only
          STATUS      mandatory
          DESCRIPTION
             "Displays the number of Frames received during VBERT Test that 
              had the Discard Eligibility indicator bit set."
          ::= { tfrapVnipTopologyEntry  18 }
     
   
     
      tfrapVnipTopoVBertTxDEClrFrames   OBJECT-TYPE
          SYNTAX      Counter
          ACCESS      read-only
          STATUS      mandatory
          DESCRIPTION
             "Displays the number of Frames transmitted during VBERT Test that
              had the Discard Eligibility indicator bit cleared."
          ::= { tfrapVnipTopologyEntry  19 }
      
      
      tfrapVnipTopoVBertRxDEClrFrames OBJECT-TYPE
          SYNTAX      Counter
          ACCESS      read-only
          STATUS      mandatory
          DESCRIPTION
             "Displays the number of Frames received during VBERT Test that 
              had the Discard Eligibility indicator bit cleared."
          ::= { tfrapVnipTopologyEntry  20 }
      
      tfrapVnipTopoVBertTransitDelayMax OBJECT-TYPE
          SYNTAX      Counter
          ACCESS      read-only
          STATUS      mandatory
          DESCRIPTION
             "The maximum transit delay between this node and the 
              remote peer during the VBERT test. This delay measurement
              will include internal device latencies. This result may
              differ from the VNIP transit delay measurement which accounts
              for internal latencies."
          ::= { tfrapVnipTopologyEntry  21 }
      
       
      tfrapVnipTopoVBertTransitDelayAvg OBJECT-TYPE
          SYNTAX      Counter
          ACCESS      read-only
          STATUS      mandatory
          DESCRIPTION
             "The average transit delay between this node and the remote 
              peer during the VBERT test. This delay measurement
              will include internal device latencies. This result may
              differ from the VNIP transit delay measurement which accounts
              for internal latencies"
          ::= { tfrapVnipTopologyEntry  22 }
      
      tfrapVnipTopoVBertTimeElapse OBJECT-TYPE
          SYNTAX      TimeTicks
          ACCESS      read-only
          STATUS      mandatory
          DESCRIPTION
             "Elapsed time since VBERT/VLOOP test was started or cleared
              (in seconds)."
          ::= { tfrapVnipTopologyEntry  23 }

      tfrapVnipTopoVBertPerUtilCIR OBJECT-TYPE
          SYNTAX      INTEGER
          ACCESS      read-only
          STATUS      mandatory
          DESCRIPTION
             " The calculated percent of CIR utilization during a VBERT test,
               this value is only valid after a test is complete not during."
          ::= { tfrapVnipTopologyEntry 24 }


      tfrapVnipTopoVBertPerUtilEIR OBJECT-TYPE
          SYNTAX      INTEGER
          ACCESS      read-only
          STATUS      mandatory
          DESCRIPTION
             " The calculated percent of EIR utilization during a VBERT test,
               this value is only valid after a test is complete not during."
          ::= { tfrapVnipTopologyEntry 25 }


tfrapVnipTransitDelayClear    OBJECT-TYPE
          SYNTAX      INTEGER
          {
              clear-transit-delay (1)
          }
          ACCESS      write-only
          STATUS      mandatory
          DESCRIPTION
             "Allows the user to clear all the VNIP Transit Delay
              data collected in the VNIP topology database.
              (1) Clear entire Transit Delay results database"
          ::= { tfrapStatus 5 }

tfrapLmiSourcing OBJECT-TYPE
         SYNTAX      INTEGER
         {
              initializing (1),
              passthrough  (2),
              user-dte     (3),
              user-t1      (4),
              network-dte  (5),
              network-t1   (6),
              disabled     (7),
              both-ports   (8)
         }
         ACCESS      read-only
         STATUS      mandatory
         DESCRIPTION
            "If configured for Frame Relay with a non-zero LMI inactivity timer
             the unit will monitor the status of LMI and, if proper messaging
             is not detected, will attempt to emulate either Frame Relay DTE or 
             DCE devices in attempt to restore LMI to any attached equipment and 
             provide managed access for diagnostic purposes. Typically frads/routers 
             are Frame Relay DTE while switches are Frame Relay DCE but this model
             may vary. In the absence of full-duplex LMI, the unit will cycle 
             through various states in attempt to adapt to an LMI partner.  The 
             unit will try each state for the duration of the LMI Inactivity timer 
             and then advance to the next one if satisfactory handshaking is not 
             established. While in any of these states if full-duplex LMI handshaking 
             does appear, the unit will immediately revert to the passthrough state.
             (1) initializing
             (2) Passthrough: not sourcing any LMI messages.
             (3) Status Enquiries out DTE interface: unit is emulating a Frame 
                 Relay DTE device out the its (physical) DTE interface. 
             (4) Status Enquiries out WAN interface: unit is emulating a Frame 
                 Relay DTE device out the its WAN interface.
             (5) Status Responses out the DTE interface: unit is emulating a 
                 Frame Relay DCE device out the its (physical) DTE interface
                 (provisioning the single default management DLCI).
             (6) Status Responses out the WAN interface: unit is emulating a 
                 Frame Relay DCE device out the its WAN interface (provisioning 
                 the single default management DLCI).
             (7) Disabled - LMI Inactivity timer is zero or unit not configured
                 for a Frame Relay application.
             (8) Status Responses out both DTE and WAN interfaces: unit is 
                 configured for Fixed DCE mode of management and emulates a Frame
                 Relay DCE independently on both ports (provisioning 
                 the single default management DLCI)."
         ::= { tfrapStatus 6 }

tfrapVBertClear    OBJECT-TYPE
          SYNTAX      INTEGER
          {
              clear-vbert (1)
          }
          ACCESS      write-only
          STATUS      mandatory
          DESCRIPTION
             "Allows the user to clear all the VBERT data
              collected in the VNIP topology database as long as 
              the entry is not in a test status.
              (1) Clear all VBERT/VLOOP status information"
      ::= { tfrapStatus 11 }

--
--      Management Status 
--
--         The current status of the InBand Mangement configuration. 
--         This section is intended to display a status summary of 
--         how the TFRAP is configured for ip-based Management.
--
tfrapStatusMgmtTable   OBJECT IDENTIFIER ::= { tfrapStatus 3 }

tfrapStatusMgmtChannel   OBJECT-TYPE
     SYNTAX  INTEGER
     {
        none             (1),
        slip             (2), 
        private-dlci     (3),
        piggyback-dlci   (4)
     }
     ACCESS  read-only
     STATUS  mandatory
     DESCRIPTION
        "This is the method in which the unit is configured for
         SNMP management access.
         (1) None: SNMP management disabled
         (2) SLIP: out-of-band management via asynchronous Serial Line IP
         (3) Private DLCI: in-band management using a private DLCI that 
             is dedicated solely to this unit's management.
         (4) Piggyback DLCI: in-band management using any DLCI optionally
             multiplexing both management and user data."
    ::= {tfrapStatusMgmtTable 1}                

tfrapStatusMgmtInterface   OBJECT-TYPE
     SYNTAX  INTEGER
     {
        comm            (1),
        dte             (2), 
        t1              (3),
        dte-and-t1      (4)
     }
     ACCESS  read-only
     STATUS  mandatory
     DESCRIPTION
        "This is the port(s) on which the management traffic will appear.
         (1) Async Maintenance(Comm)/Console port - SLIP mode
         (2) Local DTE interface: unit is configured for Private Local 
             DLCI mode
         (3) Remote WAN Interface: unit is confiogured for Private Remote
             DLCI mode
         (4) DTE and WAN Interfaces: unit is configured for either Piggyback
             Bidirectional mode."
     ::= {tfrapStatusMgmtTable 2}                

tfrapStatusMgmtInterfaceStatus   OBJECT-TYPE
     SYNTAX  INTEGER
     {
        active     (1),
        inactive   (2), 
        alarm      (3)
     }
     ACCESS  read-only
     STATUS  mandatory
     DESCRIPTION
        "This is the status of the port(s) on which
         the management traffic will appear.
         (1) Active: port or DLCI is configured and status is okay
         (2) Inactive: port or DLCI is declared out of service 
         (3) Alarm: port or DLCI is experiencing an alarm condition that may
             interefere with management access  "
     ::= {tfrapStatusMgmtTable 3}                

tfrapStatusMgmtDefaultDLCINo   OBJECT-TYPE
     SYNTAX  INTEGER
     ACCESS  read-only
     STATUS  mandatory
     DESCRIPTION
        "This is the DLCI for the PVC that is defined for the
        Management port.  All traffic using this DLCI in the Frame
        Replay packet will be destined for the InBand Management task."
     ::= {tfrapStatusMgmtTable 4}                

tfrapStatusMgmtDefaultDLCIStatus   OBJECT-TYPE
     SYNTAX  INTEGER
     {
        na              (1),
        dlci-active     (2), 
        dlci-inactive   (3)
     }
     ACCESS  read-only
     STATUS  mandatory
     DESCRIPTION
        "This is the status of the default management DLCI.
         (1) not applicable: SLIP mode or management is disabled
         (2) DLCI Active: default DLCI is active in the LMI full 
             status response.
         (3) DLCI Inactive: default DLCI is not active in the LMI full 
             status response."
     ::= {tfrapStatusMgmtTable 5}                

tfrapStatusLmiAutosense   OBJECT-TYPE
     SYNTAX  INTEGER
     {
        disabled            (1),
        searching           (2),
        learned-annex-d     (3),
        learned-annex-a     (4),
        learned-type1       (5)
     }
     ACCESS  read-only
     STATUS  mandatory
     DESCRIPTION
        "This indicates the current status of LMI Auto Sensing if 
         it's enabled.
         (1) Disabled: LMI is configured as Type 1, Annex-D, or Annex-A
         (2) Searching: unit is attempting to determine the LMI type of
             the attached equipment by issuing LMI messages of each LMI 
             type and searching for responses.
         (3) Learned Annex-D: unit has successfully detected Annex-D LMI
             (ANSI T1.617 Annex D)
         (4) Learned Annex-A: unit has successfully detected Annex-A LMI
             (ITU/CCITT Q.933 Annex A)
         (5) Learned Type 1: unit has successfully detected Type 1 LMI
             (Cisco, Group of four, LMI)"
     ::= { tfrapStatus 12 }


-- =========================
-- ==  PERFORMANCE group  ==
-- =========================

tfrapPerformance  OBJECT IDENTIFIER ::= { tfrap 5 }

tfrapPerfPhysicalIntf OBJECT IDENTIFIER ::= { tfrapPerformance 1 }

--
--      T1 Current Performance Table
--       The T1 current performance table contains various statistics 
--       being collected for the current 15 minute interval.

tfrapPerfT1CurrentTable OBJECT-TYPE
     SYNTAX  SEQUENCE OF TfrapT1CurrentEntry
     ACCESS  not-accessible
     STATUS  mandatory
     DESCRIPTION
        "The T1 physical layer performance numbers for the current  
        15 minute interval. These are defined and accumulated per 
        ANSI specification T1.403 and AT&T publication 54016. Depending
        upon the configured T1 Framing mode, these results may be 
        retrieved via ESF facility data link by service personnel."
     ::= { tfrapPerfPhysicalIntf 1 }

tfrapT1CurrentEntry OBJECT-TYPE
     SYNTAX  TfrapT1CurrentEntry
     ACCESS  not-accessible
     STATUS  mandatory
     DESCRIPTION
        "An entry in the T1 Current Perf table. This table is
         structured for devices to support multiple T1 interfaces."
     INDEX   { tfrapT1CurrentIndex }
     ::= { tfrapPerfT1CurrentTable 1 }

TfrapT1CurrentEntry ::=
     SEQUENCE {
        tfrapT1CurrentIndex       INTEGER,
        tfrapT1CurrentCrc6Events  Gauge,
        tfrapT1CurrentOofEvents   Gauge,
        tfrapT1CurrentESs         Gauge,
        tfrapT1CurrentSESs        Gauge,
        tfrapT1CurrentSEFSs       Gauge,
        tfrapT1CurrentUASs        Gauge,
        tfrapT1CurrentCSSs        Gauge,
        tfrapT1CurrentBESs        Gauge,
        tfrapT1CurrentLCVs        Gauge
     }

tfrapT1CurrentIndex OBJECT-TYPE
     SYNTAX  INTEGER (1..4)
     ACCESS  read-only
     STATUS  mandatory
     DESCRIPTION
        "The index value which uniquely identifies the
         T1 interface to which this entry is applicable.
         There's only one T1 on this unit so the index
         will always be 1."
     ::= { tfrapT1CurrentEntry 1 }

tfrapT1CurrentCrc6Events OBJECT-TYPE
     SYNTAX  Gauge
     ACCESS  read-only
     STATUS  mandatory
     DESCRIPTION
        "Count of CRC errors detected on an ESF framed circuit.
        In ESF framing a CRC is generated at the source, based upon 
        the composite data. A CRC error indicates the presence of
        at least one bit error in an ESF superframe. This field is 
        a free-running accumulation of CRC errors and IS NOT reset 
        when the current 15 minute interval expires. It can be reset 
        with the performance command tfrapT1PerfClearEvents. 
        Not applicable if D4/SF framing is selcted."
     ::= { tfrapT1CurrentEntry 2 }

tfrapT1CurrentOofEvents OBJECT-TYPE
     SYNTAX  Gauge
     ACCESS  read-only
     STATUS  mandatory
     DESCRIPTION
        "Count of Out-of-Frame events on a T1 circuit. An out-of-
         frame event occurs when the frame synchronization criteria
         is lost and a resynchronization must occur. Data is interrupted
         during frame resynchronization. This field is a free-running 
         accumulation of OOF transitions and IS NOT reset when the 
         current 15 minute interval expires. It can be reset with the 
         performance command tfrapT1PerfClearEvents." 
     ::= { tfrapT1CurrentEntry 3 }

tfrapT1CurrentESs OBJECT-TYPE
     SYNTAX  Gauge
     ACCESS  read-only
     STATUS  mandatory
     DESCRIPTION
        "The number of Errored Seconds, encountered  by
        a T1 interface in the current 15 minute inter-
        val. An errored second is a one-second interval with
        CRC errors or a loss of frame sync occurred."
     ::= { tfrapT1CurrentEntry 4 }

tfrapT1CurrentSESs OBJECT-TYPE
     SYNTAX  Gauge
     ACCESS  read-only
     STATUS  mandatory
     DESCRIPTION
        "The number of Severely Errored Seconds encountered by
         a t1 interface in the current 15 minute interval. A
         severely errored second is a one second interval with
         more than 320 CRC errors or one or more frame sync losses."
     ::= { tfrapT1CurrentEntry 5 }

tfrapT1CurrentSEFSs OBJECT-TYPE
     SYNTAX  Gauge
     ACCESS  read-only
     STATUS  mandatory
     DESCRIPTION
        "The number of Severely Errored Framing Seconds
        encountered by a t1 interface in the current
        15 minute interval. A SEFS is a one second interval
        with one or more frame sync losses."
     ::= { tfrapT1CurrentEntry 6 }

tfrapT1CurrentUASs OBJECT-TYPE
     SYNTAX  Gauge
     ACCESS  read-only
     STATUS  mandatory
     DESCRIPTION
        "The number of Unavailable Seconds  encountered
        by a t1 interface in the current 15 minute in-
        terval. A UAS is a one second interval during which 
        the received signal is classified as 'unavailable due
        to excessive errors'. A signal is unavailable after
        receiving ten consective severely errored seconds and
        stays unavailable until ten seconds without a severely
        errored second occur."
     ::= { tfrapT1CurrentEntry 7 }

tfrapT1CurrentCSSs OBJECT-TYPE
     SYNTAX  Gauge
     ACCESS  read-only
     STATUS  mandatory
     DESCRIPTION
        "The number of Controlled Slip Seconds encoun-
        tered by a t1 interface in the current 15
        minute interval. A controlled slip is the 
        replication or deletion of a T1 frame at the receiver.
        These events often indicate a T1 network timing 
        problem."
     ::= { tfrapT1CurrentEntry 8 }

tfrapT1CurrentBESs OBJECT-TYPE
     SYNTAX Gauge
     ACCESS read-only
     STATUS mandatory
     DESCRIPTION
        "The number of Bursty  Errored  Seconds  (BESs)
        encountered  by  a DS1 interface in the current
        15 minute interval. A BES is a one second interval
        with more than one and less than 320 CRC errors."
     ::= {tfrapT1CurrentEntry 9 }

tfrapT1CurrentLCVs OBJECT-TYPE
     SYNTAX Gauge
     ACCESS read-only
     STATUS mandatory
     DESCRIPTION
        "The number of Line Code Violations (LCVs)  en-
        countered  by a DS1 interface in the current 15
        minute interval. LCVs are non-B8ZS related
        violations of the alternate mark inversion protocol.
        An excessive count usually indicates a B8ZS/AMI
        configuration mismatch in the T1 network."
     ::= {tfrapT1CurrentEntry 10 }


--      T1 Performance Intervals
--      The T1 Interval Table contains various statistics
--      collected by each T1 Interface over the previous 24 hours of
--      operation.  The past 24 hours are broken into 96 completed
--      15 minute intervals.

tfrapPerfT1IntervalTable OBJECT-TYPE
     SYNTAX  SEQUENCE OF TfrapT1IntervalEntry
     ACCESS  not-accessible
     STATUS  mandatory
     DESCRIPTION
        "The DS1 Interval table. A history of physical layer performance 
         results are maintained and represented as 96 15-minute intervals.
         These are defined and accumulated per  ANSI specification T1.403 
         and AT&T publication 54016. Depending upon the configured T1 
         Framing mode, these results may be retrieved via ESF facility data 
         link by service personnel"
     ::= { tfrapPerfPhysicalIntf 2 }

tfrapT1IntervalEntry OBJECT-TYPE
     SYNTAX  TfrapT1IntervalEntry
     ACCESS  not-accessible
     STATUS  mandatory
     DESCRIPTION
        "An entry in the DS1 Interval table which includes physical
         layer statistics for each of the prior 96 15-minute intervals."
     INDEX   { tfrapT1IntervalIndex, tfrapT1IntervalNumber }
     ::= { tfrapPerfT1IntervalTable 1 }

TfrapT1IntervalEntry ::=
     SEQUENCE {
         tfrapT1IntervalIndex  INTEGER,
         tfrapT1IntervalNumber INTEGER,
         tfrapT1IntervalESs    Gauge,
         tfrapT1IntervalSESs   Gauge,
         tfrapT1IntervalSEFSs  Gauge,
         tfrapT1IntervalUASs   Gauge,
         tfrapT1IntervalCSSs   Gauge,
         tfrapT1IntervalBESs   Gauge,
         tfrapT1IntervalLCVs   Gauge
     }
      
tfrapT1IntervalIndex OBJECT-TYPE
     SYNTAX  INTEGER (1..4)
     ACCESS  read-only
     STATUS  mandatory
     DESCRIPTION
        "The index value which uniquely identifies the
         t1 interface to which this entry is applicable.
         There is only one T1 on this unit so this index 
         will be 1."
     ::= { tfrapT1IntervalEntry 1 }


tfrapT1IntervalNumber OBJECT-TYPE
     SYNTAX  INTEGER (1..96)
     ACCESS  read-only
     STATUS  mandatory
     DESCRIPTION
        "A number between 1 and 96, where 96 is the most
         recently completed 15 minute interval and 1 
         occurred 24 hours ago (assuming that all 96 
         intervals are valid)."
     ::= { tfrapT1IntervalEntry 2 }

tfrapT1IntervalESs OBJECT-TYPE
     SYNTAX  Gauge
     ACCESS  read-only
     STATUS  mandatory
     DESCRIPTION
        "The number of Errored Seconds encountered by a
        t1 interface in one of the previous 96, indi-
        vidual 15 minute, intervals. An errored second is 
        a one-second interval with CRC errors or a loss 
        of frame sync occurred."
     ::= { tfrapT1IntervalEntry 3 }


tfrapT1IntervalSESs OBJECT-TYPE
     SYNTAX  Gauge
     ACCESS  read-only
     STATUS  mandatory
     DESCRIPTION
        "The number of Severely Errored Seconds encoun-
        tered by a t1 interface in one of the previous
        96, individual 15 minute, intervals. A severely 
        errored second is a one second interval with more 
        than 320 CRC errors or one or more frame sync losses."
     ::= { tfrapT1IntervalEntry 4 }


tfrapT1IntervalSEFSs OBJECT-TYPE
     SYNTAX  Gauge
     ACCESS  read-only
     STATUS  mandatory
     DESCRIPTION
        "The number of Severely Errored Framing Seconds
        encountered  by  a  t1 interface in one of the
        previous 96, individual 15 minute, intervals.
        A SEFS is a one second interval with one or more 
        frame sync losses."
     ::= { tfrapT1IntervalEntry 5 }


tfrapT1IntervalUASs OBJECT-TYPE
     SYNTAX  Gauge
     ACCESS  read-only
     STATUS  mandatory
     DESCRIPTION
        "The number of Unavailable Seconds  encountered
        by  a  t1 interface in one of the previous 96,
        individual 15 minute, intervals. A UAS is a one second 
        interval during which the received signal is classified 
        as 'unavailable due to excessive errors'. A signal is 
        unavailable after receiving ten consective severely 
        errored seconds and stays unavailable until ten seconds 
        without a severely errored second occur."
     ::= { tfrapT1IntervalEntry 6 }

tfrapT1IntervalCSSs OBJECT-TYPE
     SYNTAX  Gauge
     ACCESS  read-only
     STATUS  mandatory
     DESCRIPTION
        "The number of Controlled Slip Seconds  encoun-
        tered by a t1 interface in one of the previous
        96, individual 15 minute, intervals. A controlled 
        slip is the replication or deletion of a T1 frame 
        at the receiver. These events often indicate a T1 
        network timing problem."
     ::= { tfrapT1IntervalEntry 7 }

tfrapT1IntervalBESs OBJECT-TYPE
     SYNTAX Gauge
     ACCESS read-only
     STATUS mandatory
     DESCRIPTION
        "The number of Bursty  Errored  Seconds  (BESs)
        encountered  by  a  t1 interface in one of the
        previous 96, individual 15 minute, intervals.
        A BES is a one second interval with more than one 
        and less than 320 CRC errors."
     ::= {tfrapT1IntervalEntry 8 }

tfrapT1IntervalLCVs OBJECT-TYPE
     SYNTAX Gauge
     ACCESS read-only
     STATUS mandatory
     DESCRIPTION
        "The number of Line Code Violations (LCVs)  en-
        countered  by a DS1 interface in the current 15
        minute interval. LCVs are non-B8ZS related
        violations of the alternate mark inversion protocol.
        An excessive count usually indicates a B8ZS/AMI
        configuration mismatch in the T1 network."
     ::= {tfrapT1IntervalEntry 9 }


--       T1 Performance 24 Hour
--       The T1 Totals Table contains the cumulative sum of the
--       various statistics for the 24 hour period preceding the
--       current interval.

tfrapPerfT1TotalTable OBJECT-TYPE
     SYNTAX  SEQUENCE OF TfrapT1TotalEntry
     ACCESS  not-accessible
     STATUS  mandatory
     DESCRIPTION
        "The T1 Total table cumulative physical layer performance 
         results from the past 24 hours. These are defined and 
         accumulated per ANSI specification T1.403 and AT&T publication
         54016. Depending upon the configured T1 Framing mode, these 
         results may be retrieved via ESF facility data link by service 
         personnel."
     ::= { tfrapPerfPhysicalIntf 3 }

tfrapT1TotalEntry OBJECT-TYPE
     SYNTAX  TfrapT1TotalEntry
     ACCESS  not-accessible
     STATUS  mandatory
     DESCRIPTION
        "An entry in the T1 Physical Layer Measurement Totals table."
     INDEX   { tfrapT1TotalIndex }
     ::= { tfrapPerfT1TotalTable 1 }

TfrapT1TotalEntry ::=
     SEQUENCE {
        tfrapT1TotalIndex INTEGER, 
        tfrapT1TotalESs   Gauge,
        tfrapT1TotalSESs  Gauge,
        tfrapT1TotalSEFSs Gauge,
        tfrapT1TotalUASs  Gauge,
        tfrapT1TotalCSSs  Gauge,
        tfrapT1TotalBESs  Gauge,
        tfrapT1TotalLCVs  Gauge
     }

tfrapT1TotalIndex OBJECT-TYPE
     SYNTAX  INTEGER (1..4)
     ACCESS  read-only
     STATUS  mandatory
     DESCRIPTION
        "The index value which uniquely identifies  the
        t1  interface  to which this entry is applica-
        ble. There is only one T1 port on this device 
        so this index must be 1."
     ::= { tfrapT1TotalEntry 1 }

tfrapT1TotalESs OBJECT-TYPE
     SYNTAX  Gauge
     ACCESS  read-only
     STATUS  mandatory
     DESCRIPTION
        "The number of Errored Seconds encountered by a
        t1 interface in the previous 24 hour interval.
        An errored second is a one-second interval with 
        CRC errors or a loss of frame sync occurred."
     ::= { tfrapT1TotalEntry 2 }

tfrapT1TotalSESs OBJECT-TYPE
     SYNTAX  Gauge
     ACCESS  read-only
     STATUS  mandatory
     DESCRIPTION
        "The number of Severely Errored Seconds encoun-
        tered  by  a  t1  interface in the previous 24
        hour interval. A severely errored second is a one 
        second interval with more than 320 CRC errors or 
        one or more frame sync losses."
     ::= { tfrapT1TotalEntry 3 }

tfrapT1TotalSEFSs OBJECT-TYPE
     SYNTAX  Gauge
     ACCESS  read-only
     STATUS  mandatory
     DESCRIPTION
        "The number of Severely Errored Framing Seconds
        24 hour interval. A SEFS is a one second interval 
        with one or more frame sync losses."
     ::= { tfrapT1TotalEntry 4 }

tfrapT1TotalUASs OBJECT-TYPE
     SYNTAX  Gauge
     ACCESS  read-only
     STATUS  mandatory
     DESCRIPTION
        "The number of Unavailable Seconds  encountered
        by  a t1 interface in the previous 24 hour in-
        terval. A UAS is a one second interval during which 
        the received signal is classified as 'unavailable 
        due to excessive errors'. A signal is unavailable 
        after receiving ten consective severely errored 
        seconds and stays unavailable until ten seconds 
        without a severely errored second occur."
     ::= { tfrapT1TotalEntry 5 }

tfrapT1TotalCSSs OBJECT-TYPE
     SYNTAX  Gauge
     ACCESS  read-only
     STATUS  mandatory
     DESCRIPTION
        "The number of Controlled Slip Seconds  encoun-
        tered by a t1 interface in the previous 24
        hour interval. A controlled slip is the replication 
        or deletion of a T1 frame at the receiver. These 
        events often indicate a T1 network timing problem."
     ::= { tfrapT1TotalEntry 6 }

tfrapT1TotalBESs OBJECT-TYPE
     SYNTAX Gauge
     ACCESS read-only
     STATUS mandatory
     DESCRIPTION
        "The number of Bursty  Errored  Seconds  (BESs)
        encountered by a t1 interface in the previous
        24 hour interval. A BES is a one second interval 
        with more than one and less than 320 CRC errors."
     ::= { tfrapT1TotalEntry 7 }

tfrapT1TotalLCVs OBJECT-TYPE
     SYNTAX Gauge
     ACCESS read-only
     STATUS mandatory
     DESCRIPTION
        "The number of Line Code Violations (LCVs)  en-
        countered by a t1 interface in the current 15
        minute interval. LCVs are non-B8ZS related
        violations of the alternate mark inversion protocol.
        An excessive count usually indicates a B8ZS/AMI
        configuration mismatch in the T1 network."
     ::= {tfrapT1TotalEntry 8 }


--      T1 Performance Commands
--      A set of commands that affect the (user) bank of T1 performance 
--      registers         


tfrapT1PerfCmdTypeTable OBJECT IDENTIFIER ::= { tfrapPerfPhysicalIntf 4 }
    
tfrapT1PerfFreezeState OBJECT-TYPE
     SYNTAX      INTEGER
      {
         freeze-reg (1),
         unfreeze-reg (2)
      }
     ACCESS  read-write
     STATUS  mandatory
     DESCRIPTION
        "This command halts the node's performance monitoring
        and freezes the current, interval, and total performance
        register values."
        ::= { tfrapT1PerfCmdTypeTable 1 }

tfrapT1PerfClearEvents OBJECT-TYPE
     SYNTAX      INTEGER
      {
         clear-events (1)
      }
     ACCESS  write-only
     STATUS  mandatory
     DESCRIPTION
        "This command resets all of the (user's) error event 
        registers. This includes the CRC6 and Out-of-Frame
        counts. It does not affect the interval or 24 hour
        performance totals."
     ::= { tfrapT1PerfCmdTypeTable 2 }

tfrapT1PerfClearAll OBJECT-TYPE
     SYNTAX      INTEGER
     {
        clear-all (1)
     }
     ACCESS  write-only
     STATUS  mandatory
     DESCRIPTION
        "This command resets all of the (user's) performance 
        registers."
     ::= { tfrapT1PerfCmdTypeTable 3 }



--
--    IP protocol stack statistics - a reflection of some MIB-2 variables
--

tfrapPerfMgmtIp   OBJECT IDENTIFIER ::= { tfrapPerformance 2 }

   tfrapPerfMgmtIpIFStatsTable OBJECT IDENTIFIER ::= { tfrapPerfMgmtIp 1 }

          tfrapPerfMgmtIpIFInOctets OBJECT-TYPE
              SYNTAX  Counter
              ACCESS  read-only
              STATUS  mandatory
              DESCRIPTION
                 "The count of all octets associated with received frames 
                  that are specifically addressed as management packets 
                  for this unit. Same as ifInOctets in mib-2."
              ::= { tfrapPerfMgmtIpIFStatsTable 1 }

          tfrapPerfMgmtIpIFInErrors OBJECT-TYPE
              SYNTAX  Counter
              ACCESS  read-only
              STATUS  mandatory
              DESCRIPTION
                 "The count of packets associated with received frames 
                  that are specifically addressed as management packets 
                  for this unit which could not be handled because of 
                  errors. Same as ifInErrors in mib-2."
              ::= { tfrapPerfMgmtIpIFStatsTable 2 }

          tfrapPerfMgmtIpIFOutOctets OBJECT-TYPE
              SYNTAX  Counter
              ACCESS  read-only
              STATUS  mandatory
              DESCRIPTION
                 "The count of all octets associated with generated frames 
                  that are specifically addressed as management packets 
                  from this unit. Same as ifOutOctets in mib-2.                     Same as ifOutOctets in mib-2."
              ::= { tfrapPerfMgmtIpIFStatsTable 3 }

          tfrapPerfMgmtIpIFOperStatus OBJECT-TYPE
              SYNTAX  INTEGER 
              {
                  up(1),
                  down(2),
                  testing(3)
              }
              ACCESS  read-only
              STATUS  mandatory
              DESCRIPTION
                 "The current operational state of the management interface.
                  Same as ifOperStatus in mib-2.
                  (1) Interface Up
                  (2) Interface Down
                  (3) Interface in Test"
              ::= { tfrapPerfMgmtIpIFStatsTable 4 }

   tfrapPerfMgmtIpIPStatsTable OBJECT IDENTIFIER ::= { tfrapPerfMgmtIp 2 }

          tfrapPerfMgmtIpIPInRcv OBJECT-TYPE
              SYNTAX  Counter
              ACCESS  read-only
              STATUS  mandatory
              DESCRIPTION
                 "The count of all ip datagrams received which
                  are specifically addressed as management frames 
                  for this unit. Same as ipInReceives in mib-2."
              ::= { tfrapPerfMgmtIpIPStatsTable 1 }

          tfrapPerfMgmtIpIPInHdrErr OBJECT-TYPE
              SYNTAX  Counter
              ACCESS  read-only
              STATUS  mandatory
              DESCRIPTION
                 "The count of ip datagrams received which
                  are specifically addressed as management frames 
                  for this unit that were discarded because of 
                  errors in their IP headers. Same as ipInHdrErrors 
                  in mib-2."
              ::= { tfrapPerfMgmtIpIPStatsTable 2 }

          tfrapPerfMgmtIpIPInAddrErr OBJECT-TYPE
              SYNTAX  Counter
              ACCESS  read-only
              STATUS  mandatory
              DESCRIPTION
                 "The count of ip datagrams received which
                  are specifically addressed as management frames 
                  for this unit that were discarded because unexpected 
                  or invalid IP addresses in their IP headers.
                  Same as ipInAddrErrors in mib-2."
              ::= { tfrapPerfMgmtIpIPStatsTable 3 }

          tfrapPerfMgmtIpIPInProtUnk OBJECT-TYPE
              SYNTAX  Counter
              ACCESS  read-only
              STATUS  mandatory
              DESCRIPTION
                 "The count of ip datagrams received which
                  are specifically addressed as management frames 
                  for this unit that were discarded because of 
                  unsupported protocols. Same as ipInUnknownProtos 
                  in mib-2."
              ::= { tfrapPerfMgmtIpIPStatsTable 4 }

          tfrapPerfMgmtIpIPInDscrd OBJECT-TYPE
              SYNTAX  Counter
              ACCESS  read-only
              STATUS  mandatory
              DESCRIPTION
                 "The count of datagrams received which
                  are specifically addressed as management frames 
                  for this unit that were discarded for reasons 
                  other than a problem with the datagram. Same as 
                  ipInDiscards in mib-2."
              ::= { tfrapPerfMgmtIpIPStatsTable 5 }

          tfrapPerfMgmtIpIPInDlvrs OBJECT-TYPE
              SYNTAX  Counter
              ACCESS  read-only
              STATUS  mandatory
              DESCRIPTION
                 "The count ofip datagrams received which
                  are specifically addressed as management frames 
                  for this unit that were delivered to IP client 
                  protocols. Same as ipInDelivers in mib-2."
              ::= { tfrapPerfMgmtIpIPStatsTable 6 }

          tfrapPerfMgmtIpIPOutRqst OBJECT-TYPE
              SYNTAX  Counter
              ACCESS  read-only
              STATUS  mandatory
              DESCRIPTION
                 "The count of all outgoing datagrams generated by this 
                  unit which are specifically addressed as management frames. 
                  Same as ipOutRequests in mib-2."
              ::= { tfrapPerfMgmtIpIPStatsTable 7 }

          tfrapPerfMgmtIpIPOutDscrd OBJECT-TYPE
              SYNTAX  Counter
              ACCESS  read-only
              STATUS  mandatory
              DESCRIPTION
                 "The count of outgoing datagrams generated by this 
                  unit which are specifically addressed as management 
                  frames that were discarded for reasons other than a 
                  problem with the datagram. Same as ipOutDiscards in mib-2."
              ::= { tfrapPerfMgmtIpIPStatsTable 8 }

          tfrapPerfMgmtIpIPOutNoRt OBJECT-TYPE
              SYNTAX  Counter
              ACCESS  read-only
              STATUS  mandatory
              DESCRIPTION
                "The count of outgoing datagrams generated by this 
                 unit which are specifically addressed as management 
                 frames that were discarded because no route could be 
                 found for transmission. Same as ipOutNoRoutes in mib-2."
              ::= { tfrapPerfMgmtIpIPStatsTable 9 }


   tfrapPerfMgmtIpICMPStatsTable OBJECT IDENTIFIER ::= { tfrapPerfMgmtIp 3 }

          tfrapPerfMgmtIpICMPInMsgs OBJECT-TYPE
              SYNTAX  Counter
              ACCESS  read-only
              STATUS  mandatory
              DESCRIPTION
                 "The count of all ICMP messages received which are
                  addressed to this unit. Same as icmpInMsgs in mib-2."
              ::= { tfrapPerfMgmtIpICMPStatsTable 1 }

          tfrapPerfMgmtIpICMPInErrors OBJECT-TYPE
              SYNTAX  Counter
              ACCESS  read-only
              STATUS  mandatory
              DESCRIPTION
                 "The count of ICMP messages received which are
                  addressed to this unit but contain errors. Same 
                  as icmpInErrors in mib-2."
              ::= { tfrapPerfMgmtIpICMPStatsTable 2 }

          tfrapPerfMgmtIpICMPInDestUnreachs OBJECT-TYPE
              SYNTAX  Counter
              ACCESS  read-only
              STATUS  mandatory
              DESCRIPTION
                 "The count of ICMP Destination Unreachable messages 
                  received which are addressed to this unit. Same as 
                  icmpInDestUnreachs in mib-2."
              ::= { tfrapPerfMgmtIpICMPStatsTable 3 }

          tfrapPerfMgmtIpICMPInTimeExcds OBJECT-TYPE
              SYNTAX  Counter
              ACCESS  read-only
              STATUS  mandatory
              DESCRIPTION
                 "The count of ICMP Time Exceeded messages received which 
                  are addressed to this unit. Same as icmpInTimeExcds in 
                  mib-2."
              ::= { tfrapPerfMgmtIpICMPStatsTable 4 }

          tfrapPerfMgmtIpICMPInParmProbs OBJECT-TYPE
              SYNTAX  Counter
              ACCESS  read-only
              STATUS  mandatory
              DESCRIPTION
                 "The count of ICMP Parameter Problem messages received 
                  which are addressed to this unit. Same as icmpInParmProbs 
                  in mib-2."
              ::= { tfrapPerfMgmtIpICMPStatsTable 5 }

          tfrapPerfMgmtIpICMPInRedirects OBJECT-TYPE
              SYNTAX  Counter
              ACCESS  read-only
              STATUS  mandatory
              DESCRIPTION
                 "The count of ICMP Redirect messages received which are
                  addressed to this unit. Same as icmpInRedirects in mib-2."
              ::= { tfrapPerfMgmtIpICMPStatsTable 6 }

          tfrapPerfMgmtIpICMPInEchos OBJECT-TYPE
              SYNTAX  Counter
              ACCESS  read-only
              STATUS  mandatory
              DESCRIPTION
                 "The count of ICMP Echo messages received which are
                  addressed to this unit. Same as icmpInEchos in mib-2."
              ::= { tfrapPerfMgmtIpICMPStatsTable 7 }

          tfrapPerfMgmtIpICMPInEchoReps OBJECT-TYPE
              SYNTAX  Counter
              ACCESS  read-only
              STATUS  mandatory
              DESCRIPTION
                 "The count of ICMP Echo Reply messages received which are
                  addressed to this unit. Same as icmpInEchoReps in mib-2."
              ::= { tfrapPerfMgmtIpICMPStatsTable 8 }

          tfrapPerfMgmtIpICMPOutMsgs OBJECT-TYPE
              SYNTAX  Counter
              ACCESS  read-only
              STATUS  mandatory
              DESCRIPTION
                 "The count of all outgoing ICMP messages originating 
                  from this node. Same as icmpOutMsgs in mib-2."
              ::= { tfrapPerfMgmtIpICMPStatsTable 9 }

          tfrapPerfMgmtIpICMPOutErrors OBJECT-TYPE
              SYNTAX  Counter
              ACCESS  read-only
              STATUS  mandatory
              DESCRIPTION
                 "The count of outgoing ICMP messages generated by this
                  unit which are not transmitted due problems found by 
                  the ICMP layer. Same as icmpOutErrors in mib-2."
              ::= { tfrapPerfMgmtIpICMPStatsTable 10 }

          tfrapPerfMgmtIpICMPOutDestUnreachs OBJECT-TYPE
              SYNTAX  Counter
              ACCESS  read-only
              STATUS  mandatory
              DESCRIPTION
                 "The count of outgoing ICMP Destination Unreachable
                  messages generated by this unit. Same as 
                  icmpOutDestUnreachs in mib-2."
              ::= { tfrapPerfMgmtIpICMPStatsTable 11 }

          tfrapPerfMgmtIpICMPOutParmProbs OBJECT-TYPE
              SYNTAX  Counter
              ACCESS  read-only
              STATUS  mandatory
              DESCRIPTION
                 "The count of outgoing ICMP Parameter Problem messages
                  generated by this unit. Same as icmpOutParmProbs in mib-2."
              ::= { tfrapPerfMgmtIpICMPStatsTable 12 }

          tfrapPerfMgmtIpICMPOutRedirects OBJECT-TYPE
              SYNTAX  Counter
              ACCESS  read-only
              STATUS  mandatory
              DESCRIPTION
                 "The count of outgoing ICMP Redirect messages generated
                  by this unit. Same as icmpOutRedirects in mib-2."
              ::= { tfrapPerfMgmtIpICMPStatsTable 13 }

          tfrapPerfMgmtIpICMPOutEchos OBJECT-TYPE
              SYNTAX  Counter
              ACCESS  read-only
              STATUS  mandatory
              DESCRIPTION
                 "The count of outgoing ICMP Echo messages generated by this
                  unit. Same as icmpOutEchos in mib-2."
              ::= { tfrapPerfMgmtIpICMPStatsTable 14 }

          tfrapPerfMgmtIpICMPOutEchoReps OBJECT-TYPE
              SYNTAX  Counter
              ACCESS  read-only
              STATUS  mandatory
              DESCRIPTION
                 "The count of outgoing ICMP Echo Reply messages generated 
                  by this unit. Same as icmpOutEchoReps in mib-2."
              ::= { tfrapPerfMgmtIpICMPStatsTable 15 }

   tfrapPerfMgmtIpUDPStatsTable OBJECT IDENTIFIER ::= { tfrapPerfMgmtIp 4 }

          tfrapPerfMgmtIpUDPInDatagrams OBJECT-TYPE
              SYNTAX  Counter
              ACCESS  read-only
              STATUS  mandatory
              DESCRIPTION
                 "The count of all UDP datagrams received that are 
                  addressed as management frames for this unit. Same 
                  as udpInDatagrams in mib-2."
              ::= { tfrapPerfMgmtIpUDPStatsTable 1 }

          tfrapPerfMgmtIpUDPOutDatagrams OBJECT-TYPE
              SYNTAX  Counter
              ACCESS  read-only
              STATUS  mandatory
              DESCRIPTION
                      "The count of all UDP datagrams generated by
                       this unit. Same as udpOutDatagrams in mib-2."
              ::= { tfrapPerfMgmtIpUDPStatsTable 2 }

          tfrapPerfMgmtIpUDPNoPorts OBJECT-TYPE
              SYNTAX  Counter
              ACCESS  read-only
              STATUS  mandatory
              DESCRIPTION
                 "The count of all UDP datagrams received that are 
                  addressed as management frames for this unit with 
                  no application at the destination port. Same as 
                  udpNoPorts in mib-2."
              ::= { tfrapPerfMgmtIpUDPStatsTable 3 }


   tfrapPerfMgmtIpTCPStatsTable OBJECT IDENTIFIER ::= { tfrapPerfMgmtIp 5 }

          tfrapPerfMgmtIpTCPActiveOpens OBJECT-TYPE
              SYNTAX  Counter
              ACCESS  read-only
              STATUS  mandatory
              DESCRIPTION
                 "The count of the times TCP connections specific to this 
                  unit have made a direct state transition from CLOSED to 
                  SYN-SENT. Same as tcpActiveOpens in mib-2."
              ::= { tfrapPerfMgmtIpTCPStatsTable 1 }

          tfrapPerfMgmtIpTCPPassiveOpens OBJECT-TYPE
              SYNTAX  Counter
              ACCESS  read-only
              STATUS  mandatory
              DESCRIPTION
                 "The count of the times TCP connections specific to 
                  this unit have made a direct state transition from 
                  CLOSED to SYN-RCVD. Same as tcpPassiveOpens in mib-2."
              ::= { tfrapPerfMgmtIpTCPStatsTable 2 }

          tfrapPerfMgmtIpTCPAttemptFails OBJECT-TYPE
              SYNTAX  Counter
              ACCESS  read-only
              STATUS  mandatory
              DESCRIPTION
                 "The count of the times TCP connections specific to this unit
                  have made a direct state transition from SYN-SENT or SYN-RCVD
                  to CLOSED state, plus the count of the times TCP connections 
                  have made a direct state transition from SYN-RCVD to LISTEN.
                  Same as tcpAttemptFails in mib-2."
              ::= { tfrapPerfMgmtIpTCPStatsTable 3 }

          tfrapPerfMgmtIpTCPCurrEstab OBJECT-TYPE
              SYNTAX  Gauge
              ACCESS  read-only
              STATUS  mandatory
              DESCRIPTION
                 "The count of the TCP connections specific to this unit
                  in state ESTABLISHED or CLOSE-WAIT. Same as tcpCurrEstab 
                  in mib-2."
              ::= { tfrapPerfMgmtIpTCPStatsTable 4 }

          tfrapPerfMgmtIpTCPInSegs OBJECT-TYPE
              SYNTAX  Counter
              ACCESS  read-only
              STATUS  mandatory
              DESCRIPTION
                 "The count of all the segments received that are 
                  addressed as management frames for this unit.
                  Same as tcpInSegs in mib-2."
              ::= { tfrapPerfMgmtIpTCPStatsTable 5 }

          tfrapPerfMgmtIpTCPOutSegs OBJECT-TYPE
              SYNTAX  Counter
              ACCESS  read-only
              STATUS  mandatory
              DESCRIPTION
                 "The count of all the segments generated from this unit.
                  Same as tcpOutSegs in mib-2."
              ::= { tfrapPerfMgmtIpTCPStatsTable 6 }


--
--       The TFRAP Performance Thruput Table
--              This table contains Thruput statistics for the DTE port
--              and the T1 port.  This table does NOT contain any PVC 
--              DLCI thruput statistics.
--

tfrapPerfThruput   OBJECT IDENTIFIER ::= { tfrapPerformance 3 }

tfrapPerfThruputPerIntfTable  OBJECT-TYPE
     SYNTAX  SEQUENCE OF TfrapPerfThruputPerIntfEntry
     ACCESS  not-accessible
     STATUS  mandatory
     DESCRIPTION
        "The throughput per interface table. These values are accumulated
         across all DLCIs."
     ::= { tfrapPerfThruput 1 }

tfrapPerfThruputPerIntfEntry  OBJECT-TYPE
     SYNTAX  TfrapPerfThruputPerIntfEntry
     ACCESS  not-accessible
     STATUS  mandatory
     DESCRIPTION
        "An entry in the throughput per interface table."
     INDEX   { tfrapPerfThruputPerIntfIndex }
     ::= { tfrapPerfThruputPerIntfTable 1 }

TfrapPerfThruputPerIntfEntry ::=
     SEQUENCE {
        tfrapPerfThruputPerIntfIndex       INTEGER, 
        tfrapPerfThruputPerIntfRxByteCnt   Counter,
        tfrapPerfThruputPerIntfTxByteCnt   Counter,
        tfrapPerfThruputPerIntfRxFrameCnt  Counter,
        tfrapPerfThruputPerIntfTxFrameCnt  Counter,
        tfrapPerfThruputPerIntfRxCrcErrCnt Counter,
        tfrapPerfThruputPerIntfRxAbortCnt  Counter
     }

   tfrapPerfThruputPerIntfIndex    OBJECT-TYPE
          SYNTAX      INTEGER
          {
             dte (1),
             t1  (2)
          }
          ACCESS      read-only
          STATUS      mandatory
          DESCRIPTION
             "Interface for which the statistics apply.
              (1) DTE interface
              (2) T1 interface"
          ::= { tfrapPerfThruputPerIntfEntry 1 }

   tfrapPerfThruputPerIntfRxByteCnt    OBJECT-TYPE
          SYNTAX      Counter 
          ACCESS      read-only
          STATUS      mandatory
          DESCRIPTION
             "The number of framed bytes that have been received
              on this interface."
          ::= { tfrapPerfThruputPerIntfEntry 2 }

   tfrapPerfThruputPerIntfTxByteCnt    OBJECT-TYPE
             SYNTAX      Counter
             ACCESS      read-only
             STATUS      mandatory
             DESCRIPTION
                "The number of framed bytes that have been transmit
                 on this interface."
             ::= { tfrapPerfThruputPerIntfEntry 3 }

   tfrapPerfThruputPerIntfRxFrameCnt    OBJECT-TYPE
             SYNTAX      Counter 
             ACCESS      read-only
             STATUS      mandatory
             DESCRIPTION
                "The number of frames that have been received
                 on this interface."
             ::= { tfrapPerfThruputPerIntfEntry 4 }

   tfrapPerfThruputPerIntfTxFrameCnt    OBJECT-TYPE
             SYNTAX      Counter 
             ACCESS      read-only
             STATUS      mandatory
             DESCRIPTION
                "The number of frames that have been transmit
                 on this interface."
             ::= { tfrapPerfThruputPerIntfEntry 5 }

   tfrapPerfThruputPerIntfRxCrcErrCnt  OBJECT-TYPE
             SYNTAX      Counter 
             ACCESS      read-only
             STATUS      mandatory
             DESCRIPTION
                "The number of frames with CRC errors received
                 on this interface."
            ::= { tfrapPerfThruputPerIntfEntry 6 }

   tfrapPerfThruputPerIntfRxAbortCnt   OBJECT-TYPE
             SYNTAX      Counter 
             ACCESS      read-only
             STATUS      mandatory
             DESCRIPTION
                "The number of aborted frames received
                 on this interface."
            ::= { tfrapPerfThruputPerIntfEntry 7 }


--
--       The DLCI Statistics Table
--              This table contains the DLCI Statistics (layer 2).

   Index ::= INTEGER

   tfrapPerfThruputPerDlciTable OBJECT-TYPE
         SYNTAX   SEQUENCE OF TfrapPerfThruputPerDlciEntry
         ACCESS   not-accessible
         STATUS   mandatory
         DESCRIPTION
            "Layer 2 statistics on a per-DLCI basis. Transmit direction
             is from DTE to WAN and receive direction is from the WAN
             towards the DTE."
         ::= { tfrapPerfThruput 2 }

         tfrapPerfThruputPerDlciEntry OBJECT-TYPE
             SYNTAX   TfrapPerfThruputPerDlciEntry
             ACCESS   not-accessible
             STATUS   mandatory
             DESCRIPTION
                "The Statistics for a particular Data Link
                 Connection Management Interface (DLCI)."
            INDEX { tfrapPerfThruputPerDlciIndex,
                    tfrapPerfThruputPerDlciValue }
            ::= { tfrapPerfThruputPerDlciTable 1 }

         TfrapPerfThruputPerDlciEntry ::=
             SEQUENCE {
                 tfrapPerfThruputPerDlciIndex        Index,
                 tfrapPerfThruputPerDlciValue        INTEGER,
                 tfrapPerfThruputPerDlciCreateTime   INTEGER,
                 tfrapPerfThruputPerDlciChangeTime   INTEGER,
                 tfrapPerfThruputPerDlciRxByte       Counter,
                 tfrapPerfThruputPerDlciTxByte       Counter,
                 tfrapPerfThruputPerDlciRxFrame      Counter,
                 tfrapPerfThruputPerDlciTxFrame      Counter,
                 tfrapPerfThruputPerDlciRxFecn       Counter,
                 tfrapPerfThruputPerDlciRxBecn       Counter,
                 tfrapPerfThruputPerDlciRxDe         Counter,
                 tfrapPerfThruputPerDlciTxDe         Counter,
                 tfrapPerfThruputPerDlciRxThruput    INTEGER,
                 tfrapPerfThruputPerDlciTxThruput    INTEGER,
                 tfrapPerfThruputPerDlciCIR          INTEGER,
                 tfrapPerfThruputPerDlciUptime       INTEGER,
                 tfrapPerfThruputPerDlciDowntime     INTEGER,
                 tfrapPerfThruputPerDlciCirType      INTEGER,
                 tfrapPerfThruputPerDlciPvcState     INTEGER,
                 tfrapPerfThruputPerDlciOutageCount  Counter,
                 tfrapPerfThruputPerDlciAvailability INTEGER,
                 tfrapPerfThruputPerDlciMTBSO        INTEGER,
                 tfrapPerfThruputPerDlciMTTSR        INTEGER,
                 tfrapPerfThruputPerDlciEncapType    INTEGER,
                 tfrapPerfThruputPerDlciRxUtilizationStatus INTEGER,
                 tfrapPerfThruputPerDlciTxUtilizationStatus INTEGER,
                 tfrapPerfThruputPerDlciEIR          INTEGER
             }

   tfrapPerfThruputPerDlciIndex OBJECT-TYPE
             SYNTAX   Index
             ACCESS   read-only
             STATUS   mandatory
             DESCRIPTION
                "This value must be in the range 1-3.
                 Other than that, this value is ignored as
                 all three will return the same result."
            ::= { tfrapPerfThruputPerDlciEntry 1 }

   tfrapPerfThruputPerDlciValue    OBJECT-TYPE
             SYNTAX      INTEGER 
             ACCESS      read-only
             STATUS      mandatory
             DESCRIPTION
                "The DLCI value in which the Statistics are associated."
            ::= { tfrapPerfThruputPerDlciEntry 2 }

   tfrapPerfThruputPerDlciCreateTime    OBJECT-TYPE
             SYNTAX      INTEGER 
             ACCESS      read-only
             STATUS      mandatory
             DESCRIPTION
                "The amount of time elapsed since this DLCI was first
                 detected through traffic sensing or in an LMI message 
                 (in seconds)."
            ::= { tfrapPerfThruputPerDlciEntry 3 }

   tfrapPerfThruputPerDlciChangeTime    OBJECT-TYPE
           SYNTAX      INTEGER 
             ACCESS      read-only
             STATUS      mandatory
             DESCRIPTION
                "The amount of elapsed time since this DLCI last
                 changed state from active to inactive or vice versa
                 (in seconds)."
            ::= { tfrapPerfThruputPerDlciEntry 4 }

   tfrapPerfThruputPerDlciRxByte    OBJECT-TYPE
             SYNTAX      Counter 
             ACCESS      read-only
             STATUS      mandatory
             DESCRIPTION
                "The number of bytes that have been received from
                 the WAN towards the DTE on this DLCI. This count
                 will include any frames that are terminated by the 
                 unit and do not pass through to the opposite interface 
                 (management and networking data)."
            ::= { tfrapPerfThruputPerDlciEntry 5 }

   tfrapPerfThruputPerDlciTxByte    OBJECT-TYPE
             SYNTAX      Counter
             ACCESS      read-only
             STATUS      mandatory
             DESCRIPTION
                "The number of bytes that have been transmit from the
                 DTE towards the WAN on this DLCI. This count
                 will include any frames that are terminated by the 
                 unit and do not pass through to the opposite interface 
                 (management and networking data)."
       ::= { tfrapPerfThruputPerDlciEntry 6 }

   tfrapPerfThruputPerDlciRxFrame    OBJECT-TYPE
             SYNTAX      Counter
             ACCESS      read-only
             STATUS      mandatory
             DESCRIPTION
                "The number of frames that have been received from
                 the WAN towards to the DTE on this DLCI. This count
                 will include any frames that are terminated by the 
                 unit and do not pass through to the opposite interface 
                 (management and networking data)."
            ::= { tfrapPerfThruputPerDlciEntry 7 }

   tfrapPerfThruputPerDlciTxFrame    OBJECT-TYPE
             SYNTAX      Counter
             ACCESS      read-only
             STATUS      mandatory
             DESCRIPTION
                "The number of frames that have been transmit from the
                 DTE towards the WAN on this DLCI. This count
                 will include any frames that are terminated by the 
                 unit and do not pass through to the opposite interface 
                 (management and networking data)."
            ::= { tfrapPerfThruputPerDlciEntry 8 }

   tfrapPerfThruputPerDlciRxFecn    OBJECT-TYPE
             SYNTAX      Counter
             ACCESS      read-only
             STATUS      mandatory
             DESCRIPTION
                "The number frames received from the WAN towards the DTE 
                 that have had the Forward Explict Congestion Notification 
                 (FECN) bit set on this DLCI. This count will include any 
                 frames that are terminated by the unit and do not pass 
                 through to the opposite interface (management and networking 
                 data)."
            ::= { tfrapPerfThruputPerDlciEntry 9 }

   tfrapPerfThruputPerDlciRxBecn    OBJECT-TYPE
             SYNTAX      Counter
             ACCESS      read-only
             STATUS      mandatory
             DESCRIPTION
                "The number frames received from the WAN towards the DTE 
                 that have had the Backward Explict Congestion Notification 
                 (BECN) bit set on this DLCI. This count will include any 
                 frames that are terminated by the unit and do not pass 
                 through to the opposite interface (management and networking 
                 data)."
            ::= { tfrapPerfThruputPerDlciEntry 10 }

   tfrapPerfThruputPerDlciRxDe    OBJECT-TYPE
             SYNTAX      Counter
             ACCESS      read-only
             STATUS      mandatory
             DESCRIPTION
                "The number frames received from the WAN towards the DTE 
                 that have had the Discard Eligibility (DE) bit set on 
                 this DLCI. This count will include any frames that are 
                 terminated by the unit and do not pass through to the 
                 opposite interface (management and networking data)."
            ::= { tfrapPerfThruputPerDlciEntry 11 }

   tfrapPerfThruputPerDlciTxDe    OBJECT-TYPE
             SYNTAX      Counter
             ACCESS      read-only
             STATUS      mandatory
             DESCRIPTION
                "The number frames transmit towards the WAN from the DTE 
                 that have had the Discard Eligibility (DE) bit set on 
                 this DLCI. This count will include any frames that are 
                 terminated by the unit and do not pass through to the 
                 opposite interface (management and networking data)."
            ::= { tfrapPerfThruputPerDlciEntry 12 }

   tfrapPerfThruputPerDlciRxThruput    OBJECT-TYPE
             SYNTAX      INTEGER
             ACCESS      read-only
             STATUS      mandatory
             DESCRIPTION
                "The number of bits/sec received from the WAN on this 
                 DLCI. This count will include any frames that are 
                 terminated by the unit and do not pass through to the 
                 opposite interface (management and networking data)."
            ::= { tfrapPerfThruputPerDlciEntry 13 }

   tfrapPerfThruputPerDlciTxThruput    OBJECT-TYPE
             SYNTAX      INTEGER
             ACCESS      read-only
             STATUS      mandatory
             DESCRIPTION
                "The number of bits/sec transmit to the WAN on this 
                 DLCI. This count will include any frames that are 
                 terminated by the unit and do not pass through to 
                 the opposite interface (management and networking data)."
            ::= { tfrapPerfThruputPerDlciEntry 14 }

   tfrapPerfThruputPerDlciCIR    OBJECT-TYPE
             SYNTAX      INTEGER
             ACCESS      read-only
             STATUS      mandatory
             DESCRIPTION
                "The Committed Information Rate (CIR) for this DLCI.
                 This can come form one of three sources: From the LMI
                 Full Status Response, configured by the user, or 
                 the DTE line rate (default)."
            ::= { tfrapPerfThruputPerDlciEntry 15 }

   tfrapPerfThruputPerDlciCirType    OBJECT-TYPE
             SYNTAX      INTEGER 
             {
               cir-acquired-from-lmi  (1),
               cir-configured-by-user (2),
               cir-is-dte-datarate    (3)
             }
             ACCESS      read-only
             STATUS      mandatory
             DESCRIPTION
               "The source of the CIR value for this DLCI. 
                (1) CIR acquired from LMI message. Will override user
                    configured CIR. This feature is not supported by all
                    Frame Relay DCE (switches).
                (2) CIR configured by user.
                (3) CIR is DTE Line Rate. Default if CIR is not set
                    by one of the other methods."
            ::= { tfrapPerfThruputPerDlciEntry 18 }

   tfrapPerfThruputPerDlciUptime    OBJECT-TYPE
             SYNTAX      INTEGER 
             ACCESS      read-only
             STATUS      mandatory
             DESCRIPTION
                "The total amount of time that the DLCI has been up as
                 reproted by the LMI Full Status Response (in seconds)."
            ::= { tfrapPerfThruputPerDlciEntry 16 }

   tfrapPerfThruputPerDlciDowntime    OBJECT-TYPE
             SYNTAX      INTEGER 
             ACCESS      read-only
             STATUS      mandatory
             DESCRIPTION
                "The total amount of time that the DLCI has been declared
                 down (in seconds). A DLCI is Down if it's explicitly 
                 declared Inactive through LMI or if it's missing from the 
                 LMI Full Status message or if there is no Full Status 
                 message at all."
            ::= { tfrapPerfThruputPerDlciEntry 17 }

   tfrapPerfThruputPerDlciPvcState   OBJECT-TYPE
            SYNTAX       INTEGER
          {
            pvc-active        (1),
            pvc-inactive      (2),
            pvc-unprovisioned (3),
            pvc-not-in-lmi    (4),
            pvc-lmi-timeout   (5),
            pvc-undetermined  (6)
           }
          ACCESS      read-only
          STATUS      mandatory
          DESCRIPTION
             "The current state of the DLCI:
            (1) DLCI marked active in last full status LMI
            (2) DLCI in last full status LMI but not marked active
            (3) DLCI has never been seen in a full status LMI
            (4) DLCI was seen at least once in a full status LMI
                but was not in the last full status LMI
            (5) the full status LMI has timed out; all previously
                active or inactive DLCIs are changed to this state
            (6) DLCI was detected in the traffic stream and a full
                status LMI has not been received so the state cannot
                be determined yet. "
         ::= { tfrapPerfThruputPerDlciEntry 19 }
         
   tfrapPerfThruputPerDlciOutageCount   OBJECT-TYPE
            SYNTAX      Counter
          ACCESS      read-only
          STATUS      mandatory
          DESCRIPTION
             "The number of times the smperPerfThruputPerDlciPvcState
             transitions from pvc-active or pvc-undetermined to one
             of the other (inactive) states. "
            ::= { tfrapPerfThruputPerDlciEntry 20 }

   tfrapPerfThruputPerDlciAvailability    OBJECT-TYPE
            SYNTAX      INTEGER
          ACCESS      read-only
          STATUS      mandatory
          DESCRIPTION
                "The measure of the percentage time the DLCI is
             available: UpTime/CreateTime or zero if CreateTime
             = 0. (in 1/1000 per cent; i.e. availability = 1000 
             converts to 1%). "
            ::= { tfrapPerfThruputPerDlciEntry 21 }

   tfrapPerfThruputPerDlciMTBSO    OBJECT-TYPE
            SYNTAX      INTEGER
          ACCESS      read-only
          STATUS      mandatory
          DESCRIPTION
             "Mean Time Between Service Outages: UpTime/OutageCount
             or zero if OutageCount = 0 (in seconds). "
            ::= { tfrapPerfThruputPerDlciEntry 22 }

   tfrapPerfThruputPerDlciMTTSR    OBJECT-TYPE
            SYNTAX      INTEGER
          ACCESS      read-only
          STATUS      mandatory
          DESCRIPTION
             "Mean Time to ServiceRestoral: DownTime/OutageCount
             or zero if OutageCount = 0 (in seconds). "
            ::= { tfrapPerfThruputPerDlciEntry 23 }

   tfrapPerfThruputPerDlciEncapType   OBJECT-TYPE
            SYNTAX      INTEGER
          {
            encap-na      (1),
            encap-1490    (2),
            encap-cisco   (3),
            encap-annex-g (4),
            encap-other   (5)
          }
          ACCESS      read-only
          STATUS      mandatory
          DESCRIPTION
             "The encapsulation protocol seen in the last frame
             analyzed on this DLCI:
             (1) DLCI is the LMI DLCI or no frames have been
                 analyzed
              (2) The encapsulation is per rfc1490
             (3) The encapsulation is per Cisco proprietary
             (4) The encapsulation is per Annex-G (X.25 over
                 frame relay)
              (5) The encapsulation is not one of the above. "
            ::= { tfrapPerfThruputPerDlciEntry 24 }
      
   tfrapPerfThruputPerDlciRxUtilizationStatus OBJECT-TYPE
             SYNTAX      INTEGER
             {
               clear                  (1),
               over-threshold         (2),
               alarm                  (3),
               alarm-under-threshold  (4)
             }
             ACCESS      read-only
             STATUS      mandatory
             DESCRIPTION
                " The status of the per-DLCI utilization
                  alarm in the receive direction.
                  (1) there is no alarm condition; utilization
                      is under the configured CIR percentage
                      threshold; if traps are enabled and the 
                      alarm had been previously triggered, a
                      utilization alarm clear trap will be sent.
                  (2) the utilization has been over the configured 
                      CIR percentage threshold for less than the
                      configured duration.
                  (3) the utilization has been over the configured 
                      CIR percentage threshold for more than the
                      configured duration; if traps are enabled
                      a utilization exceeded trap will be sent.
                  (4) the utilization has been under the configured 
                      CIR percentage threshold for less than the
                      configured duration. "
             ::= { tfrapPerfThruputPerDlciEntry 25 }
             
   tfrapPerfThruputPerDlciTxUtilizationStatus OBJECT-TYPE
             SYNTAX      INTEGER
             {
               clear                  (1),
               over-threshold         (2),
               alarm                  (3),
               alarm-under-threshold  (4)
             }
             ACCESS      read-only
             STATUS      mandatory
             DESCRIPTION
                " The status of the per-DLCI utilization
                  alarm in the transmit direction.
                  (1) there is no alarm condition; utilization
                      is under the configured CIR percentage
                      threshold; if traps are enabled and the 
                      alarm had been previously triggered, a
                      utilization alarm clear trap will be sent.
                  (2) the utilization has been over the configured 
                      CIR percentage threshold for less than the
                      configured duration.
                  (3) the utilization has been over the configured 
                      CIR percentage threshold for more than the
                      configured duration; if traps are enabled
                      a utilization exceeded trap will be sent.
                  (4) the utilization has been under the configured 
                      CIR percentage threshold for less than the
                      configured duration. "
             ::= { tfrapPerfThruputPerDlciEntry 26 }
             
   tfrapPerfThruputPerDlciEIR    OBJECT-TYPE
             SYNTAX      INTEGER
             ACCESS      read-only
             STATUS      mandatory
             DESCRIPTION
                "The Excess Information Rate.  This is defined to
                 be the maximum rate traffic is (supposed to be)
                 allowed to burst to."
            ::= { tfrapPerfThruputPerDlciEntry 27 }
             

tfrapPerfThruputCommands OBJECT IDENTIFIER ::= { tfrapPerfThruput 3 }

   tfrapPerfThruputCmdClearDteStats    OBJECT-TYPE
          SYNTAX      INTEGER
          {
              clear-statistics (1)
          }
          ACCESS      write-only
          STATUS      mandatory
          DESCRIPTION
             "Allows the user to zero out all the interface statistics in
              the DTE portion of the ThruputPerIntf statistics table.
              (1) Clear DTE interface statistics command."
          ::= { tfrapPerfThruputCommands 1 }

   tfrapPerfThruputCmdClearT1Stats    OBJECT-TYPE
          SYNTAX      INTEGER
          {
              clear-statistics (1)
          }
          ACCESS      write-only
          STATUS      mandatory
          DESCRIPTION
             "Allows the user to zero out all the interface statistics in
              the WAN portion of the ThruputPerIntf statistics table.
              (1) Clear WAN interface statistics command."
          ::= { tfrapPerfThruputCommands 2 }

   tfrapPerfThruputCmdClearAllIntfStats    OBJECT-TYPE
          SYNTAX      INTEGER
          {
              clear-statistics (1)
          }
          ACCESS      write-only
          STATUS      mandatory
          DESCRIPTION
             "Allows the user to zero out all the statistics in
              the ThruputPerIntf statistics table."
          ::= { tfrapPerfThruputCommands 3 }

   tfrapPerfThruputCmdClearDlciStats    OBJECT-TYPE
          SYNTAX      INTEGER
          {
              clear-statistics (1)
          }
          ACCESS      write-only
          STATUS      mandatory
          DESCRIPTION
             "Allows the user to zero out all the per-DLCI statistics
              in the ThruputPerDlci statistics table and the the short 
              term statistics tables.
              (1) Clear layer 2 per-DLCI statistics command."
          ::= { tfrapPerfThruputCommands 4 }

   tfrapPerfThruputCmdClearAllStats    OBJECT-TYPE
          SYNTAX      INTEGER
          {
              clear-statistics (1)
          }
          ACCESS      write-only
          STATUS      mandatory
          DESCRIPTION
             "Allows the user to zero out all the statistics
              in the ThruputPerIntf and ThruputPerDlci statistics
              tables and in the short term statistics tables.
              (1) Clear all interface and layer 2 per-DLCI statistics."
          ::= { tfrapPerfThruputCommands 5 }

   tfrapPerfThruputCmdRemoveStsDlci    OBJECT-TYPE
          SYNTAX      INTEGER
          ACCESS      write-only
          STATUS      mandatory
          DESCRIPTION
             "Allows the user to remove a Dlci from the short term 
              statistics tables."
          ::= { tfrapPerfThruputCommands 6 }

   tfrapPerfThruputCmdReplaceDlciTable    OBJECT-TYPE
          SYNTAX      SEQUENCE OF TfrapPerfThruputCmdReplaceDlciEntry
          ACCESS      not-accessible
          STATUS      mandatory
          DESCRIPTION
             "Allows the user to replace one DLCI in the short-term
              statistics table with another one."
          ::= { tfrapPerfThruputCommands 7 }

   tfrapPerfThruputCmdReplaceDlciEntry   OBJECT-TYPE
          SYNTAX  TfrapPerfThruputCmdReplaceDlciEntry
          ACCESS  not-accessible
          STATUS  mandatory
          DESCRIPTION
                "Allows the user to replace one DLCI in the short-term
                 statistics table with another one."
          INDEX { tfrapPerfThruputCmdReplaceDlciValue }
          ::= { tfrapPerfThruputCmdReplaceDlciTable 1 }

     TfrapPerfThruputCmdReplaceDlciEntry ::=
          SEQUENCE {
            tfrapPerfThruputCmdReplaceDlciValue     INTEGER,
            tfrapPerfThruputCmdReplaceDlciNewValue  INTEGER
          }
            
          tfrapPerfThruputCmdReplaceDlciValue  OBJECT-TYPE
             SYNTAX  INTEGER
             ACCESS  read-only
             STATUS  mandatory
             DESCRIPTION
                "A Dlci that is in the short-term stats table.  Index by
                 this Dlci value to identify the statistics entry to be
                 replaced."
             ::= { tfrapPerfThruputCmdReplaceDlciEntry 1 }

          tfrapPerfThruputCmdReplaceDlciNewValue  OBJECT-TYPE
             SYNTAX  INTEGER
             ACCESS  write-only
             STATUS  mandatory
             DESCRIPTION
                "A Dlci that is to replace another in the short-term stats 
                 table.  Index by this Dlci value to identify the statistics 
                 entry to do the replacing."
             ::= { tfrapPerfThruputCmdReplaceDlciEntry 2 }

   tfrapPerfThruputCmdAvailabilityStsDlciReset    OBJECT-TYPE
          SYNTAX      INTEGER
          ACCESS      write-only
          STATUS      mandatory
          DESCRIPTION
             "Allows the user to reset the availability
              statistics of an individual Dlci within
              the short-term stats table."
          ::= { tfrapPerfThruputCommands 8 }

   tfrapPerfThruputCmdAvailabilityStsDlciResetAll    OBJECT-TYPE
          SYNTAX      INTEGER
          ACCESS      write-only
          STATUS      mandatory
          DESCRIPTION
             "Allows the user to reset the availability
              statistics of all Dlci's within the short-term
              stats table."
          ::= { tfrapPerfThruputCommands 9 }

   tfrapPerfThruputCmdCountsStsDlciReset    OBJECT-TYPE
          SYNTAX      INTEGER
          ACCESS      write-only
          STATUS      mandatory
          DESCRIPTION
             "Allows the user to reset the count 
              statistics of an individual Dlci within
              the short-term stats table."
          ::= { tfrapPerfThruputCommands 10 }

   tfrapPerfThruputCmdCountsStsDlciResetAll    OBJECT-TYPE
          SYNTAX      INTEGER
          ACCESS      write-only
          STATUS      mandatory
          DESCRIPTION
             "Allows the user to reset the count
              statistics of all Dlci's within the short-term
              stats table."
          ::= { tfrapPerfThruputCommands 11 }

   tfrapPerfThruputCmdAllStsDlciReset    OBJECT-TYPE
          SYNTAX      INTEGER
          ACCESS      write-only
          STATUS      mandatory
          DESCRIPTION
             "Allows the user to reset both the count 
              and availability statistics of an individual Dlci within
              the short-term stats table."
          ::= { tfrapPerfThruputCommands 12 }

   tfrapPerfThruputCmdAllStsDlciResetAll    OBJECT-TYPE
          SYNTAX      INTEGER
          ACCESS      write-only
          STATUS      mandatory
          DESCRIPTION
             "Allows the user to reset both the count and the
              availability statistics of all Dlci's within the short-term
              stats table."
          ::= { tfrapPerfThruputCommands 13 }



tfrapPerfNetworkShortTerm OBJECT IDENTIFIER ::= { tfrapPerformance 4 }

   --  Network Layer Short Term Statistics for each DLCI.

   tfrapPerfNetwProtoPerDlciTable OBJECT-TYPE
         SYNTAX   SEQUENCE OF TfrapPerfNetwProtoPerDlciEntry
         ACCESS   not-accessible
         STATUS   mandatory
         DESCRIPTION
            "The Short Term Statistics on the Network Layer
             protocol for each DLCI. These are protocol-based
             per-DLCI statistics. The Short Term model maintains
             three intervals: current, previous, and cumulative
             totals. Interval duration is defined by the Short Term
             Timer (CfgFrPerfTimersSTInterval)."
         ::= { tfrapPerfNetworkShortTerm 1 }

         tfrapPerfNetwProtoPerDlciEntry OBJECT-TYPE
             SYNTAX   TfrapPerfNetwProtoPerDlciEntry
             ACCESS   not-accessible
             STATUS   mandatory
             DESCRIPTION
                "The Network Layer Short Term Statistics
                 for a particular DLCI. This table organizes
                 statistics by high-layer network protocol."
            INDEX { tfrapPerfNetwProtoPerDlciInterval,
                    tfrapPerfNetwProtoPerDlciValue }
            ::= { tfrapPerfNetwProtoPerDlciTable 1 }

         TfrapPerfNetwProtoPerDlciEntry ::=
             SEQUENCE {
                 tfrapPerfNetwProtoPerDlciInterval  INTEGER,
                 tfrapPerfNetwProtoPerDlciValue     INTEGER,
                 tfrapPerfNetwProtoPerDlciRxTotal   Counter,
                 tfrapPerfNetwProtoPerDlciTxTotal   Counter,
                 tfrapPerfNetwProtoPerDlciRxIp      Counter,
                 tfrapPerfNetwProtoPerDlciTxIp      Counter,
                 tfrapPerfNetwProtoPerDlciRxIpx     Counter,
                 tfrapPerfNetwProtoPerDlciTxIpx     Counter,
                 tfrapPerfNetwProtoPerDlciRxSna     Counter,
                 tfrapPerfNetwProtoPerDlciTxSna     Counter,
                 tfrapPerfNetwProtoPerDlciRxArp     Counter,
                 tfrapPerfNetwProtoPerDlciTxArp     Counter,
                 tfrapPerfNetwProtoPerDlciRxCisco   Counter,
                 tfrapPerfNetwProtoPerDlciTxCisco   Counter,
                 tfrapPerfNetwProtoPerDlciRxOther   Counter,
                 tfrapPerfNetwProtoPerDlciTxOther   Counter,
                 tfrapPerfNetwProtoPerDlciRxVnip    Counter,
                 tfrapPerfNetwProtoPerDlciTxVnip    Counter,
                 tfrapPerfNetwProtoPerDlciRxAnnexG  Counter,
                 tfrapPerfNetwProtoPerDlciTxAnnexG  Counter
             }

      tfrapPerfNetwProtoPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfNetwProtoPerDlciEntry 1 }

      tfrapPerfNetwProtoPerDlciValue    OBJECT-TYPE
             SYNTAX      INTEGER 
             ACCESS      read-only
             STATUS      mandatory
             DESCRIPTION
                "The DLCI value with which the Statistics are associated."
            ::= { tfrapPerfNetwProtoPerDlciEntry 2 }

      tfrapPerfNetwProtoPerDlciRxTotal    OBJECT-TYPE
             SYNTAX      Counter 
             ACCESS      read-only
             STATUS      mandatory
             DESCRIPTION
                "The total number of received Network Layer bytes
                 that have been counted on this DLCI."
            ::= { tfrapPerfNetwProtoPerDlciEntry 3 }

      tfrapPerfNetwProtoPerDlciTxTotal    OBJECT-TYPE
             SYNTAX      Counter
             ACCESS      read-only
             STATUS      mandatory
             DESCRIPTION
                "The total number of transmitted Network Layer bytes
                 that have been counted on this DLCI."
            ::= { tfrapPerfNetwProtoPerDlciEntry 4 }

      tfrapPerfNetwProtoPerDlciRxIp    OBJECT-TYPE
             SYNTAX      Counter
             ACCESS      read-only
             STATUS      mandatory
             DESCRIPTION
                "The number of received IP bytes
                 that have been counted on this DLCI."
            ::= { tfrapPerfNetwProtoPerDlciEntry 5 }

      tfrapPerfNetwProtoPerDlciTxIp    OBJECT-TYPE
             SYNTAX      Counter
             ACCESS      read-only
             STATUS      mandatory
             DESCRIPTION
                "The number of transmitted IP bytes
                 that have been counted on this DLCI."
            ::= { tfrapPerfNetwProtoPerDlciEntry 6 }

      tfrapPerfNetwProtoPerDlciRxIpx    OBJECT-TYPE
             SYNTAX      Counter
             ACCESS      read-only
             STATUS      mandatory
             DESCRIPTION
                "The number of received IPX bytes
                 that have been counted on this DLCI."
            ::= { tfrapPerfNetwProtoPerDlciEntry 7 }

      tfrapPerfNetwProtoPerDlciTxIpx    OBJECT-TYPE
             SYNTAX      Counter
             ACCESS      read-only
             STATUS      mandatory
             DESCRIPTION
                "The number of transmitted IPX bytes
                 that have been counted on this DLCI."
            ::= { tfrapPerfNetwProtoPerDlciEntry 8 }

      tfrapPerfNetwProtoPerDlciRxSna    OBJECT-TYPE
             SYNTAX      Counter
             ACCESS      read-only
             STATUS      mandatory
             DESCRIPTION
                "The number of received SNA bytes
                 that have been counted on this DLCI."
            ::= { tfrapPerfNetwProtoPerDlciEntry 9 }

      tfrapPerfNetwProtoPerDlciTxSna    OBJECT-TYPE
             SYNTAX      Counter
             ACCESS      read-only
             STATUS      mandatory
             DESCRIPTION
                "The number of transmitted SNA bytes
                 that have been counted on this DLCI."
            ::= { tfrapPerfNetwProtoPerDlciEntry 10 }

      tfrapPerfNetwProtoPerDlciRxArp    OBJECT-TYPE
             SYNTAX      Counter
             ACCESS      read-only
             STATUS      mandatory
             DESCRIPTION
                "The number of received ARP bytes
                 that have been counted on this DLCI."
            ::= { tfrapPerfNetwProtoPerDlciEntry 11 }

      tfrapPerfNetwProtoPerDlciTxArp    OBJECT-TYPE
             SYNTAX      Counter
             ACCESS      read-only
             STATUS      mandatory
             DESCRIPTION
                "The number of transmitted ARP bytes
                 that have been counted on this DLCI."
            ::= { tfrapPerfNetwProtoPerDlciEntry 12 }

      tfrapPerfNetwProtoPerDlciRxCisco    OBJECT-TYPE
             SYNTAX      Counter
             ACCESS      read-only
             STATUS      mandatory
             DESCRIPTION
                "The number of received Cisco protocol bytes
                 that have been counted on this DLCI."
            ::= { tfrapPerfNetwProtoPerDlciEntry 13 }

      tfrapPerfNetwProtoPerDlciTxCisco    OBJECT-TYPE
             SYNTAX      Counter
             ACCESS      read-only
             STATUS      mandatory
             DESCRIPTION
                "The number of transmitted Cisco protocol bytes
                 that have been counted on this DLCI."
            ::= { tfrapPerfNetwProtoPerDlciEntry 14 }

      tfrapPerfNetwProtoPerDlciRxOther    OBJECT-TYPE
             SYNTAX      Counter
             ACCESS      read-only
             STATUS      mandatory
             DESCRIPTION
                "The number of received bytes on this DLCI
                 from protocols that are not counted elsewhere
                 in this table."
            ::= { tfrapPerfNetwProtoPerDlciEntry 15 }

      tfrapPerfNetwProtoPerDlciTxOther    OBJECT-TYPE
             SYNTAX      Counter
             ACCESS      read-only
             STATUS      mandatory
             DESCRIPTION
                "The number of transmitted bytes on this DLCI
                 from protocols that are not counted elsewhere
                 in this table."
            ::= { tfrapPerfNetwProtoPerDlciEntry 16 }

      tfrapPerfNetwProtoPerDlciRxVnip    OBJECT-TYPE
             SYNTAX      Counter 
             ACCESS      read-only
             STATUS      mandatory
             DESCRIPTION
                "The number of received VNIP protocol bytes
                 that have been counted on this DLCI."
            ::= { tfrapPerfNetwProtoPerDlciEntry 17 }

      tfrapPerfNetwProtoPerDlciTxVnip    OBJECT-TYPE
             SYNTAX      Counter 
             ACCESS      read-only
             STATUS      mandatory
             DESCRIPTION
                "The number of transmitted VNIP protocol bytes
                 that have been counted on this DLCI."
            ::= { tfrapPerfNetwProtoPerDlciEntry 18 }

      tfrapPerfNetwProtoPerDlciRxAnnexG  OBJECT-TYPE
             SYNTAX      Counter 
             ACCESS      read-only
             STATUS      mandatory
             DESCRIPTION
                "The number of received Annex G protocol 
                 bytes that have been counted on this DLCI."
            ::= { tfrapPerfNetwProtoPerDlciEntry 19 }

      tfrapPerfNetwProtoPerDlciTxAnnexG  OBJECT-TYPE
             SYNTAX      Counter 
             ACCESS      read-only
             STATUS      mandatory
             DESCRIPTION
                "The number of transmitted Annex G protocol 
                 bytes that have been counted on this DLCI."
            ::= { tfrapPerfNetwProtoPerDlciEntry 20 }



   --  Network Layer Short Term Statistics totals.

   tfrapPerfNetwProtoTotalTable OBJECT-TYPE
         SYNTAX   SEQUENCE OF TfrapPerfNetwProtoTotalEntry
         ACCESS   not-accessible
         STATUS   mandatory
         DESCRIPTION
            "The Short Term Statistics on Network Layer
            protocols summed across all DLCIs."
         ::= { tfrapPerfNetworkShortTerm 2 }

         tfrapPerfNetwProtoTotalEntry OBJECT-TYPE
             SYNTAX   TfrapPerfNetwProtoTotalEntry
             ACCESS   not-accessible
             STATUS   mandatory
             DESCRIPTION
                "The Network Layer Short Term Statistics
                 for a particular DLCI."
            INDEX { tfrapPerfNetwProtoTotalInterval }
            ::= { tfrapPerfNetwProtoTotalTable 1 }

         TfrapPerfNetwProtoTotalEntry ::=
             SEQUENCE {
                 tfrapPerfNetwProtoTotalInterval  INTEGER,
                 tfrapPerfNetwProtoTotalRxTotal   Counter,
                 tfrapPerfNetwProtoTotalTxTotal   Counter,
                 tfrapPerfNetwProtoTotalRxIp      Counter,
                 tfrapPerfNetwProtoTotalTxIp      Counter,
                 tfrapPerfNetwProtoTotalRxIpx     Counter,
                 tfrapPerfNetwProtoTotalTxIpx     Counter,
                 tfrapPerfNetwProtoTotalRxSna     Counter,
                 tfrapPerfNetwProtoTotalTxSna     Counter,
                 tfrapPerfNetwProtoTotalRxArp     Counter,
                 tfrapPerfNetwProtoTotalTxArp     Counter,
                 tfrapPerfNetwProtoTotalRxCisco   Counter,
                 tfrapPerfNetwProtoTotalTxCisco   Counter,
                 tfrapPerfNetwProtoTotalRxOther   Counter,
                 tfrapPerfNetwProtoTotalTxOther   Counter,
                 tfrapPerfNetwProtoTotalRxVnip    Counter,
                 tfrapPerfNetwProtoTotalTxVnip    Counter,
                 tfrapPerfNetwProtoTotalRxAnnexG  Counter,
                 tfrapPerfNetwProtoTotalTxAnnexG  Counter
             }

      tfrapPerfNetwProtoTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfNetwProtoTotalEntry 1 }

      tfrapPerfNetwProtoTotalRxTotal    OBJECT-TYPE
             SYNTAX      Counter 
             ACCESS      read-only
             STATUS      mandatory
             DESCRIPTION
                "The total number of received Network Layer bytes
                 that have been counted across all DLCIs."
            ::= { tfrapPerfNetwProtoTotalEntry 3 }

      tfrapPerfNetwProtoTotalTxTotal    OBJECT-TYPE
             SYNTAX      Counter 
             ACCESS      read-only
             STATUS      mandatory
             DESCRIPTION
                "The total number of transmitted Network Layer bytes
                 that have been counted across all DLCIs."
            ::= { tfrapPerfNetwProtoTotalEntry 4 }

      tfrapPerfNetwProtoTotalRxIp    OBJECT-TYPE
             SYNTAX      Counter 
             ACCESS      read-only
             STATUS      mandatory
             DESCRIPTION
                "The number of received IP bytes
                 that have been counted across all DLCIs."
            ::= { tfrapPerfNetwProtoTotalEntry 5 }

      tfrapPerfNetwProtoTotalTxIp    OBJECT-TYPE
             SYNTAX      Counter
             ACCESS      read-only
             STATUS      mandatory
             DESCRIPTION
                "The number of transmitted IP bytes
                 that have been counted across all DLCIs."
            ::= { tfrapPerfNetwProtoTotalEntry 6 }

      tfrapPerfNetwProtoTotalRxIpx    OBJECT-TYPE
             SYNTAX      Counter
             ACCESS      read-only
             STATUS      mandatory
             DESCRIPTION
                "The number of received IPX bytes
                 that have been counted across all DLCIs."
            ::= { tfrapPerfNetwProtoTotalEntry 7 }

      tfrapPerfNetwProtoTotalTxIpx    OBJECT-TYPE
             SYNTAX      Counter
             ACCESS      read-only
             STATUS      mandatory
             DESCRIPTION
                "The number of transmitted IPX bytes
                 that have been counted across all DLCIs."
            ::= { tfrapPerfNetwProtoTotalEntry 8 }

      tfrapPerfNetwProtoTotalRxSna    OBJECT-TYPE
             SYNTAX      Counter
             ACCESS      read-only
             STATUS      mandatory
             DESCRIPTION
                "The number of received SNA bytes
                 that have been counted across all DLCIs."
            ::= { tfrapPerfNetwProtoTotalEntry 9 }

      tfrapPerfNetwProtoTotalTxSna    OBJECT-TYPE
             SYNTAX      Counter
             ACCESS      read-only
             STATUS      mandatory
             DESCRIPTION
                "The number of transmitted SNA bytes
                 that have been counted across all DLCIs."
            ::= { tfrapPerfNetwProtoTotalEntry 10 }

      tfrapPerfNetwProtoTotalRxArp    OBJECT-TYPE
             SYNTAX      Counter
             ACCESS      read-only
             STATUS      mandatory
             DESCRIPTION
                "The number of received ARP bytes
                 that have been counted across all DLCIs."
            ::= { tfrapPerfNetwProtoTotalEntry 11 }

      tfrapPerfNetwProtoTotalTxArp    OBJECT-TYPE
             SYNTAX      Counter
             ACCESS      read-only
             STATUS      mandatory
             DESCRIPTION
                "The number of transmitted ARP bytes
                 that have been counted across all DLCIs."
            ::= { tfrapPerfNetwProtoTotalEntry 12 }

      tfrapPerfNetwProtoTotalRxCisco    OBJECT-TYPE
             SYNTAX      Counter
             ACCESS      read-only
             STATUS      mandatory
             DESCRIPTION
                "The number of received Cisco protocol bytes
                 that have been counted across all DLCIs."
            ::= { tfrapPerfNetwProtoTotalEntry 13 }

      tfrapPerfNetwProtoTotalTxCisco    OBJECT-TYPE
             SYNTAX      Counter
             ACCESS      read-only
             STATUS      mandatory
             DESCRIPTION
                "The number of transmitted Cisco protocol bytes
                 that have been counted across all DLCIs."
            ::= { tfrapPerfNetwProtoTotalEntry 14 }

      tfrapPerfNetwProtoTotalRxOther    OBJECT-TYPE
             SYNTAX      Counter
             ACCESS      read-only
             STATUS      mandatory
             DESCRIPTION
                "The number of received bytes across all DLCIs
                 from protocols that are not counted elsewhere
                 in this table."
            ::= { tfrapPerfNetwProtoTotalEntry 15 }

      tfrapPerfNetwProtoTotalTxOther    OBJECT-TYPE
             SYNTAX      Counter
             ACCESS      read-only
             STATUS      mandatory
             DESCRIPTION
                "The number of transmitted bytes across all DLCIs
                 from protocols that are not counted elsewhere
                 in this table."
            ::= { tfrapPerfNetwProtoTotalEntry 16 }

      tfrapPerfNetwProtoTotalRxVnip    OBJECT-TYPE
             SYNTAX      Counter 
             ACCESS      read-only
             STATUS      mandatory
             DESCRIPTION
                "The number of received VNIP protocol bytes
                 that have been counted across all DLCIs."
            ::= { tfrapPerfNetwProtoTotalEntry 17 }

      tfrapPerfNetwProtoTotalTxVnip    OBJECT-TYPE
             SYNTAX      Counter 
             ACCESS      read-only
             STATUS      mandatory
             DESCRIPTION
                "The number of transmitted VNIP protocol bytes
                 that have been counted across all DLCIs."
            ::= { tfrapPerfNetwProtoTotalEntry 18 }

      tfrapPerfNetwProtoTotalRxAnnexG  OBJECT-TYPE
             SYNTAX      Counter 
             ACCESS      read-only
             STATUS      mandatory
             DESCRIPTION
                "The number of received Annex G protocol bytes
                 that have been counted across all DLCIs."
            ::= { tfrapPerfNetwProtoTotalEntry 19 }

      tfrapPerfNetwProtoTotalTxAnnexG  OBJECT-TYPE
             SYNTAX      Counter 
             ACCESS      read-only
             STATUS      mandatory
             DESCRIPTION
                "The number of transmitted Annex G protocol bytes
                 that have been counted across all DLCIs."
            ::= { tfrapPerfNetwProtoTotalEntry 20 }


   --  IP Short Term Statistics for each DLCI.

   tfrapPerfIpPerDlciTable OBJECT-TYPE
         SYNTAX   SEQUENCE OF TfrapPerfIpPerDlciEntry
         ACCESS   not-accessible
         STATUS   mandatory
         DESCRIPTION
            "The Short Term Statistics on the IP
            protocol for each DLCI."
         ::= { tfrapPerfNetworkShortTerm 3 }

         tfrapPerfIpPerDlciEntry OBJECT-TYPE
             SYNTAX   TfrapPerfIpPerDlciEntry
             ACCESS   not-accessible
             STATUS   mandatory
             DESCRIPTION
                "The IP Short Term Statistics for a particular DLCI."
            INDEX { tfrapPerfIpPerDlciInterval, tfrapPerfIpPerDlciValue }
            ::= { tfrapPerfIpPerDlciTable 1 }

         TfrapPerfIpPerDlciEntry ::=
             SEQUENCE {
                 tfrapPerfIpPerDlciInterval  INTEGER,
                 tfrapPerfIpPerDlciValue     INTEGER,
                 tfrapPerfIpPerDlciRxTotal   Counter,
                 tfrapPerfIpPerDlciTxTotal   Counter,
                 tfrapPerfIpPerDlciRxTcp     Counter,
                 tfrapPerfIpPerDlciTxTcp     Counter,
                 tfrapPerfIpPerDlciRxUdp     Counter,
                 tfrapPerfIpPerDlciTxUdp     Counter,
                 tfrapPerfIpPerDlciRxIcmp    Counter,
                 tfrapPerfIpPerDlciTxIcmp    Counter,
                 tfrapPerfIpPerDlciRxOther   Counter,
                 tfrapPerfIpPerDlciTxOther   Counter,
                 tfrapPerfIpPerDlciRxIgrp    Counter,
                 tfrapPerfIpPerDlciTxIgrp    Counter
             }

      tfrapPerfIpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfIpPerDlciEntry 1 }

      tfrapPerfIpPerDlciValue    OBJECT-TYPE
             SYNTAX      INTEGER 
             ACCESS      read-only
             STATUS      mandatory
             DESCRIPTION
                "The DLCI value with which the Statistics are associated."
            ::= { tfrapPerfIpPerDlciEntry 2 }

      tfrapPerfIpPerDlciRxTotal    OBJECT-TYPE
             SYNTAX      Counter 
             ACCESS      read-only
             STATUS      mandatory
             DESCRIPTION
                "The total number of received IP bytes
                 that have been counted on this DLCI."
            ::= { tfrapPerfIpPerDlciEntry 3 }

      tfrapPerfIpPerDlciTxTotal    OBJECT-TYPE
             SYNTAX      Counter
             ACCESS      read-only
             STATUS      mandatory
             DESCRIPTION
                "The total number of transmitted IP bytes
                 that have been counted on this DLCI."
            ::= { tfrapPerfIpPerDlciEntry 4 }

      tfrapPerfIpPerDlciRxTcp    OBJECT-TYPE
             SYNTAX      Counter
             ACCESS      read-only
             STATUS      mandatory
             DESCRIPTION
                "The number of received TCP over IP bytes
                 that have been counted on this DLCI."
            ::= { tfrapPerfIpPerDlciEntry 5 }

      tfrapPerfIpPerDlciTxTcp    OBJECT-TYPE
             SYNTAX      Counter
             ACCESS      read-only
             STATUS      mandatory
             DESCRIPTION
                "The number of transmitted TCP over IP bytes
                 that have been counted on this DLCI."
            ::= { tfrapPerfIpPerDlciEntry 6 }

      tfrapPerfIpPerDlciRxUdp    OBJECT-TYPE
             SYNTAX      Counter
             ACCESS      read-only
             STATUS      mandatory
             DESCRIPTION
                "The number of received UDP over IP bytes
                 that have been counted on this DLCI."
            ::= { tfrapPerfIpPerDlciEntry 7 }

      tfrapPerfIpPerDlciTxUdp    OBJECT-TYPE
             SYNTAX      Counter
             ACCESS      read-only
             STATUS      mandatory
             DESCRIPTION
                "The number of transmitted UDP over IP bytes
                 that have been counted on this DLCI."
            ::= { tfrapPerfIpPerDlciEntry 8 }

      tfrapPerfIpPerDlciRxIcmp    OBJECT-TYPE
             SYNTAX      Counter
             ACCESS      read-only
             STATUS      mandatory
             DESCRIPTION
                "The number of received ICMP over IP bytes
                 that have been counted on this DLCI."
            ::= { tfrapPerfIpPerDlciEntry 9 }

      tfrapPerfIpPerDlciTxIcmp    OBJECT-TYPE
             SYNTAX      Counter
             ACCESS      read-only
             STATUS      mandatory
             DESCRIPTION
                "The number of transmitted ICMP over IP bytes
                 that have been counted on this DLCI."
            ::= { tfrapPerfIpPerDlciEntry 10 }

      tfrapPerfIpPerDlciRxOther    OBJECT-TYPE
             SYNTAX      Counter
             ACCESS      read-only
             STATUS      mandatory
             DESCRIPTION
                "The number of received bytes on this DLCI
                 from protocols over IP that are not counted
                 elsewhere in this table."
            ::= { tfrapPerfIpPerDlciEntry 11 }

      tfrapPerfIpPerDlciTxOther    OBJECT-TYPE
             SYNTAX      Counter
             ACCESS      read-only
             STATUS      mandatory
             DESCRIPTION
                "The number of transmitted bytes on this DLCI
                 from protocols over IP that are not counted
                 elsewhere in this table."
            ::= { tfrapPerfIpPerDlciEntry 12 }

      tfrapPerfIpPerDlciRxIgrp    OBJECT-TYPE
             SYNTAX      Counter 
             ACCESS      read-only
             STATUS      mandatory
             DESCRIPTION
                "The number of received IGRP over IP bytes
                 that have been counted on this DLCI."
            ::= { tfrapPerfIpPerDlciEntry 13 }

      tfrapPerfIpPerDlciTxIgrp    OBJECT-TYPE
             SYNTAX      Counter 
             ACCESS      read-only
             STATUS      mandatory
             DESCRIPTION
                "The number of transmitted IGRP over IP bytes
                 that have been counted on this DLCI."
            ::= { tfrapPerfIpPerDlciEntry 14 }


   --  IP Short Term Statistics totals.

   tfrapPerfIpTotalTable OBJECT-TYPE
         SYNTAX   SEQUENCE OF TfrapPerfIpTotalEntry
         ACCESS   not-accessible
         STATUS   mandatory
         DESCRIPTION
            "The Short Term Statistics on the IP
            protocol across all DLCIs."
         ::= { tfrapPerfNetworkShortTerm 4 }

         tfrapPerfIpTotalEntry OBJECT-TYPE
             SYNTAX   TfrapPerfIpTotalEntry
             ACCESS   not-accessible
             STATUS   mandatory
             DESCRIPTION
                "The IP Short Term Statistics across all DLCIs."
            INDEX { tfrapPerfIpTotalInterval }
            ::= { tfrapPerfIpTotalTable 1 }

         TfrapPerfIpTotalEntry ::=
             SEQUENCE {
                 tfrapPerfIpTotalInterval INTEGER,
                 tfrapPerfIpTotalRxTotal  Counter,
                 tfrapPerfIpTotalTxTotal  Counter,
                 tfrapPerfIpTotalRxTcp    Counter,
                 tfrapPerfIpTotalTxTcp    Counter,
                 tfrapPerfIpTotalRxUdp    Counter,
                 tfrapPerfIpTotalTxUdp    Counter,
                 tfrapPerfIpTotalRxIcmp   Counter,
                 tfrapPerfIpTotalTxIcmp   Counter,
                 tfrapPerfIpTotalRxOther  Counter,
                 tfrapPerfIpTotalTxOther  Counter,
                 tfrapPerfIpTotalRxIgrp   Counter,
                 tfrapPerfIpTotalTxIgrp   Counter
             }

      tfrapPerfIpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfIpTotalEntry 1 }

      tfrapPerfIpTotalRxTotal    OBJECT-TYPE
             SYNTAX      Counter
             ACCESS      read-only
             STATUS      mandatory
             DESCRIPTION
                "The total number of received IP bytes
                 that have been counted across all DLCIs."
            ::= { tfrapPerfIpTotalEntry 3 }

      tfrapPerfIpTotalTxTotal    OBJECT-TYPE
             SYNTAX      Counter
             ACCESS      read-only
             STATUS      mandatory
             DESCRIPTION
                "The total number of transmitted IP bytes
                 that have been counted across all DLCIs."
            ::= { tfrapPerfIpTotalEntry 4 }

      tfrapPerfIpTotalRxTcp    OBJECT-TYPE
             SYNTAX      Counter
             ACCESS      read-only
             STATUS      mandatory
             DESCRIPTION
                "The number of received TCP over IP bytes
                 that have been counted across all DLCIs."
            ::= { tfrapPerfIpTotalEntry 5 }

      tfrapPerfIpTotalTxTcp    OBJECT-TYPE
             SYNTAX      Counter
             ACCESS      read-only
             STATUS      mandatory
             DESCRIPTION
                "The number of transmitted TCP over IP bytes
                 that have been counted across all DLCIs."
            ::= { tfrapPerfIpTotalEntry 6 }

      tfrapPerfIpTotalRxUdp    OBJECT-TYPE
             SYNTAX      Counter
             ACCESS      read-only
             STATUS      mandatory
             DESCRIPTION
                "The number of received UDP over IP bytes
                 that have been counted across all DLCIs."
            ::= { tfrapPerfIpTotalEntry 7 }

      tfrapPerfIpTotalTxUdp    OBJECT-TYPE
             SYNTAX      Counter
             ACCESS      read-only
             STATUS      mandatory
             DESCRIPTION
                "The number of transmitted UDP over IP bytes
                 that have been counted across all DLCIs."
            ::= { tfrapPerfIpTotalEntry 8 }

      tfrapPerfIpTotalRxIcmp    OBJECT-TYPE
             SYNTAX      Counter
             ACCESS      read-only
             STATUS      mandatory
             DESCRIPTION
                "The number of received ICMP over IP bytes
                 that have been counted  across all DLCIs."
            ::= { tfrapPerfIpTotalEntry 9 }

      tfrapPerfIpTotalTxIcmp    OBJECT-TYPE
             SYNTAX      Counter
             ACCESS      read-only
             STATUS      mandatory
             DESCRIPTION
                "The number of transmitted ICMP over IP bytes
                 that have been counted across all DLCIs."
            ::= { tfrapPerfIpTotalEntry 10 }

      tfrapPerfIpTotalRxOther    OBJECT-TYPE
             SYNTAX      Counter
             ACCESS      read-only
             STATUS      mandatory
             DESCRIPTION
                "The number of received bytes across all DLCIs
                 from protocols over IP that are not counted
                 elsewhere in this table."
            ::= { tfrapPerfIpTotalEntry 11 }

      tfrapPerfIpTotalTxOther    OBJECT-TYPE
             SYNTAX      Counter
             ACCESS      read-only
             STATUS      mandatory
             DESCRIPTION
                "The number of transmitted bytes across all DLCIs.
                 from protocols over IP that are not counted
                 elsewhere in this table."
            ::= { tfrapPerfIpTotalEntry 12 }

      tfrapPerfIpTotalRxIgrp    OBJECT-TYPE
             SYNTAX      Counter 
             ACCESS      read-only
             STATUS      mandatory
             DESCRIPTION
                "The number of received IGRP over IP bytes
                 that have been counted across all DLCIs."
            ::= { tfrapPerfIpTotalEntry 13 }

      tfrapPerfIpTotalTxIgrp    OBJECT-TYPE
             SYNTAX      Counter 
             ACCESS      read-only
             STATUS      mandatory
             DESCRIPTION
                "The number of transmitted IGRP over IP bytes
                 that have been counted across all DLCIs."
            ::= { tfrapPerfIpTotalEntry 14 }


   --  ICMP Short Term Statistics for each DLCI.

   tfrapPerfIcmpPerDlciTable OBJECT-TYPE
         SYNTAX   SEQUENCE OF TfrapPerfIcmpPerDlciEntry
         ACCESS   not-accessible
         STATUS   mandatory
         DESCRIPTION
            "Short Term Statistics on the ICMP
             protocol for each DLCI."
         ::= { tfrapPerfNetworkShortTerm 5 }

         tfrapPerfIcmpPerDlciEntry OBJECT-TYPE
             SYNTAX   TfrapPerfIcmpPerDlciEntry
             ACCESS   not-accessible
             STATUS   mandatory
             DESCRIPTION
                "The ICMP Short Term Statistics for a particular DLCI."
            INDEX { tfrapPerfIcmpPerDlciInterval, tfrapPerfIcmpPerDlciValue }
            ::= { tfrapPerfIcmpPerDlciTable 1 }

         TfrapPerfIcmpPerDlciEntry ::=
             SEQUENCE {
                 tfrapPerfIcmpPerDlciInterval        INTEGER,
                 tfrapPerfIcmpPerDlciValue           INTEGER,
                 tfrapPerfIcmpPerDlciRxTotal         Counter,
                 tfrapPerfIcmpPerDlciTxTotal         Counter,
                 tfrapPerfIcmpPerDlciRxEchoRep       Counter,
                 tfrapPerfIcmpPerDlciTxEchoRep       Counter,
                 tfrapPerfIcmpPerDlciRxDestUnr       Counter,
                 tfrapPerfIcmpPerDlciTxDestUnr       Counter,
                 tfrapPerfIcmpPerDlciRxSrcQuench     Counter,
                 tfrapPerfIcmpPerDlciTxSrcQuench     Counter,
                 tfrapPerfIcmpPerDlciRxRedirect      Counter,
                 tfrapPerfIcmpPerDlciTxRedirect      Counter,
                 tfrapPerfIcmpPerDlciRxEchoReq       Counter,
                 tfrapPerfIcmpPerDlciTxEchoReq       Counter,
                 tfrapPerfIcmpPerDlciRxTimeExcd      Counter,
                 tfrapPerfIcmpPerDlciTxTimeExcd      Counter,
                 tfrapPerfIcmpPerDlciRxParamProb     Counter,
                 tfrapPerfIcmpPerDlciTxParamProb     Counter,
                 tfrapPerfIcmpPerDlciRxTimestpReq    Counter,
                 tfrapPerfIcmpPerDlciTxTimestpReq    Counter,
                 tfrapPerfIcmpPerDlciRxTimestpRep    Counter,
                 tfrapPerfIcmpPerDlciTxTimestpRep    Counter,
                 tfrapPerfIcmpPerDlciRxAddrMaskReq   Counter,
                 tfrapPerfIcmpPerDlciTxAddrMaskReq   Counter,
                 tfrapPerfIcmpPerDlciRxAddrMaskRep   Counter,
                 tfrapPerfIcmpPerDlciTxAddrMaskRep   Counter,
                 tfrapPerfIcmpPerDlciRxPktTooBig     Counter,
                 tfrapPerfIcmpPerDlciTxPktTooBig     Counter,
                 tfrapPerfIcmpPerDlciRxGmQuery       Counter,
                 tfrapPerfIcmpPerDlciTxGmQuery       Counter,
                 tfrapPerfIcmpPerDlciRxGmReport      Counter,
                 tfrapPerfIcmpPerDlciTxGmReport      Counter,
                 tfrapPerfIcmpPerDlciRxGmReduct      Counter,
                 tfrapPerfIcmpPerDlciTxGmReduct      Counter
             }

      tfrapPerfIcmpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfIcmpPerDlciEntry 1 }

      tfrapPerfIcmpPerDlciValue    OBJECT-TYPE
             SYNTAX      INTEGER 
            ACCESS      read-only
             STATUS      mandatory
             DESCRIPTION
                "The DLCI value in which the Statistics are associated."
            ::= { tfrapPerfIcmpPerDlciEntry 2 }

      tfrapPerfIcmpPerDlciRxTotal    OBJECT-TYPE
             SYNTAX      Counter
             ACCESS      read-only
             STATUS      mandatory
             DESCRIPTION
                "The total number of ICMP bytes that have been
                 counted on this DLCI."
            ::= { tfrapPerfIcmpPerDlciEntry 3 }

      tfrapPerfIcmpPerDlciTxTotal    OBJECT-TYPE
             SYNTAX      Counter
             ACCESS      read-only
               STATUS      mandatory
             DESCRIPTION
                "The total number of ICMP bytes that have been
                 counted on this DLCI."
            ::= { tfrapPerfIcmpPerDlciEntry 4 }

      tfrapPerfIcmpPerDlciRxEchoRep    OBJECT-TYPE
             SYNTAX      Counter
             ACCESS      read-only
             STATUS      mandatory
             DESCRIPTION
                "The number of bytes in ICMP ECHO repies
                 that have been counted on this DLCI."
            ::= { tfrapPerfIcmpPerDlciEntry 5 }

      tfrapPerfIcmpPerDlciTxEchoRep    OBJECT-TYPE
             SYNTAX      Counter
             ACCESS      read-only
               STATUS      mandatory
             DESCRIPTION
                "The number of bytes in ICMP ECHO repies
                 that have been counted on this DLCI."
            ::= { tfrapPerfIcmpPerDlciEntry 6 }

      tfrapPerfIcmpPerDlciRxDestUnr    OBJECT-TYPE
             SYNTAX      Counter
             ACCESS      read-only
             STATUS      mandatory
             DESCRIPTION
                "The number of bytes in ICMP destination unreachables
                 that have been counted on this DLCI."
            ::= { tfrapPerfIcmpPerDlciEntry 7 }

      tfrapPerfIcmpPerDlciTxDestUnr    OBJECT-TYPE
             SYNTAX      Counter
             ACCESS      read-only
               STATUS      mandatory
             DESCRIPTION
                "The number of bytes in ICMP destination unreachables
                 that have been counted on this DLCI."
            ::= { tfrapPerfIcmpPerDlciEntry 8 }

      tfrapPerfIcmpPerDlciRxSrcQuench    OBJECT-TYPE
             SYNTAX      Counter
             ACCESS      read-only
             STATUS      mandatory
             DESCRIPTION
                "The number of bytes in ICMP source quenches
                 that have been counted on this DLCI."
            ::= { tfrapPerfIcmpPerDlciEntry 9 }

      tfrapPerfIcmpPerDlciTxSrcQuench    OBJECT-TYPE
             SYNTAX      Counter
             ACCESS      read-only
             STATUS      mandatory
             DESCRIPTION
                "The number of bytes in ICMP source quenches
                 that have been counted on this DLCI."
            ::= { tfrapPerfIcmpPerDlciEntry 10 }

      tfrapPerfIcmpPerDlciRxRedirect    OBJECT-TYPE
             SYNTAX      Counter
             ACCESS      read-only
             STATUS      mandatory
             DESCRIPTION
                "The number of bytes in ICMP redirects
                 that have been counted on this DLCI."
            ::= { tfrapPerfIcmpPerDlciEntry 11 }

      tfrapPerfIcmpPerDlciTxRedirect    OBJECT-TYPE
             SYNTAX      Counter
             ACCESS      read-only
             STATUS      mandatory
             DESCRIPTION
                "The number of bytes in ICMP redirects
                 that have been counted on this DLCI."
            ::= { tfrapPerfIcmpPerDlciEntry 12 }

      tfrapPerfIcmpPerDlciRxEchoReq    OBJECT-TYPE
             SYNTAX      Counter
             ACCESS      read-only
             STATUS      mandatory
             DESCRIPTION
                "The number of bytes in ICMP ECHO requests
                 that have been counted on this DLCI."
            ::= { tfrapPerfIcmpPerDlciEntry 13 }

      tfrapPerfIcmpPerDlciTxEchoReq    OBJECT-TYPE
             SYNTAX      Counter
             ACCESS      read-only
             STATUS      mandatory
             DESCRIPTION
                "The number of bytes in ICMP ECHO requests
                 that have been counted on this DLCI."
            ::= { tfrapPerfIcmpPerDlciEntry 14 }

      tfrapPerfIcmpPerDlciRxTimeExcd    OBJECT-TYPE
             SYNTAX      Counter
             ACCESS      read-only
             STATUS      mandatory
             DESCRIPTION
                "The number of bytes in ICMP time exceededs
                 that have been counted on this DLCI."
            ::= { tfrapPerfIcmpPerDlciEntry 15 }

      tfrapPerfIcmpPerDlciTxTimeExcd    OBJECT-TYPE
             SYNTAX      Counter
             ACCESS      read-only
             STATUS      mandatory
             DESCRIPTION
                "The number of bytes in ICMP time exceededs
                 that have been counted on this DLCI."
            ::= { tfrapPerfIcmpPerDlciEntry 16 }

      tfrapPerfIcmpPerDlciRxParamProb    OBJECT-TYPE
             SYNTAX      Counter
             ACCESS      read-only
             STATUS      mandatory
             DESCRIPTION
                "The number of bytes in ICMP parameter problems
                 that have been counted on this DLCI."
            ::= { tfrapPerfIcmpPerDlciEntry 17 }

      tfrapPerfIcmpPerDlciTxParamProb    OBJECT-TYPE
             SYNTAX      Counter
             ACCESS      read-only
             STATUS      mandatory
             DESCRIPTION
                "The number of bytes in ICMP parameter problems
                 that have been counted on this DLCI."
            ::= { tfrapPerfIcmpPerDlciEntry 18 }

      tfrapPerfIcmpPerDlciRxTimestpReq    OBJECT-TYPE
             SYNTAX      Counter
             ACCESS      read-only
             STATUS      mandatory
             DESCRIPTION
                "The number of bytes in ICMP timestamp requests
                 that have been counted on this DLCI."
            ::= { tfrapPerfIcmpPerDlciEntry 19 }

      tfrapPerfIcmpPerDlciTxTimestpReq    OBJECT-TYPE
             SYNTAX      Counter
             ACCESS      read-only
             STATUS      mandatory
             DESCRIPTION
                "The number of bytes in ICMP timestamp requests
                 that have been counted on this DLCI."
            ::= { tfrapPerfIcmpPerDlciEntry 20 }

      tfrapPerfIcmpPerDlciRxTimestpRep    OBJECT-TYPE
             SYNTAX      Counter
             ACCESS      read-only
             STATUS      mandatory
             DESCRIPTION
                "The number of bytes in ICMP timestamp replies
                 that have been counted on this DLCI."
            ::= { tfrapPerfIcmpPerDlciEntry 21 }

      tfrapPerfIcmpPerDlciTxTimestpRep    OBJECT-TYPE
             SYNTAX      Counter
             ACCESS      read-only
             STATUS      mandatory
             DESCRIPTION
                "The number of bytes in ICMP timestamp replies
                 that have been counted on this DLCI."
            ::= { tfrapPerfIcmpPerDlciEntry 22 }

      tfrapPerfIcmpPerDlciRxAddrMaskReq    OBJECT-TYPE
             SYNTAX      Counter
             ACCESS      read-only
             STATUS      mandatory
             DESCRIPTION
                "The number of bytes in ICMP address mask requests
                 that have been counted on this DLCI."
            ::= { tfrapPerfIcmpPerDlciEntry 23 }

      tfrapPerfIcmpPerDlciTxAddrMaskReq    OBJECT-TYPE
             SYNTAX      Counter
             ACCESS      read-only
             STATUS      mandatory
             DESCRIPTION
                "The number of bytes in ICMP address mask requests
                 that have been counted on this DLCI."
            ::= { tfrapPerfIcmpPerDlciEntry 24 }

      tfrapPerfIcmpPerDlciRxAddrMaskRep    OBJECT-TYPE
             SYNTAX      Counter
             ACCESS      read-only
             STATUS      mandatory
             DESCRIPTION
                "The number of bytes in ICMP address mask replies
                 that have been counted on this DLCI."
            ::= { tfrapPerfIcmpPerDlciEntry 25 }

      tfrapPerfIcmpPerDlciTxAddrMaskRep    OBJECT-TYPE
             SYNTAX      Counter
             ACCESS      read-only
             STATUS      mandatory
             DESCRIPTION
                "The number of bytes in ICMP address mask replies
                 that have been counted on this DLCI."
            ::= { tfrapPerfIcmpPerDlciEntry 26 }

      tfrapPerfIcmpPerDlciRxPktTooBig    OBJECT-TYPE
             SYNTAX      Counter
             ACCESS      read-only
             STATUS      mandatory
             DESCRIPTION
                "The number of bytes in ICMP packet too bigs
                 that have been counted on this DLCI."
            ::= { tfrapPerfIcmpPerDlciEntry 27 }

      tfrapPerfIcmpPerDlciTxPktTooBig    OBJECT-TYPE
             SYNTAX      Counter
             ACCESS      read-only
             STATUS      mandatory
             DESCRIPTION
                "The number of bytes in ICMP packet too bigs
                 that have been counted on this DLCI."
            ::= { tfrapPerfIcmpPerDlciEntry 28 }

      tfrapPerfIcmpPerDlciRxGmQuery    OBJECT-TYPE
             SYNTAX      Counter
             ACCESS      read-only
             STATUS      mandatory
             DESCRIPTION
                "The number of bytes in ICMP group membership
                 queries that have been counted on this DLCI."
            ::= { tfrapPerfIcmpPerDlciEntry 29 }

      tfrapPerfIcmpPerDlciTxGmQuery    OBJECT-TYPE
             SYNTAX      Counter
             ACCESS      read-only
             STATUS      mandatory
             DESCRIPTION
                "The number of bytes in ICMP group membership
                 queries that have been counted on this DLCI."
            ::= { tfrapPerfIcmpPerDlciEntry 30 }

      tfrapPerfIcmpPerDlciRxGmReport    OBJECT-TYPE
             SYNTAX      Counter
             ACCESS      read-only
             STATUS      mandatory
             DESCRIPTION
                "The number of bytes in ICMP group membership
                 reports that have been counted on this DLCI."
            ::= { tfrapPerfIcmpPerDlciEntry 31 }

      tfrapPerfIcmpPerDlciTxGmReport    OBJECT-TYPE
             SYNTAX      Counter
             ACCESS      read-only
             STATUS      mandatory
             DESCRIPTION
                "The number of bytes in ICMP group membership
                 reports that have been counted on this DLCI."
            ::= { tfrapPerfIcmpPerDlciEntry 32 }

      tfrapPerfIcmpPerDlciRxGmReduct    OBJECT-TYPE
             SYNTAX      Counter
             ACCESS      read-only
             STATUS      mandatory
             DESCRIPTION
                "The number of bytes in ICMP group membership
                 reductions that have been counted on this DLCI."
            ::= { tfrapPerfIcmpPerDlciEntry 33 }

      tfrapPerfIcmpPerDlciTxGmReduct    OBJECT-TYPE
             SYNTAX      Counter
             ACCESS      read-only
             STATUS      mandatory
             DESCRIPTION
                "The number of bytes in ICMP group membership
                 reductions that have been counted on this DLCI."
            ::= { tfrapPerfIcmpPerDlciEntry 34 }


   --  ICMP Short Term Statistics totals.

   tfrapPerfIcmpTotalTable OBJECT-TYPE
         SYNTAX   SEQUENCE OF TfrapPerfIcmpTotalEntry
         ACCESS   not-accessible
         STATUS   mandatory
         DESCRIPTION
            "Short Term Statistics on the ICMP
             protocol across all DLCIs."
         ::= { tfrapPerfNetworkShortTerm 6 }

         tfrapPerfIcmpTotalEntry OBJECT-TYPE
             SYNTAX   TfrapPerfIcmpTotalEntry
             ACCESS   not-accessible
             STATUS   mandatory
             DESCRIPTION
                "The ICMP Short Term Statistics for a particular DLCI."
            INDEX { tfrapPerfIcmpTotalInterval }
            ::= { tfrapPerfIcmpTotalTable 1 }

         TfrapPerfIcmpTotalEntry ::=
             SEQUENCE {
                 tfrapPerfIcmpTotalInterval        INTEGER,
                 tfrapPerfIcmpTotalRxTotal         Counter,
                 tfrapPerfIcmpTotalTxTotal         Counter,
                 tfrapPerfIcmpTotalRxEchoRep       Counter,
                 tfrapPerfIcmpTotalTxEchoRep       Counter,
                 tfrapPerfIcmpTotalRxDestUnr       Counter,
                 tfrapPerfIcmpTotalTxDestUnr       Counter,
                 tfrapPerfIcmpTotalRxSrcQuench     Counter,
                 tfrapPerfIcmpTotalTxSrcQuench     Counter,
                 tfrapPerfIcmpTotalRxRedirect      Counter,
                 tfrapPerfIcmpTotalTxRedirect      Counter,
                 tfrapPerfIcmpTotalRxEchoReq       Counter,
                 tfrapPerfIcmpTotalTxEchoReq       Counter,
                 tfrapPerfIcmpTotalRxTimeExcd      Counter,
                 tfrapPerfIcmpTotalTxTimeExcd      Counter,
                 tfrapPerfIcmpTotalRxParamProb     Counter,
                 tfrapPerfIcmpTotalTxParamProb     Counter,
                 tfrapPerfIcmpTotalRxTimestpReq    Counter,
                 tfrapPerfIcmpTotalTxTimestpReq    Counter,
                 tfrapPerfIcmpTotalRxTimestpRep    Counter,
                 tfrapPerfIcmpTotalTxTimestpRep    Counter,
                 tfrapPerfIcmpTotalRxAddrMaskReq   Counter,
                 tfrapPerfIcmpTotalTxAddrMaskReq   Counter,
                 tfrapPerfIcmpTotalRxAddrMaskRep   Counter,
                 tfrapPerfIcmpTotalTxAddrMaskRep   Counter,
                 tfrapPerfIcmpTotalRxPktTooBig     Counter,
                 tfrapPerfIcmpTotalTxPktTooBig     Counter,
                 tfrapPerfIcmpTotalRxGmQuery       Counter,
                 tfrapPerfIcmpTotalTxGmQuery       Counter,
                 tfrapPerfIcmpTotalRxGmReport      Counter,
                 tfrapPerfIcmpTotalTxGmReport      Counter,
                 tfrapPerfIcmpTotalRxGmReduct      Counter,
                 tfrapPerfIcmpTotalTxGmReduct      Counter
             }

      tfrapPerfIcmpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfIcmpTotalEntry 1 }

      tfrapPerfIcmpTotalRxTotal    OBJECT-TYPE
             SYNTAX      Counter
             ACCESS      read-only
             STATUS      mandatory
             DESCRIPTION
                "The total number of ICMP bytes that have been
                 counted across all DLCIs."
            ::= { tfrapPerfIcmpTotalEntry 3 }

      tfrapPerfIcmpTotalTxTotal    OBJECT-TYPE
             SYNTAX      Counter
             ACCESS      read-only
               STATUS      mandatory
             DESCRIPTION
                "The total number of ICMP bytes that have been
                 counted across all DLCIs."
            ::= { tfrapPerfIcmpTotalEntry 4 }

      tfrapPerfIcmpTotalRxEchoRep    OBJECT-TYPE
             SYNTAX      Counter
             ACCESS      read-only
             STATUS      mandatory
             DESCRIPTION
                "The number of bytes in ICMP ECHO repies
                 that have been counted across all DLCIs."
            ::= { tfrapPerfIcmpTotalEntry 5 }

      tfrapPerfIcmpTotalTxEchoRep    OBJECT-TYPE
             SYNTAX      Counter
             ACCESS      read-only
               STATUS      mandatory
             DESCRIPTION
                "The number of bytes in ICMP ECHO repies
                 that have been counted across all DLCIs."
            ::= { tfrapPerfIcmpTotalEntry 6 }

      tfrapPerfIcmpTotalRxDestUnr    OBJECT-TYPE
             SYNTAX      Counter
             ACCESS      read-only
             STATUS      mandatory
             DESCRIPTION
                "The number of bytes in ICMP destination unreachables
                 that have been counted across all DLCIs."
            ::= { tfrapPerfIcmpTotalEntry 7 }

      tfrapPerfIcmpTotalTxDestUnr    OBJECT-TYPE
             SYNTAX      Counter
             ACCESS      read-only
               STATUS      mandatory
             DESCRIPTION
                "The number of bytes in ICMP destination unreachables
                 that have been counted across all DLCIs."
            ::= { tfrapPerfIcmpTotalEntry 8 }

      tfrapPerfIcmpTotalRxSrcQuench    OBJECT-TYPE
             SYNTAX      Counter
             ACCESS      read-only
             STATUS      mandatory
             DESCRIPTION
                "The number of bytes in ICMP source quenches
                 that have been counted across all DLCIs."
            ::= { tfrapPerfIcmpTotalEntry 9 }

      tfrapPerfIcmpTotalTxSrcQuench    OBJECT-TYPE
             SYNTAX      Counter
             ACCESS      read-only
             STATUS      mandatory
             DESCRIPTION
                "The number of bytes in ICMP source quenches
                 that have been counte across all DLCIs."
            ::= { tfrapPerfIcmpTotalEntry 10 }

      tfrapPerfIcmpTotalRxRedirect    OBJECT-TYPE
             SYNTAX      Counter
             ACCESS      read-only
             STATUS      mandatory
             DESCRIPTION
                "The number of bytes in ICMP redirects
                 that have been counte across all DLCIs."
            ::= { tfrapPerfIcmpTotalEntry 11 }

      tfrapPerfIcmpTotalTxRedirect    OBJECT-TYPE
             SYNTAX      Counter
             ACCESS      read-only
             STATUS      mandatory
             DESCRIPTION
                "The number of bytes in ICMP redirects
                 that have been counte across all DLCIs."
            ::= { tfrapPerfIcmpTotalEntry 12 }

      tfrapPerfIcmpTotalRxEchoReq    OBJECT-TYPE
             SYNTAX      Counter
             ACCESS      read-only
             STATUS      mandatory
             DESCRIPTION
                "The number of bytes in ICMP ECHO requests
                 that have been counte across all DLCIs."
            ::= { tfrapPerfIcmpTotalEntry 13 }

      tfrapPerfIcmpTotalTxEchoReq    OBJECT-TYPE
             SYNTAX      Counter
             ACCESS      read-only
             STATUS      mandatory
             DESCRIPTION
                "The number of bytes in ICMP ECHO requests
                 that have been counte across all DLCIs."
            ::= { tfrapPerfIcmpTotalEntry 14 }

      tfrapPerfIcmpTotalRxTimeExcd    OBJECT-TYPE
             SYNTAX      Counter
             ACCESS      read-only
             STATUS      mandatory
             DESCRIPTION
                "The number of bytes in ICMP time exceededs
                 that have been counte across all DLCIs."
            ::= { tfrapPerfIcmpTotalEntry 15 }

      tfrapPerfIcmpTotalTxTimeExcd    OBJECT-TYPE
             SYNTAX      Counter
             ACCESS      read-only
             STATUS      mandatory
             DESCRIPTION
                "The number of bytes in ICMP time exceededs
                 that have been counte across all DLCIs."
            ::= { tfrapPerfIcmpTotalEntry 16 }

      tfrapPerfIcmpTotalRxParamProb    OBJECT-TYPE
             SYNTAX      Counter
             ACCESS      read-only
             STATUS      mandatory
             DESCRIPTION
                "The number of bytes in ICMP parameter problems
                 that have been counte across all DLCIs."
            ::= { tfrapPerfIcmpTotalEntry 17 }

      tfrapPerfIcmpTotalTxParamProb    OBJECT-TYPE
             SYNTAX      Counter
             ACCESS      read-only
             STATUS      mandatory
             DESCRIPTION
                "The number of bytes in ICMP parameter problems
                 that have been counte across all DLCIs."
            ::= { tfrapPerfIcmpTotalEntry 18 }

      tfrapPerfIcmpTotalRxTimestpReq    OBJECT-TYPE
             SYNTAX      Counter
             ACCESS      read-only
             STATUS      mandatory
             DESCRIPTION
                "The number of bytes in ICMP timestamp requests
                 that have been counte across all DLCIs."
            ::= { tfrapPerfIcmpTotalEntry 19 }

      tfrapPerfIcmpTotalTxTimestpReq    OBJECT-TYPE
             SYNTAX      Counter
             ACCESS      read-only
             STATUS      mandatory
             DESCRIPTION
                "The number of bytes in ICMP timestamp requests
                 that have been counte across all DLCIs."
            ::= { tfrapPerfIcmpTotalEntry 20 }

      tfrapPerfIcmpTotalRxTimestpRep    OBJECT-TYPE
             SYNTAX      Counter
             ACCESS      read-only
             STATUS      mandatory
             DESCRIPTION
                "The number of bytes in ICMP timestamp replies
                 that have been counted across all DLCIs."
            ::= { tfrapPerfIcmpTotalEntry 21 }

      tfrapPerfIcmpTotalTxTimestpRep    OBJECT-TYPE
             SYNTAX      Counter
             ACCESS      read-only
             STATUS      mandatory
             DESCRIPTION
                "The number of bytes in ICMP timestamp replies
                 that have been counte across all DLCIs."
            ::= { tfrapPerfIcmpTotalEntry 22 }

      tfrapPerfIcmpTotalRxAddrMaskReq    OBJECT-TYPE
             SYNTAX      Counter
             ACCESS      read-only
             STATUS      mandatory
             DESCRIPTION
                "The number of bytes in ICMP address mask requests
                 that have been counte across all DLCIs."
            ::= { tfrapPerfIcmpTotalEntry 23 }

      tfrapPerfIcmpTotalTxAddrMaskReq    OBJECT-TYPE
             SYNTAX      Counter
             ACCESS      read-only
             STATUS      mandatory
             DESCRIPTION
                "The number of bytes in ICMP address mask requests
                 that have been counte across all DLCIs."
            ::= { tfrapPerfIcmpTotalEntry 24 }

      tfrapPerfIcmpTotalRxAddrMaskRep    OBJECT-TYPE
             SYNTAX      Counter
             ACCESS      read-only
             STATUS      mandatory
             DESCRIPTION
                "The number of bytes in ICMP address mask replies
                 that have been counte across all DLCIs."
            ::= { tfrapPerfIcmpTotalEntry 25 }

      tfrapPerfIcmpTotalTxAddrMaskRep    OBJECT-TYPE
             SYNTAX      Counter
             ACCESS      read-only
             STATUS      mandatory
             DESCRIPTION
                "The number of bytes in ICMP address mask replies
                 that have been counte across all DLCIs."
            ::= { tfrapPerfIcmpTotalEntry 26 }

      tfrapPerfIcmpTotalRxPktTooBig    OBJECT-TYPE
             SYNTAX      Counter
             ACCESS      read-only
             STATUS      mandatory
             DESCRIPTION
                "The number of bytes in ICMP packet too bigs
                 that have been counte across all DLCIs."
            ::= { tfrapPerfIcmpTotalEntry 27 }

      tfrapPerfIcmpTotalTxPktTooBig    OBJECT-TYPE
             SYNTAX      Counter
             ACCESS      read-only
             STATUS      mandatory
             DESCRIPTION
                "The number of bytes in ICMP packet too bigs
                 that have been counte across all DLCIs."
            ::= { tfrapPerfIcmpTotalEntry 28 }

      tfrapPerfIcmpTotalRxGmQuery    OBJECT-TYPE
             SYNTAX      Counter
             ACCESS      read-only
             STATUS      mandatory
             DESCRIPTION
                "The number of bytes in ICMP group membership
                 queries that have been counte across all DLCIs."
            ::= { tfrapPerfIcmpTotalEntry 29 }

      tfrapPerfIcmpTotalTxGmQuery    OBJECT-TYPE
             SYNTAX      Counter
             ACCESS      read-only
             STATUS      mandatory
             DESCRIPTION
                "The number of bytes in ICMP group membership
                 queries that have been counte across all DLCIs."
            ::= { tfrapPerfIcmpTotalEntry 30 }

      tfrapPerfIcmpTotalRxGmReport    OBJECT-TYPE
             SYNTAX      Counter
             ACCESS      read-only
             STATUS      mandatory
             DESCRIPTION
                "The number of bytes in ICMP group membership
                 reports that have been counte across all DLCIs."
            ::= { tfrapPerfIcmpTotalEntry 31 }

      tfrapPerfIcmpTotalTxGmReport    OBJECT-TYPE
             SYNTAX      Counter
             ACCESS      read-only
             STATUS      mandatory
             DESCRIPTION
                "The number of bytes in ICMP group membership
                 reports that have been counte across all DLCIs."
            ::= { tfrapPerfIcmpTotalEntry 32 }

      tfrapPerfIcmpTotalRxGmReduct    OBJECT-TYPE
             SYNTAX      Counter
             ACCESS      read-only
             STATUS      mandatory
             DESCRIPTION
                "The number of bytes in ICMP group membership
                 reductions that have been counte across all DLCIs."
            ::= { tfrapPerfIcmpTotalEntry 33 }

      tfrapPerfIcmpTotalTxGmReduct    OBJECT-TYPE
             SYNTAX      Counter
             ACCESS      read-only
             STATUS      mandatory
             DESCRIPTION
                "The number of bytes in ICMP group membership
                 reductions that have been counte across all DLCIs."
            ::= { tfrapPerfIcmpTotalEntry 34 }

   --  Application-level Short Term Statistics for each DLCI.

   tfrapPerfApplicationPerDlciTable OBJECT-TYPE
         SYNTAX   SEQUENCE OF TfrapPerfApplicationPerDlciEntry
         ACCESS   not-accessible
         STATUS   mandatory
         DESCRIPTION
            "The Short Term Statistics on the Application
            protocol for each DLCI."
         ::= { tfrapPerfNetworkShortTerm 7 }

         tfrapPerfApplicationPerDlciEntry OBJECT-TYPE
             SYNTAX   TfrapPerfApplicationPerDlciEntry
             ACCESS   not-accessible
             STATUS   mandatory
             DESCRIPTION
                "The Application Short Term Statistics for a particular DLCI."
            INDEX { tfrapPerfApplicationPerDlciInterval, 
                    tfrapPerfApplicationPerDlciValue }
            ::= { tfrapPerfApplicationPerDlciTable 1 }

         TfrapPerfApplicationPerDlciEntry ::=
             SEQUENCE {
                 tfrapPerfApplicationPerDlciInterval   INTEGER,
                 tfrapPerfApplicationPerDlciValue      INTEGER,
                 tfrapPerfApplicationPerDlciRxSnmp     Counter,
                 tfrapPerfApplicationPerDlciTxSnmp     Counter,
                 tfrapPerfApplicationPerDlciRxSnmpTrap Counter,
                 tfrapPerfApplicationPerDlciTxSnmpTrap Counter,
                 tfrapPerfApplicationPerDlciRxHttp     Counter,
                 tfrapPerfApplicationPerDlciTxHttp     Counter,
                 tfrapPerfApplicationPerDlciRxTelnet   Counter,
                 tfrapPerfApplicationPerDlciTxTelnet   Counter,
                 tfrapPerfApplicationPerDlciRxSmtp     Counter,
                 tfrapPerfApplicationPerDlciTxSmtp     Counter,
                 tfrapPerfApplicationPerDlciRxFtp      Counter,
                 tfrapPerfApplicationPerDlciTxFtp      Counter,
                 tfrapPerfApplicationPerDlciRxTftp     Counter,
                 tfrapPerfApplicationPerDlciTxTftp     Counter,
                 tfrapPerfApplicationPerDlciRxCustom1  Counter,
                 tfrapPerfApplicationPerDlciTxCustom1  Counter,
                 tfrapPerfApplicationPerDlciRxCustom2  Counter,
                 tfrapPerfApplicationPerDlciTxCustom2  Counter,
                 tfrapPerfApplicationPerDlciRxCustom3  Counter,
                 tfrapPerfApplicationPerDlciTxCustom3  Counter,
                 tfrapPerfApplicationPerDlciRxCustom4  Counter,
                 tfrapPerfApplicationPerDlciTxCustom4  Counter
             }

      tfrapPerfApplicationPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfApplicationPerDlciEntry 1 }

      tfrapPerfApplicationPerDlciValue    OBJECT-TYPE
             SYNTAX      INTEGER 
             ACCESS      read-only
             STATUS      mandatory
             DESCRIPTION
                "The DLCI value with which the Statistics are associated."
            ::= { tfrapPerfApplicationPerDlciEntry 2 }

      tfrapPerfApplicationPerDlciRxSnmp    OBJECT-TYPE
             SYNTAX      Counter
             ACCESS      read-only
             STATUS      mandatory
             DESCRIPTION
                "The number of received SNMP bytes
                 that have been counted on this DLCI."
            ::= { tfrapPerfApplicationPerDlciEntry 3 }

      tfrapPerfApplicationPerDlciTxSnmp    OBJECT-TYPE
             SYNTAX      Counter
             ACCESS      read-only
             STATUS      mandatory
             DESCRIPTION
                "The number of transmitted SNMP bytes
                 that have been counted on this DLCI."
            ::= { tfrapPerfApplicationPerDlciEntry 4 }

      tfrapPerfApplicationPerDlciRxSnmpTrap    OBJECT-TYPE
             SYNTAX      Counter
             ACCESS      read-only
             STATUS      mandatory
             DESCRIPTION
                "The number of received SNMP TRAP bytes
                 that have been counted on this DLCI."
            ::= { tfrapPerfApplicationPerDlciEntry 5 }

      tfrapPerfApplicationPerDlciTxSnmpTrap    OBJECT-TYPE
             SYNTAX      Counter
             ACCESS      read-only
             STATUS      mandatory
             DESCRIPTION
                "The number of transmitted SNMP TRAP bytes
                 that have been counted on this DLCI."
            ::= { tfrapPerfApplicationPerDlciEntry 6 }

      tfrapPerfApplicationPerDlciRxHttp    OBJECT-TYPE
             SYNTAX      Counter
             ACCESS      read-only
             STATUS      mandatory
             DESCRIPTION
                "The number of received HTTP bytes
                 that have been counted on this DLCI."
            ::= { tfrapPerfApplicationPerDlciEntry 7 }

      tfrapPerfApplicationPerDlciTxHttp    OBJECT-TYPE
             SYNTAX      Counter
             ACCESS      read-only
             STATUS      mandatory
             DESCRIPTION
                "The number of transmitted HTTP bytes
                 that have been counted on this DLCI."
            ::= { tfrapPerfApplicationPerDlciEntry 8 }

      tfrapPerfApplicationPerDlciRxTelnet    OBJECT-TYPE
             SYNTAX      Counter
             ACCESS      read-only
             STATUS      mandatory
             DESCRIPTION
                "The number of received Telnet bytes
                 that have been counted on this DLCI."
            ::= { tfrapPerfApplicationPerDlciEntry 9 }

      tfrapPerfApplicationPerDlciTxTelnet    OBJECT-TYPE
             SYNTAX      Counter
             ACCESS      read-only
             STATUS      mandatory
             DESCRIPTION
                "The number of transmitted Telnet bytes
                 that have been counted on this DLCI."
            ::= { tfrapPerfApplicationPerDlciEntry 10 }

      tfrapPerfApplicationPerDlciRxSmtp    OBJECT-TYPE
             SYNTAX      Counter
             ACCESS      read-only
             STATUS      mandatory
             DESCRIPTION
                "The number of received SMTP bytes
                 that have been counted on this DLCI."
            ::= { tfrapPerfApplicationPerDlciEntry 11 }

      tfrapPerfApplicationPerDlciTxSmtp    OBJECT-TYPE
             SYNTAX      Counter
             ACCESS      read-only
             STATUS      mandatory
             DESCRIPTION
                "The number of transmitted SMTP bytes
                 that have been counted on this DLCI."
            ::= { tfrapPerfApplicationPerDlciEntry 12 }

      tfrapPerfApplicationPerDlciRxFtp    OBJECT-TYPE
             SYNTAX      Counter
             ACCESS      read-only
             STATUS      mandatory
             DESCRIPTION
                "The number of received FTP bytes
                 that have been counted on this DLCI."
            ::= { tfrapPerfApplicationPerDlciEntry 13 }

      tfrapPerfApplicationPerDlciTxFtp    OBJECT-TYPE
             SYNTAX      Counter
             ACCESS      read-only
             STATUS      mandatory
             DESCRIPTION
                "The number of transmitted FTP bytes
                 that have been counted on this DLCI."
            ::= { tfrapPerfApplicationPerDlciEntry 14 }

      tfrapPerfApplicationPerDlciRxTftp    OBJECT-TYPE
             SYNTAX      Counter
             ACCESS      read-only
             STATUS      mandatory
             DESCRIPTION
                "The number of received TFTP bytes
                 that have been counted on this DLCI."
            ::= { tfrapPerfApplicationPerDlciEntry 15 }

      tfrapPerfApplicationPerDlciTxTftp    OBJECT-TYPE
             SYNTAX      Counter
             ACCESS      read-only
             STATUS      mandatory
             DESCRIPTION
                "The number of transmitted TFTP bytes
                 that have been counted on this DLCI."
            ::= { tfrapPerfApplicationPerDlciEntry 16 }

      tfrapPerfApplicationPerDlciRxCustom1    OBJECT-TYPE
             SYNTAX      Counter
             ACCESS      read-only
             STATUS      mandatory
             DESCRIPTION
                "The number of received bytes of
                 User Defined Protocol #1 that have
                 been counted on this DLCI."
            ::= { tfrapPerfApplicationPerDlciEntry 17 }

      tfrapPerfApplicationPerDlciTxCustom1    OBJECT-TYPE
             SYNTAX      Counter
             ACCESS      read-only
             STATUS      mandatory
             DESCRIPTION
                "The number of transmitted bytes of
                 User Defined Protocol #1 that have
                 been counted on this DLCI."
            ::= { tfrapPerfApplicationPerDlciEntry 18 }

      tfrapPerfApplicationPerDlciRxCustom2    OBJECT-TYPE
             SYNTAX      Counter
             ACCESS      read-only
             STATUS      mandatory
             DESCRIPTION
                "The number of received bytes of
                 User Defined Protocol #2 that have
                 been counted on this DLCI."
            ::= { tfrapPerfApplicationPerDlciEntry 19 }

      tfrapPerfApplicationPerDlciTxCustom2    OBJECT-TYPE
             SYNTAX      Counter
             ACCESS      read-only
             STATUS      mandatory
             DESCRIPTION
                "The number of transmitted bytes of
                 User Defined Protocol #2 that have
                 been counted on this DLCI."
            ::= { tfrapPerfApplicationPerDlciEntry 20 }

      tfrapPerfApplicationPerDlciRxCustom3    OBJECT-TYPE
             SYNTAX      Counter
             ACCESS      read-only
             STATUS      mandatory
             DESCRIPTION
                "The number of received bytes of
                 User Defined Protocol #3 that have
                 been counted on this DLCI."
            ::= { tfrapPerfApplicationPerDlciEntry 21 }

      tfrapPerfApplicationPerDlciTxCustom3    OBJECT-TYPE
             SYNTAX      Counter
             ACCESS      read-only
             STATUS      mandatory
             DESCRIPTION
                "The number of transmitted bytes of
                 User Defined Protocol #3 that have
                 been counted on this DLCI."
            ::= { tfrapPerfApplicationPerDlciEntry 22 }

      tfrapPerfApplicationPerDlciRxCustom4    OBJECT-TYPE
             SYNTAX      Counter
             ACCESS      read-only
             STATUS      mandatory
             DESCRIPTION
                "The number of received bytes of
                 User Defined Protocol #4 that have
                 been counted on this DLCI."
            ::= { tfrapPerfApplicationPerDlciEntry 23 }

      tfrapPerfApplicationPerDlciTxCustom4    OBJECT-TYPE
             SYNTAX      Counter
             ACCESS      read-only
             STATUS      mandatory
             DESCRIPTION
                "The number of transmitted bytes of
                 User Defined Protocol #4 that have
                 been counted on this DLCI."
            ::= { tfrapPerfApplicationPerDlciEntry 24 }



   --  Application-level Short Term Statistics totals.

   tfrapPerfApplicationTotalTable OBJECT-TYPE
         SYNTAX   SEQUENCE OF TfrapPerfApplicationTotalEntry
         ACCESS   not-accessible
         STATUS   mandatory
         DESCRIPTION
            "The Short Term Statistics on the Application
            protocol across all DLCIs."
         ::= { tfrapPerfNetworkShortTerm 8 }

         tfrapPerfApplicationTotalEntry OBJECT-TYPE
             SYNTAX   TfrapPerfApplicationTotalEntry
             ACCESS   not-accessible
             STATUS   mandatory
             DESCRIPTION
                "The Application Short Term Statistics for a particular DLCI."
            INDEX { tfrapPerfApplicationTotalInterval }
            ::= { tfrapPerfApplicationTotalTable 1 }

         TfrapPerfApplicationTotalEntry ::=
             SEQUENCE {
                 tfrapPerfApplicationTotalInterval   INTEGER,
                 tfrapPerfApplicationTotalRxSnmp     Counter,
                 tfrapPerfApplicationTotalTxSnmp     Counter,
                 tfrapPerfApplicationTotalRxSnmpTrap Counter,
                 tfrapPerfApplicationTotalTxSnmpTrap Counter,
                 tfrapPerfApplicationTotalRxHttp     Counter,
                 tfrapPerfApplicationTotalTxHttp     Counter,
                 tfrapPerfApplicationTotalRxTelnet   Counter,
                 tfrapPerfApplicationTotalTxTelnet   Counter,
                 tfrapPerfApplicationTotalRxSmtp     Counter,
                 tfrapPerfApplicationTotalTxSmtp     Counter,
                 tfrapPerfApplicationTotalRxFtp      Counter,
                 tfrapPerfApplicationTotalTxFtp      Counter,
                 tfrapPerfApplicationTotalRxTftp     Counter,
                 tfrapPerfApplicationTotalTxTftp     Counter,
                 tfrapPerfApplicationTotalRxCustom1  Counter,
                 tfrapPerfApplicationTotalTxCustom1  Counter,
                 tfrapPerfApplicationTotalRxCustom2  Counter,
                 tfrapPerfApplicationTotalTxCustom2  Counter,
                 tfrapPerfApplicationTotalRxCustom3  Counter,
                 tfrapPerfApplicationTotalTxCustom3  Counter,
                 tfrapPerfApplicationTotalRxCustom4  Counter,
                 tfrapPerfApplicationTotalTxCustom4  Counter
             }

      tfrapPerfApplicationTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfApplicationTotalEntry 1 }

      tfrapPerfApplicationTotalRxSnmp    OBJECT-TYPE
             SYNTAX      Counter
             ACCESS      read-only
             STATUS      mandatory
             DESCRIPTION
                "The number of received SNMP bytes
                 that have been counted across all DLCIs."
            ::= { tfrapPerfApplicationTotalEntry 3 }

      tfrapPerfApplicationTotalTxSnmp    OBJECT-TYPE
             SYNTAX      Counter
             ACCESS      read-only
             STATUS      mandatory
             DESCRIPTION
                "The number of transmitted SNMP bytes
                 that have been counted across all DLCIs."
            ::= { tfrapPerfApplicationTotalEntry 4 }

      tfrapPerfApplicationTotalRxSnmpTrap    OBJECT-TYPE
             SYNTAX      Counter
             ACCESS      read-only
             STATUS      mandatory
             DESCRIPTION
                "The number of received SNMP TRAP bytes
                 that have been counted across all DLCIs."
            ::= { tfrapPerfApplicationTotalEntry 5 }

      tfrapPerfApplicationTotalTxSnmpTrap    OBJECT-TYPE
             SYNTAX      Counter
             ACCESS      read-only
             STATUS      mandatory
             DESCRIPTION
                "The number of transmitted SNMP TRAP bytes
                 that have been counted across all DLCIs."
            ::= { tfrapPerfApplicationTotalEntry 6 }

      tfrapPerfApplicationTotalRxHttp    OBJECT-TYPE
             SYNTAX      Counter
             ACCESS      read-only
             STATUS      mandatory
             DESCRIPTION
                "The number of received HTTP bytes
                 that have been counted across all DLCIs."
            ::= { tfrapPerfApplicationTotalEntry 7 }

      tfrapPerfApplicationTotalTxHttp    OBJECT-TYPE
             SYNTAX      Counter
             ACCESS      read-only
             STATUS      mandatory
             DESCRIPTION
                "The number of transmitted HTTP bytes
                 that have been counted across all DLCIs."
            ::= { tfrapPerfApplicationTotalEntry 8 }

      tfrapPerfApplicationTotalRxTelnet    OBJECT-TYPE
             SYNTAX      Counter
             ACCESS      read-only
             STATUS      mandatory
             DESCRIPTION
                "The number of received Telnet bytes
                 that have been counted across all DLCIs."
            ::= { tfrapPerfApplicationTotalEntry 9 }

      tfrapPerfApplicationTotalTxTelnet    OBJECT-TYPE
             SYNTAX      Counter
             ACCESS      read-only
             STATUS      mandatory
             DESCRIPTION
                "The number of transmitted Telnet bytes
                 that have been counted across all DLCIs."
            ::= { tfrapPerfApplicationTotalEntry 10 }

      tfrapPerfApplicationTotalRxSmtp    OBJECT-TYPE
             SYNTAX      Counter
             ACCESS      read-only
             STATUS      mandatory
             DESCRIPTION
                "The number of received SMTP bytes
                 that have been counted across all DLCIs."
            ::= { tfrapPerfApplicationTotalEntry 11 }

      tfrapPerfApplicationTotalTxSmtp    OBJECT-TYPE
             SYNTAX      Counter
             ACCESS      read-only
             STATUS      mandatory
             DESCRIPTION
                "The number of transmitted SMTP bytes
                 that have been counted across all DLCIs."
            ::= { tfrapPerfApplicationTotalEntry 12 }

      tfrapPerfApplicationTotalRxFtp    OBJECT-TYPE
             SYNTAX      Counter
             ACCESS      read-only
             STATUS      mandatory
             DESCRIPTION
                "The number of received FTP bytes
                 that have been counted across all DLCIs."
            ::= { tfrapPerfApplicationTotalEntry 13 }

      tfrapPerfApplicationTotalTxFtp    OBJECT-TYPE
             SYNTAX      Counter
             ACCESS      read-only
             STATUS      mandatory
             DESCRIPTION
                "The number of transmitted FTP bytes
                 that have been counted across all DLCIs."
            ::= { tfrapPerfApplicationTotalEntry 14 }

      tfrapPerfApplicationTotalRxTftp    OBJECT-TYPE
             SYNTAX      Counter
             ACCESS      read-only
             STATUS      mandatory
             DESCRIPTION
                "The number of received TFTP bytes
                 that have been counted across all DLCIs."
            ::= { tfrapPerfApplicationTotalEntry 15 }

      tfrapPerfApplicationTotalTxTftp    OBJECT-TYPE
             SYNTAX      Counter
             ACCESS      read-only
             STATUS      mandatory
             DESCRIPTION
                "The number of transmitted TFTP bytes
                 that have been counted across all DLCIs."
            ::= { tfrapPerfApplicationTotalEntry 16 }

      tfrapPerfApplicationTotalRxCustom1    OBJECT-TYPE
             SYNTAX      Counter
             ACCESS      read-only
             STATUS      mandatory
             DESCRIPTION
                "The number of received bytes of
                 User Defined Protocol #1 that have
                 been counted across all DLCIs."
            ::= { tfrapPerfApplicationTotalEntry 17 }

      tfrapPerfApplicationTotalTxCustom1    OBJECT-TYPE
             SYNTAX      Counter
             ACCESS      read-only
             STATUS      mandatory
             DESCRIPTION
                "The number of transmitted bytes of
                 User Defined Protocol #1 that have
                 been counted across all DLCIs."
            ::= { tfrapPerfApplicationTotalEntry 18 }

      tfrapPerfApplicationTotalRxCustom2    OBJECT-TYPE
             SYNTAX      Counter
             ACCESS      read-only
             STATUS      mandatory
             DESCRIPTION
                "The number of received bytes of
                 User Defined Protocol #2 that have
                 been counted across all DLCIs."
            ::= { tfrapPerfApplicationTotalEntry 19 }

      tfrapPerfApplicationTotalTxCustom2    OBJECT-TYPE
             SYNTAX      Counter
             ACCESS      read-only
             STATUS      mandatory
             DESCRIPTION
                "The number of transmitted bytes of
                 User Defined Protocol #2 that have
                 been counted across all DLCIs."
            ::= { tfrapPerfApplicationTotalEntry 20 }

      tfrapPerfApplicationTotalRxCustom3    OBJECT-TYPE
             SYNTAX      Counter
             ACCESS      read-only
             STATUS      mandatory
             DESCRIPTION
                "The number of received bytes of
                 User Defined Protocol #3 that have
                 been counted across all DLCIs."
            ::= { tfrapPerfApplicationTotalEntry 21 }

      tfrapPerfApplicationTotalTxCustom3    OBJECT-TYPE
             SYNTAX      Counter
             ACCESS      read-only
             STATUS      mandatory
             DESCRIPTION
                "The number of transmitted bytes of
                 User Defined Protocol #3 that have
                 been counted across all DLCIs."
            ::= { tfrapPerfApplicationTotalEntry 22 }

      tfrapPerfApplicationTotalRxCustom4    OBJECT-TYPE
             SYNTAX      Counter
             ACCESS      read-only
             STATUS      mandatory
             DESCRIPTION
                "The number of received bytes of
                 User Defined Protocol #4 that have
                 been counted across all DLCIs."
            ::= { tfrapPerfApplicationTotalEntry 23 }

      tfrapPerfApplicationTotalTxCustom4    OBJECT-TYPE
             SYNTAX      Counter
             ACCESS      read-only
             STATUS      mandatory
             DESCRIPTION
                "The number of transmitted bytes of
                 User Defined Protocol #4 that have
                 been counted across all DLCIs."
            ::= { tfrapPerfApplicationTotalEntry 24 }


   --  Routing Short Term Statistics for each DLCI.

   tfrapPerfRoutingPerDlciTable OBJECT-TYPE
         SYNTAX   SEQUENCE OF TfrapPerfRoutingPerDlciEntry
         ACCESS   not-accessible
         STATUS   mandatory
         DESCRIPTION
            "The Short Term Statistics on the Routing
            protocol for each DLCI."
         ::= { tfrapPerfNetworkShortTerm 9 }

         tfrapPerfRoutingPerDlciEntry OBJECT-TYPE
             SYNTAX   TfrapPerfRoutingPerDlciEntry
             ACCESS   not-accessible
             STATUS   mandatory
             DESCRIPTION
                "The Routing Short Term Statistics for a particular DLCI."
            INDEX { tfrapPerfRoutingPerDlciInterval,
                    tfrapPerfRoutingPerDlciValue }
            ::= { tfrapPerfRoutingPerDlciTable 1 }

         TfrapPerfRoutingPerDlciEntry ::=
             SEQUENCE {
                 tfrapPerfRoutingPerDlciInterval  INTEGER,
                 tfrapPerfRoutingPerDlciValue     INTEGER,
                 tfrapPerfRoutingPerDlciRxOspf    Counter,
                 tfrapPerfRoutingPerDlciTxOspf    Counter,
                 tfrapPerfRoutingPerDlciRxRip     Counter,
                 tfrapPerfRoutingPerDlciTxRip     Counter,
                 tfrapPerfRoutingPerDlciRxNetbios Counter,
                 tfrapPerfRoutingPerDlciTxNetbios Counter
             }

      tfrapPerfRoutingPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfRoutingPerDlciEntry 1 }

      tfrapPerfRoutingPerDlciValue    OBJECT-TYPE
             SYNTAX      INTEGER 
             ACCESS      read-only
             STATUS      mandatory
             DESCRIPTION
                "The DLCI value with which the Statistics are associated."
            ::= { tfrapPerfRoutingPerDlciEntry 2 }


      tfrapPerfRoutingPerDlciRxOspf    OBJECT-TYPE
             SYNTAX      Counter
             ACCESS      read-only
             STATUS      mandatory
             DESCRIPTION
                "The number of received OSPF bytes
                 that have been counted on this DLCI."
            ::= { tfrapPerfRoutingPerDlciEntry 3 }

      tfrapPerfRoutingPerDlciTxOspf    OBJECT-TYPE
             SYNTAX      Counter
             ACCESS      read-only
             STATUS      mandatory
             DESCRIPTION
                "The number of transmitted OSPF bytes
                 that have been counted on this DLCI."
            ::= { tfrapPerfRoutingPerDlciEntry 4 }

      tfrapPerfRoutingPerDlciRxRip    OBJECT-TYPE
             SYNTAX      Counter
             ACCESS      read-only
             STATUS      mandatory
             DESCRIPTION
                "The number of received RIP bytes
                 that have been counted on this DLCI."
            ::= { tfrapPerfRoutingPerDlciEntry 5 }

      tfrapPerfRoutingPerDlciTxRip    OBJECT-TYPE
             SYNTAX      Counter
             ACCESS      read-only
             STATUS      mandatory
             DESCRIPTION
                "The number of transmitted RIP bytes
                 that have been counted on this DLCI."
            ::= { tfrapPerfRoutingPerDlciEntry 6 }

      tfrapPerfRoutingPerDlciRxNetbios    OBJECT-TYPE
             SYNTAX      Counter
             ACCESS      read-only
             STATUS      mandatory
             DESCRIPTION
                "The number of received Netbios bytes
                 that have been counted on this DLCI."
            ::= { tfrapPerfRoutingPerDlciEntry 7 }

      tfrapPerfRoutingPerDlciTxNetbios    OBJECT-TYPE
             SYNTAX      Counter
             ACCESS      read-only
             STATUS      mandatory
             DESCRIPTION
                "The number of transmitted Netbios bytes
                 that have been counted on this DLCI."
            ::= { tfrapPerfRoutingPerDlciEntry 8 }


   --  Routing Short Term Statistics totals.

   tfrapPerfRoutingTotalTable OBJECT-TYPE
         SYNTAX   SEQUENCE OF TfrapPerfRoutingTotalEntry
         ACCESS   not-accessible
         STATUS   mandatory
         DESCRIPTION
            "The Short Term Statistics on the Routing
            protocol across all DLCIs."
         ::= { tfrapPerfNetworkShortTerm 10 }

         tfrapPerfRoutingTotalEntry OBJECT-TYPE
             SYNTAX   TfrapPerfRoutingTotalEntry
             ACCESS   not-accessible
             STATUS   mandatory
             DESCRIPTION
                "The Routing Short Term Statistics for a particular DLCI."
            INDEX { tfrapPerfRoutingTotalInterval }
            ::= { tfrapPerfRoutingTotalTable 1 }

         TfrapPerfRoutingTotalEntry ::=
             SEQUENCE {
                 tfrapPerfRoutingTotalInterval  INTEGER,
                 tfrapPerfRoutingTotalRxOspf    Counter,
                 tfrapPerfRoutingTotalTxOspf    Counter,
                 tfrapPerfRoutingTotalRxRip     Counter,
                 tfrapPerfRoutingTotalTxRip     Counter,
                 tfrapPerfRoutingTotalRxNetbios Counter,
                 tfrapPerfRoutingTotalTxNetbios Counter
             }

      tfrapPerfRoutingTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfRoutingTotalEntry 1 }

      tfrapPerfRoutingTotalRxOspf    OBJECT-TYPE
             SYNTAX      Counter 
             ACCESS      read-only
             STATUS      mandatory
             DESCRIPTION
                "The number of received OSPF bytes
                 that have been counted across all DLCIs."
            ::= { tfrapPerfRoutingTotalEntry 3 }

      tfrapPerfRoutingTotalTxOspf    OBJECT-TYPE
             SYNTAX      Counter
             ACCESS      read-only
             STATUS      mandatory
             DESCRIPTION
                "The number of transmitted OSPF bytes
                 that have been counted across all DLCIs."
            ::= { tfrapPerfRoutingTotalEntry 4 }

      tfrapPerfRoutingTotalRxRip    OBJECT-TYPE
             SYNTAX      Counter
             ACCESS      read-only
             STATUS      mandatory
             DESCRIPTION
                "The number of received RIP bytes
                 that have been counted across all DLCIs."
            ::= { tfrapPerfRoutingTotalEntry 5 }

      tfrapPerfRoutingTotalTxRip    OBJECT-TYPE
             SYNTAX      Counter
             ACCESS      read-only
             STATUS      mandatory
             DESCRIPTION
                "The number of transmitted RIP bytes
                 that have been counted across all DLCIs."
            ::= { tfrapPerfRoutingTotalEntry 6 }

      tfrapPerfRoutingTotalRxNetbios    OBJECT-TYPE
             SYNTAX      Counter
             ACCESS      read-only
             STATUS      mandatory
             DESCRIPTION
                "The number of received Netbios bytes
                 that have been counted across all DLCIs."
            ::= { tfrapPerfRoutingTotalEntry 7 }

      tfrapPerfRoutingTotalTxNetbios    OBJECT-TYPE
             SYNTAX      Counter
             ACCESS      read-only
             STATUS      mandatory
             DESCRIPTION
                "The number of transmitted Netbios bytes
                 that have been counted across all DLCIs."
            ::= { tfrapPerfRoutingTotalEntry 8 }



   --  IPX Short Term Statistics for each DLCI.

   tfrapPerfIpxPerDlciTable OBJECT-TYPE
         SYNTAX   SEQUENCE OF TfrapPerfIpxPerDlciEntry
         ACCESS   not-accessible
         STATUS   mandatory
         DESCRIPTION
            "Short Term Statistics on the IPX
             protocol for each DLCI."
         ::= { tfrapPerfNetworkShortTerm 11 }

         tfrapPerfIpxPerDlciEntry OBJECT-TYPE
             SYNTAX   TfrapPerfIpxPerDlciEntry
             ACCESS   not-accessible
             STATUS   mandatory
             DESCRIPTION
                "The IPX Short Term Statistics for a particular DLCI."
            INDEX { tfrapPerfIpxPerDlciInterval, tfrapPerfIpxPerDlciValue }
            ::= { tfrapPerfIpxPerDlciTable 1 }

         TfrapPerfIpxPerDlciEntry ::=
             SEQUENCE {
                 tfrapPerfIpxPerDlciInterval   INTEGER,
                 tfrapPerfIpxPerDlciValue      INTEGER,
                 tfrapPerfIpxPerDlciRxTotal    Counter,
                 tfrapPerfIpxPerDlciTxTotal    Counter,
                 tfrapPerfIpxPerDlciRxSpx      Counter,
                 tfrapPerfIpxPerDlciTxSpx      Counter,
                 tfrapPerfIpxPerDlciRxNcp      Counter,
                 tfrapPerfIpxPerDlciTxNcp      Counter,
                 tfrapPerfIpxPerDlciRxSap      Counter,
                 tfrapPerfIpxPerDlciTxSap      Counter,
                 tfrapPerfIpxPerDlciRxRip      Counter,
                 tfrapPerfIpxPerDlciTxRip      Counter,
                 tfrapPerfIpxPerDlciRxNetbios  Counter,
                 tfrapPerfIpxPerDlciTxNetbios  Counter,
                 tfrapPerfIpxPerDlciRxOther    Counter,
                 tfrapPerfIpxPerDlciTxOther    Counter
             }

      tfrapPerfIpxPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfIpxPerDlciEntry 1 }

      tfrapPerfIpxPerDlciValue    OBJECT-TYPE
             SYNTAX      INTEGER 
            ACCESS      read-only
             STATUS      mandatory
             DESCRIPTION
                "The DLCI value in which the Statistics are associated."
            ::= { tfrapPerfIpxPerDlciEntry 2 }

      tfrapPerfIpxPerDlciRxTotal    OBJECT-TYPE
             SYNTAX      Counter
             ACCESS      read-only
             STATUS      mandatory
             DESCRIPTION
                "The total number of IPX bytes
                 that have been counted on this DLCI."
            ::= { tfrapPerfIpxPerDlciEntry 3 }

      tfrapPerfIpxPerDlciTxTotal    OBJECT-TYPE
             SYNTAX      Counter
             ACCESS      read-only
             STATUS      mandatory
             DESCRIPTION
                "The total number of IPX bytes
                 that have been counted on this DLCI."
            ::= { tfrapPerfIpxPerDlciEntry 4 }

      tfrapPerfIpxPerDlciRxSpx    OBJECT-TYPE
             SYNTAX      Counter
             ACCESS      read-only
             STATUS      mandatory
             DESCRIPTION
                "The number of SPX over IPX bytes
                 that have been counted on this DLCI."
            ::= { tfrapPerfIpxPerDlciEntry 5 }

      tfrapPerfIpxPerDlciTxSpx    OBJECT-TYPE
             SYNTAX      Counter
             ACCESS      read-only
             STATUS      mandatory
             DESCRIPTION
                "The number of SPX over IPX bytes
                 that have been counted on this DLCI."
            ::= { tfrapPerfIpxPerDlciEntry 6 }

      tfrapPerfIpxPerDlciRxNcp    OBJECT-TYPE
             SYNTAX      Counter
             ACCESS      read-only
             STATUS      mandatory
             DESCRIPTION
                "The number of NCP over IPX bytes
                 that have been counted on this DLCI."
            ::= { tfrapPerfIpxPerDlciEntry 7 }

      tfrapPerfIpxPerDlciTxNcp    OBJECT-TYPE
             SYNTAX      Counter
             ACCESS      read-only
             STATUS      mandatory
             DESCRIPTION
                "The number of NCP over IPX bytes
                 that have been counted on this DLCI."
            ::= { tfrapPerfIpxPerDlciEntry 8 }

      tfrapPerfIpxPerDlciRxSap    OBJECT-TYPE
             SYNTAX      Counter
             ACCESS      read-only
             STATUS      mandatory
             DESCRIPTION
                "The number of SAP over IPX bytes
                 that have been counted on this DLCI."
            ::= { tfrapPerfIpxPerDlciEntry 9 }

      tfrapPerfIpxPerDlciTxSap    OBJECT-TYPE
             SYNTAX      Counter
             ACCESS      read-only
             STATUS      mandatory
             DESCRIPTION
                "The number of SAP over IPX bytes
                 that have been counted on this DLCI."
            ::= { tfrapPerfIpxPerDlciEntry 10 }

      tfrapPerfIpxPerDlciRxRip    OBJECT-TYPE
             SYNTAX      Counter
             ACCESS      read-only
             STATUS      mandatory
             DESCRIPTION
                "The number of RIP over IPX bytes
                 that have been counted on this DLCI."
            ::= { tfrapPerfIpxPerDlciEntry 11 }

      tfrapPerfIpxPerDlciTxRip    OBJECT-TYPE
             SYNTAX      Counter
             ACCESS      read-only
             STATUS      mandatory
             DESCRIPTION
                "The number of RIP over IPX bytes
                 that have been counted on this DLCI."
            ::= { tfrapPerfIpxPerDlciEntry 12 }

      tfrapPerfIpxPerDlciRxNetbios    OBJECT-TYPE
             SYNTAX      Counter
             ACCESS      read-only
             STATUS      mandatory
             DESCRIPTION
                "The number of NETBIOS over IPX bytes
                 that have been counted on this DLCI."
            ::= { tfrapPerfIpxPerDlciEntry 13 }

      tfrapPerfIpxPerDlciTxNetbios    OBJECT-TYPE
             SYNTAX      Counter
             ACCESS      read-only
             STATUS      mandatory
             DESCRIPTION
                "The number of NETBIOS over IPX bytes
                 that have been counted on this DLCI."
            ::= { tfrapPerfIpxPerDlciEntry 14 }

      tfrapPerfIpxPerDlciRxOther    OBJECT-TYPE
             SYNTAX      Counter
             ACCESS      read-only
             STATUS      mandatory
             DESCRIPTION
                "The number of received bytes on this DLCI
                 from protocols over IPX that are not counted
                 elsewhere in this table."
            ::= { tfrapPerfIpxPerDlciEntry 15 }

      tfrapPerfIpxPerDlciTxOther    OBJECT-TYPE
             SYNTAX      Counter
             ACCESS      read-only
             STATUS      mandatory
             DESCRIPTION
                "The number of transmitted bytes on this DLCI
                 from protocols over IPX that are not counted
                 elsewhere in this table."
            ::= { tfrapPerfIpxPerDlciEntry 16 }


   --  IPX Short Term Statistics totals.

   tfrapPerfIpxTotalTable OBJECT-TYPE
         SYNTAX   SEQUENCE OF TfrapPerfIpxTotalEntry
         ACCESS   not-accessible
         STATUS   mandatory
         DESCRIPTION
            "Short Term Statistics on the IPX
             protocol across all DLCIs."
         ::= { tfrapPerfNetworkShortTerm 12 }

         tfrapPerfIpxTotalEntry OBJECT-TYPE
             SYNTAX   TfrapPerfIpxTotalEntry
             ACCESS   not-accessible
             STATUS   mandatory
             DESCRIPTION
                "The IPX Short Term Statistics for a particular DLCI."
            INDEX { tfrapPerfIpxTotalInterval }
            ::= { tfrapPerfIpxTotalTable 1 }

         TfrapPerfIpxTotalEntry ::=
             SEQUENCE {
                 tfrapPerfIpxTotalInterval   INTEGER,
                 tfrapPerfIpxTotalRxTotal    Counter,
                 tfrapPerfIpxTotalTxTotal    Counter,
                 tfrapPerfIpxTotalRxSpx      Counter,
                 tfrapPerfIpxTotalTxSpx      Counter,
                 tfrapPerfIpxTotalRxNcp      Counter,
                 tfrapPerfIpxTotalTxNcp      Counter,
                 tfrapPerfIpxTotalRxSap      Counter,
                 tfrapPerfIpxTotalTxSap      Counter,
                 tfrapPerfIpxTotalRxRip      Counter,
                 tfrapPerfIpxTotalTxRip      Counter,
                 tfrapPerfIpxTotalRxNetbios  Counter,
                 tfrapPerfIpxTotalTxNetbios  Counter,
                 tfrapPerfIpxTotalRxOther    Counter,
                 tfrapPerfIpxTotalTxOther    Counter
             }

      tfrapPerfIpxTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfIpxTotalEntry 1 }

      tfrapPerfIpxTotalRxTotal    OBJECT-TYPE
             SYNTAX      Counter
             ACCESS      read-only
             STATUS      mandatory
             DESCRIPTION
                "The total number of IPX bytes
                 that have been counted across all DLCIs."
            ::= { tfrapPerfIpxTotalEntry 3 }

      tfrapPerfIpxTotalTxTotal    OBJECT-TYPE
             SYNTAX      Counter
             ACCESS      read-only
             STATUS      mandatory
             DESCRIPTION
                "The total number of IPX bytes
                 that have been counted across all DLCIs."
            ::= { tfrapPerfIpxTotalEntry 4 }

      tfrapPerfIpxTotalRxSpx    OBJECT-TYPE
             SYNTAX      Counter
             ACCESS      read-only
             STATUS      mandatory
             DESCRIPTION
                "The number of SPX over IPX bytes
                 that have been counted across all DLCIs."
            ::= { tfrapPerfIpxTotalEntry 5 }

      tfrapPerfIpxTotalTxSpx    OBJECT-TYPE
             SYNTAX      Counter
             ACCESS      read-only
             STATUS      mandatory
             DESCRIPTION
                "The number of SPX over IPX bytes
                 that have been counted across all DLCIs."
            ::= { tfrapPerfIpxTotalEntry 6 }

      tfrapPerfIpxTotalRxNcp    OBJECT-TYPE
             SYNTAX      Counter
             ACCESS      read-only
             STATUS      mandatory
             DESCRIPTION
                "The number of NCP over IPX bytes
                 that have been counted across all DLCIs."
            ::= { tfrapPerfIpxTotalEntry 7 }

      tfrapPerfIpxTotalTxNcp    OBJECT-TYPE
             SYNTAX      Counter
             ACCESS      read-only
             STATUS      mandatory
             DESCRIPTION
                "The number of NCP over IPX bytes
                 that have been counted across all DLCIs."
            ::= { tfrapPerfIpxTotalEntry 8 }

      tfrapPerfIpxTotalRxSap    OBJECT-TYPE
             SYNTAX      Counter
             ACCESS      read-only
             STATUS      mandatory
             DESCRIPTION
                "The number of SAP over IPX bytes
                 that have been counted across all DLCIs."
            ::= { tfrapPerfIpxTotalEntry 9 }

      tfrapPerfIpxTotalTxSap    OBJECT-TYPE
             SYNTAX      Counter
             ACCESS      read-only
             STATUS      mandatory
             DESCRIPTION
                "The number of SAP over IPX bytes
                 that have been counted across all DLCIs."
            ::= { tfrapPerfIpxTotalEntry 10 }

      tfrapPerfIpxTotalRxRip    OBJECT-TYPE
             SYNTAX      Counter
             ACCESS      read-only
             STATUS      mandatory
             DESCRIPTION
                "The number of RIP over IPX bytes
                 that have been counted across all DLCIs."
            ::= { tfrapPerfIpxTotalEntry 11 }

      tfrapPerfIpxTotalTxRip    OBJECT-TYPE
             SYNTAX      Counter
             ACCESS      read-only
             STATUS      mandatory
             DESCRIPTION
                "The number of RIP over IPX bytes
                 that have been counted across all DLCIs."
            ::= { tfrapPerfIpxTotalEntry 12 }

      tfrapPerfIpxTotalRxNetbios    OBJECT-TYPE
             SYNTAX      Counter
             ACCESS      read-only
             STATUS      mandatory
             DESCRIPTION
                "The number of NETBIOS over IPX bytes
                 that have been counted across all DLCIs."
            ::= { tfrapPerfIpxTotalEntry 13 }

      tfrapPerfIpxTotalTxNetbios    OBJECT-TYPE
             SYNTAX      Counter
             ACCESS      read-only
             STATUS      mandatory
             DESCRIPTION
                "The number of NETBIOS over IPX bytes
                 that have been counted across all DLCIs."
            ::= { tfrapPerfIpxTotalEntry 14 }

      tfrapPerfIpxTotalRxOther    OBJECT-TYPE
             SYNTAX      Counter
             ACCESS      read-only
             STATUS      mandatory
             DESCRIPTION
                "The number of received bytes across all DLCIs
                 from protocols over IPX that are not counted
                 elsewhere in this table."
            ::= { tfrapPerfIpxTotalEntry 15 }

      tfrapPerfIpxTotalTxOther    OBJECT-TYPE
             SYNTAX      Counter
             ACCESS      read-only
             STATUS      mandatory
             DESCRIPTION
                "The number of transmitted bytes across all DLCIs
                 from protocols over IPX that are not counted
                 elsewhere in this table."
            ::= { tfrapPerfIpxTotalEntry 16 }


   --  SNA Short Term Statistics for each DLCI.

   tfrapPerfSnaPerDlciTable OBJECT-TYPE
         SYNTAX   SEQUENCE OF TfrapPerfSnaPerDlciEntry
         ACCESS   not-accessible
         STATUS   mandatory
         DESCRIPTION
            "Short Term Statistics on the SNA
             protocol for each DLCI."
         ::= { tfrapPerfNetworkShortTerm 13 }

         tfrapPerfSnaPerDlciEntry OBJECT-TYPE
             SYNTAX   TfrapPerfSnaPerDlciEntry
             ACCESS   not-accessible
             STATUS   mandatory
             DESCRIPTION
                "The SNA Short Term Statistics for a particular DLCI."
            INDEX { tfrapPerfSnaPerDlciInterval, tfrapPerfSnaPerDlciValue }
            ::= { tfrapPerfSnaPerDlciTable 1 }

         TfrapPerfSnaPerDlciEntry ::=
             SEQUENCE {
                 tfrapPerfSnaPerDlciInterval        INTEGER,
                 tfrapPerfSnaPerDlciValue           INTEGER,
                 tfrapPerfSnaPerDlciRxTotal         Counter,
                 tfrapPerfSnaPerDlciTxTotal         Counter,
                 tfrapPerfSnaPerDlciRxSubarea       Counter,
                 tfrapPerfSnaPerDlciTxSubarea       Counter,
                 tfrapPerfSnaPerDlciRxPeriph        Counter,
                 tfrapPerfSnaPerDlciTxPeriph        Counter,
                 tfrapPerfSnaPerDlciRxAppn          Counter,
                 tfrapPerfSnaPerDlciTxAppn          Counter,
                 tfrapPerfSnaPerDlciRxNetbios       Counter,
                 tfrapPerfSnaPerDlciTxNetbios       Counter,
                 tfrapPerfSnaPerDlciRxOther         Counter,
                 tfrapPerfSnaPerDlciTxOther         Counter
            }

      tfrapPerfSnaPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfSnaPerDlciEntry 1 }

      tfrapPerfSnaPerDlciValue    OBJECT-TYPE
             SYNTAX      INTEGER 
             ACCESS      read-only
             STATUS      mandatory
             DESCRIPTION
                "The DLCI value in which the Statistics are associated."
            ::= { tfrapPerfSnaPerDlciEntry 2 }

      tfrapPerfSnaPerDlciRxTotal    OBJECT-TYPE
             SYNTAX      Counter
             ACCESS      read-only
             STATUS      mandatory
             DESCRIPTION
                "The total number of SNA bytes
                 that have been counted on this DLCI."
            ::= { tfrapPerfSnaPerDlciEntry 3 }

      tfrapPerfSnaPerDlciTxTotal    OBJECT-TYPE
             SYNTAX      Counter
             ACCESS      read-only
             STATUS      mandatory
             DESCRIPTION
                "The total number of SNA bytes
                 that have been counted on this DLCI."
            ::= { tfrapPerfSnaPerDlciEntry 4 }

      tfrapPerfSnaPerDlciRxSubarea    OBJECT-TYPE
             SYNTAX      Counter
             ACCESS      read-only
             STATUS      mandatory
             DESCRIPTION
                "The number of SNA Subarea bytes
                 that have been counted on this DLCI."
            ::= { tfrapPerfSnaPerDlciEntry 5 }

      tfrapPerfSnaPerDlciTxSubarea    OBJECT-TYPE
             SYNTAX      Counter
             ACCESS      read-only
             STATUS      mandatory
             DESCRIPTION
                "The number of SNA Subarea bytes
                 that have been counted on this DLCI."
            ::= { tfrapPerfSnaPerDlciEntry 6 }

      tfrapPerfSnaPerDlciRxPeriph    OBJECT-TYPE
             SYNTAX      Counter
             ACCESS      read-only
             STATUS      mandatory
             DESCRIPTION
                "The number of SNA Periph bytes
                 that have been counted on this DLCI."
            ::= { tfrapPerfSnaPerDlciEntry 7 }

      tfrapPerfSnaPerDlciTxPeriph    OBJECT-TYPE
             SYNTAX      Counter
             ACCESS      read-only
             STATUS      mandatory
             DESCRIPTION
                "The number of SNA Periph bytes
                 that have been counted on this DLCI."
            ::= { tfrapPerfSnaPerDlciEntry 8 }

      tfrapPerfSnaPerDlciRxAppn    OBJECT-TYPE
             SYNTAX      Counter
             ACCESS      read-only
             STATUS      mandatory
             DESCRIPTION
                "The number of SNA Appn bytes
                 that have been counted on this DLCI."
            ::= { tfrapPerfSnaPerDlciEntry 9 }

      tfrapPerfSnaPerDlciTxAppn    OBJECT-TYPE
             SYNTAX      Counter
             ACCESS      read-only
             STATUS      mandatory
             DESCRIPTION
                "The number of SNA Appn bytes
                 that have been counted on this DLCI."
            ::= { tfrapPerfSnaPerDlciEntry 10 }

      tfrapPerfSnaPerDlciRxNetbios    OBJECT-TYPE
             SYNTAX      Counter
             ACCESS      read-only
             STATUS      mandatory
             DESCRIPTION
                "The number of SNA Netbios bytes
                 that have been counted on this DLCI."
            ::= { tfrapPerfSnaPerDlciEntry 11 }

      tfrapPerfSnaPerDlciTxNetbios    OBJECT-TYPE
             SYNTAX      Counter
             ACCESS      read-only
             STATUS      mandatory
             DESCRIPTION
                "The number of SNA Netbios bytes
                 that have been counted on this DLCI."
            ::= { tfrapPerfSnaPerDlciEntry 12 }

      tfrapPerfSnaPerDlciRxOther    OBJECT-TYPE
             SYNTAX      Counter
             ACCESS      read-only
             STATUS      mandatory
             DESCRIPTION
                "The number of received bytes on this DLCI
                 from protocols over SNA that are not counted
                 elsewhere in this table."
            ::= { tfrapPerfSnaPerDlciEntry 13 }

      tfrapPerfSnaPerDlciTxOther    OBJECT-TYPE
             SYNTAX      Counter
             ACCESS      read-only
             STATUS      mandatory
             DESCRIPTION
                "The number of transmitted bytes on this DLCI
                 from protocols over SNA that are not counted
                 elsewhere in this table."
            ::= { tfrapPerfSnaPerDlciEntry 14 }


   --  SNA Short Term Statistics totals.

   tfrapPerfSnaTotalTable OBJECT-TYPE
         SYNTAX   SEQUENCE OF TfrapPerfSnaTotalEntry
         ACCESS   not-accessible
         STATUS   mandatory
         DESCRIPTION
            "Short Term Statistics on the SNA
             protocol across all DLCIs."
         ::= { tfrapPerfNetworkShortTerm 14 }

         tfrapPerfSnaTotalEntry OBJECT-TYPE
             SYNTAX   TfrapPerfSnaTotalEntry
             ACCESS   not-accessible
             STATUS   mandatory
             DESCRIPTION
                "The SNA Short Term Statistics for a particular DLCI."
            INDEX { tfrapPerfSnaTotalInterval }
            ::= { tfrapPerfSnaTotalTable 1 }

         TfrapPerfSnaTotalEntry ::=
             SEQUENCE {
                 tfrapPerfSnaTotalInterval        INTEGER,
                 tfrapPerfSnaTotalRxTotal         Counter,
                 tfrapPerfSnaTotalTxTotal         Counter,
                 tfrapPerfSnaTotalRxSubarea       Counter,
                 tfrapPerfSnaTotalTxSubarea       Counter,
                 tfrapPerfSnaTotalRxPeriph        Counter,
                 tfrapPerfSnaTotalTxPeriph        Counter,
                 tfrapPerfSnaTotalRxAppn          Counter,
                 tfrapPerfSnaTotalTxAppn          Counter,
                 tfrapPerfSnaTotalRxNetbios       Counter,
                 tfrapPerfSnaTotalTxNetbios       Counter,
                 tfrapPerfSnaTotalRxOther         Counter,
                 tfrapPerfSnaTotalTxOther         Counter
             }

      tfrapPerfSnaTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfSnaTotalEntry 1 }

      tfrapPerfSnaTotalRxTotal    OBJECT-TYPE
             SYNTAX      Counter
             ACCESS      read-only
             STATUS      mandatory
             DESCRIPTION
                "The total number of SNA bytes
                 that have been counted across all DLCIs."
            ::= { tfrapPerfSnaTotalEntry 3 }

      tfrapPerfSnaTotalTxTotal    OBJECT-TYPE
             SYNTAX      Counter
             ACCESS      read-only
             STATUS      mandatory
             DESCRIPTION
                "The total number of SNA bytes
                 that have been counted across all DLCIs."
            ::= { tfrapPerfSnaTotalEntry 4 }

      tfrapPerfSnaTotalRxSubarea    OBJECT-TYPE
             SYNTAX      Counter
             ACCESS      read-only
             STATUS      mandatory
             DESCRIPTION
                "The number of SNA Subarea bytes
                 that have been counted across all DLCIs."
            ::= { tfrapPerfSnaTotalEntry 5 }

      tfrapPerfSnaTotalTxSubarea    OBJECT-TYPE
             SYNTAX      Counter
             ACCESS      read-only
             STATUS      mandatory
             DESCRIPTION
                "The number of SNA Subarea bytes
                 that have been counted across all DLCIs."
            ::= { tfrapPerfSnaTotalEntry 6 }

      tfrapPerfSnaTotalRxPeriph    OBJECT-TYPE
             SYNTAX      Counter
             ACCESS      read-only
             STATUS      mandatory
             DESCRIPTION
                "The number of SNA Periph bytes
                 that have been counted across all DLCIs."
            ::= { tfrapPerfSnaTotalEntry 7 }

      tfrapPerfSnaTotalTxPeriph    OBJECT-TYPE
             SYNTAX      Counter
             ACCESS      read-only
             STATUS      mandatory
             DESCRIPTION
                "The number of SNA Periph bytes
                 that have been counted across all DLCIs."
            ::= { tfrapPerfSnaTotalEntry 8 }

      tfrapPerfSnaTotalRxAppn    OBJECT-TYPE
             SYNTAX      Counter
             ACCESS      read-only
             STATUS      mandatory
             DESCRIPTION
                "The number of SNA Appn bytes
                 that have been counted across all DLCIs."
            ::= { tfrapPerfSnaTotalEntry 9 }

      tfrapPerfSnaTotalTxAppn    OBJECT-TYPE
             SYNTAX      Counter
             ACCESS      read-only
             STATUS      mandatory
             DESCRIPTION
                "The number of SNA Appn bytes
                 that have been counted across all DLCIs."
            ::= { tfrapPerfSnaTotalEntry 10 }

      tfrapPerfSnaTotalRxNetbios    OBJECT-TYPE
             SYNTAX      Counter
             ACCESS      read-only
             STATUS      mandatory
             DESCRIPTION
                "The number of SNA Netbios bytes
                 that have been counted across all DLCIs."
            ::= { tfrapPerfSnaTotalEntry 11 }

      tfrapPerfSnaTotalTxNetbios    OBJECT-TYPE
             SYNTAX      Counter
             ACCESS      read-only
             STATUS      mandatory
             DESCRIPTION
                "The number of SNA Netbios bytes
                 that have been counted across all DLCIs."
            ::= { tfrapPerfSnaTotalEntry 12 }

      tfrapPerfSnaTotalRxOther    OBJECT-TYPE
             SYNTAX      Counter
             ACCESS      read-only
             STATUS      mandatory
             DESCRIPTION
                "The number of received bytes across all DLCIs
                 from protocols over SNA that are not counted
                 elsewhere in this table."
            ::= { tfrapPerfSnaTotalEntry 13 }

      tfrapPerfSnaTotalTxOther    OBJECT-TYPE
             SYNTAX      Counter
             ACCESS      read-only
             STATUS      mandatory
             DESCRIPTION
                "The number of transmitted bytes across all DLCIs
                 from protocols over SNA that are not counted
                 elsewhere in this table."
            ::= { tfrapPerfSnaTotalEntry 14 }


   --  ARP Short Term Statistics for each DLCI.

   tfrapPerfArpPerDlciTable OBJECT-TYPE
         SYNTAX   SEQUENCE OF TfrapPerfArpPerDlciEntry
         ACCESS   not-accessible
         STATUS   mandatory
         DESCRIPTION
            "Short Term Statistics on the ARP
             protocol for each DLCI."
         ::= { tfrapPerfNetworkShortTerm 15 }

         tfrapPerfArpPerDlciEntry OBJECT-TYPE
             SYNTAX   TfrapPerfArpPerDlciEntry
             ACCESS   not-accessible
             STATUS   mandatory
             DESCRIPTION
                "The ARP Short Term Statistics for a particular DLCI."
            INDEX { tfrapPerfArpPerDlciInterval, tfrapPerfArpPerDlciValue }
            ::= { tfrapPerfArpPerDlciTable 1 }

         TfrapPerfArpPerDlciEntry ::=
             SEQUENCE {
                 tfrapPerfArpPerDlciInterval        INTEGER,
                 tfrapPerfArpPerDlciValue           INTEGER,
                 tfrapPerfArpPerDlciRxTotal         Counter,
                 tfrapPerfArpPerDlciTxTotal         Counter,
                 tfrapPerfArpPerDlciRxArpReq        Counter,
                 tfrapPerfArpPerDlciTxArpReq        Counter,
                 tfrapPerfArpPerDlciRxArpRep        Counter,
                 tfrapPerfArpPerDlciTxArpRep        Counter,
                 tfrapPerfArpPerDlciRxRarpReq       Counter,
                 tfrapPerfArpPerDlciTxRarpReq       Counter,
                 tfrapPerfArpPerDlciRxRarpRep       Counter,
                 tfrapPerfArpPerDlciTxRarpRep       Counter,
                 tfrapPerfArpPerDlciRxInarpReq      Counter,
                 tfrapPerfArpPerDlciTxInarpReq      Counter,
                 tfrapPerfArpPerDlciRxInarpRep      Counter,
                 tfrapPerfArpPerDlciTxInarpRep      Counter,
                 tfrapPerfArpPerDlciRxOther         Counter,
                 tfrapPerfArpPerDlciTxOther         Counter
             }

      tfrapPerfArpPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfArpPerDlciEntry 1 }

      tfrapPerfArpPerDlciValue    OBJECT-TYPE
             SYNTAX      INTEGER 
            ACCESS      read-only
             STATUS      mandatory
             DESCRIPTION
                "The DLCI value in which the Statistics are associated."
            ::= { tfrapPerfArpPerDlciEntry 2 }

      tfrapPerfArpPerDlciRxTotal    OBJECT-TYPE
             SYNTAX      Counter
             ACCESS      read-only
             STATUS      mandatory
             DESCRIPTION
                "The total number of ARP bytes
                 that have been counted on this DLCI."
            ::= { tfrapPerfArpPerDlciEntry 3 }

      tfrapPerfArpPerDlciTxTotal    OBJECT-TYPE
             SYNTAX      Counter
             ACCESS      read-only
             STATUS      mandatory
             DESCRIPTION
                "The total number of ARP bytes
                 that have been counted on this DLCI."
            ::= { tfrapPerfArpPerDlciEntry 4 }

      tfrapPerfArpPerDlciRxArpReq    OBJECT-TYPE
             SYNTAX      Counter
             ACCESS      read-only
             STATUS      mandatory
             DESCRIPTION
                "The number of ARP request bytes
                 that have been counted on this DLCI."
            ::= { tfrapPerfArpPerDlciEntry 5 }

      tfrapPerfArpPerDlciTxArpReq    OBJECT-TYPE
             SYNTAX      Counter
             ACCESS      read-only
             STATUS      mandatory
             DESCRIPTION
                "The number of ARP request bytes
                 that have been counted on this DLCI."
            ::= { tfrapPerfArpPerDlciEntry 6 }

      tfrapPerfArpPerDlciRxArpRep    OBJECT-TYPE
             SYNTAX      Counter
             ACCESS      read-only
             STATUS      mandatory
             DESCRIPTION
                "The number of ARP reply bytes
                 that have been counted on this DLCI."
            ::= { tfrapPerfArpPerDlciEntry 7 }

      tfrapPerfArpPerDlciTxArpRep    OBJECT-TYPE
             SYNTAX      Counter
             ACCESS      read-only
             STATUS      mandatory
             DESCRIPTION
                "The number of ARP reply bytes
                 that have been counted on this DLCI."
            ::= { tfrapPerfArpPerDlciEntry 8 }

      tfrapPerfArpPerDlciRxRarpReq    OBJECT-TYPE
             SYNTAX      Counter
             ACCESS      read-only
             STATUS      mandatory
             DESCRIPTION
                "The number of RARP request bytes
                 that have been counted on this DLCI."
            ::= { tfrapPerfArpPerDlciEntry 9 }

      tfrapPerfArpPerDlciTxRarpReq    OBJECT-TYPE
             SYNTAX      Counter
             ACCESS      read-only
             STATUS      mandatory
             DESCRIPTION
                "The number of RARP request bytes
                 that have been counted on this DLCI."
            ::= { tfrapPerfArpPerDlciEntry 10 }

      tfrapPerfArpPerDlciRxRarpRep    OBJECT-TYPE
             SYNTAX      Counter
             ACCESS      read-only
             STATUS      mandatory
             DESCRIPTION
                "The number of RARP reply bytes
                 that have been counted on this DLCI."
            ::= { tfrapPerfArpPerDlciEntry 11 }

      tfrapPerfArpPerDlciTxRarpRep    OBJECT-TYPE
             SYNTAX      Counter
             ACCESS      read-only
             STATUS      mandatory
             DESCRIPTION
                "The number of RARP reply bytes
                 that have been counted on this DLCI."
            ::= { tfrapPerfArpPerDlciEntry 12 }

      tfrapPerfArpPerDlciRxInarpReq    OBJECT-TYPE
             SYNTAX      Counter
             ACCESS      read-only
             STATUS      mandatory
             DESCRIPTION
                "The number of INARP request bytes
                 that have been counted on this DLCI."
            ::= { tfrapPerfArpPerDlciEntry 13 }

      tfrapPerfArpPerDlciTxInarpReq    OBJECT-TYPE
             SYNTAX      Counter
             ACCESS      read-only
             STATUS      mandatory
             DESCRIPTION
                "The number of INARP request bytes
                 that have been counted on this DLCI."
            ::= { tfrapPerfArpPerDlciEntry 14 }

      tfrapPerfArpPerDlciRxInarpRep    OBJECT-TYPE
             SYNTAX      Counter
             ACCESS      read-only
             STATUS      mandatory
             DESCRIPTION
                "The number of INARP reply bytes
                 that have been counted on this DLCI."
            ::= { tfrapPerfArpPerDlciEntry 15 }

      tfrapPerfArpPerDlciTxInarpRep    OBJECT-TYPE
             SYNTAX      Counter
             ACCESS      read-only
             STATUS      mandatory
             DESCRIPTION
                "The number of INARP reply bytes
                 that have been counted on this DLCI."
            ::= { tfrapPerfArpPerDlciEntry 16 }

      tfrapPerfArpPerDlciRxOther    OBJECT-TYPE
             SYNTAX      Counter
             ACCESS      read-only
             STATUS      mandatory
             DESCRIPTION
                "The number of received bytes on this DLCI
                 from ARP message types that are not counted
                 elsewhere in this table."
            ::= { tfrapPerfArpPerDlciEntry 17 }

      tfrapPerfArpPerDlciTxOther    OBJECT-TYPE
             SYNTAX      Counter
             ACCESS      read-only
             STATUS      mandatory
             DESCRIPTION
                "The number of transmitted bytes on this DLCI
                 from ARP message types that are not counted
                 elsewhere in this table."
            ::= { tfrapPerfArpPerDlciEntry 18 }


   --  ARP Short Term Statistics totals.

   tfrapPerfArpTotalTable OBJECT-TYPE
         SYNTAX   SEQUENCE OF TfrapPerfArpTotalEntry
         ACCESS   not-accessible
         STATUS   mandatory
         DESCRIPTION
            "Short Term Statistics on the ARP
             protocol across all DLCIs."
         ::= { tfrapPerfNetworkShortTerm 16 }

         tfrapPerfArpTotalEntry OBJECT-TYPE
             SYNTAX   TfrapPerfArpTotalEntry
             ACCESS   not-accessible
             STATUS   mandatory
             DESCRIPTION
                "The ARP Short Term Statistics for a particular DLCI."
            INDEX { tfrapPerfArpTotalInterval }
            ::= { tfrapPerfArpTotalTable 1 }

         TfrapPerfArpTotalEntry ::=
             SEQUENCE {
                 tfrapPerfArpTotalInterval        INTEGER,
                 tfrapPerfArpTotalRxTotal         Counter,
                 tfrapPerfArpTotalTxTotal         Counter,
                 tfrapPerfArpTotalRxArpReq        Counter,
                 tfrapPerfArpTotalTxArpReq        Counter,
                 tfrapPerfArpTotalRxArpRep        Counter,
                 tfrapPerfArpTotalTxArpRep        Counter,
                 tfrapPerfArpTotalRxRarpReq       Counter,
                 tfrapPerfArpTotalTxRarpReq       Counter,
                 tfrapPerfArpTotalRxRarpRep       Counter,
                 tfrapPerfArpTotalTxRarpRep       Counter,
                 tfrapPerfArpTotalRxInarpReq      Counter,
                 tfrapPerfArpTotalTxInarpReq      Counter,
                 tfrapPerfArpTotalRxInarpRep      Counter,
                 tfrapPerfArpTotalTxInarpRep      Counter,
                 tfrapPerfArpTotalRxOther         Counter,
                 tfrapPerfArpTotalTxOther         Counter
             }

      tfrapPerfArpTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfArpTotalEntry 1 }

      tfrapPerfArpTotalRxTotal    OBJECT-TYPE
             SYNTAX      Counter
             ACCESS      read-only
             STATUS      mandatory
             DESCRIPTION
                "The total number of ARP bytes
                 that have been counted across all DLCIs."
            ::= { tfrapPerfArpTotalEntry 3 }

      tfrapPerfArpTotalTxTotal    OBJECT-TYPE
             SYNTAX      Counter
             ACCESS      read-only
             STATUS      mandatory
             DESCRIPTION
                "The total number of ARP bytes
                 that have been counted across all DLCIs."
            ::= { tfrapPerfArpTotalEntry 4 }

      tfrapPerfArpTotalRxArpReq    OBJECT-TYPE
             SYNTAX      Counter
             ACCESS      read-only
             STATUS      mandatory
             DESCRIPTION
                "The number of ARP request bytes
                 that have been counted across all DLCIs."
            ::= { tfrapPerfArpTotalEntry 5 }

      tfrapPerfArpTotalTxArpReq    OBJECT-TYPE
             SYNTAX      Counter
             ACCESS      read-only
             STATUS      mandatory
             DESCRIPTION
                "The number of ARP request bytes
                 that have been counted across all DLCIs."
            ::= { tfrapPerfArpTotalEntry 6 }

      tfrapPerfArpTotalRxArpRep    OBJECT-TYPE
             SYNTAX      Counter
             ACCESS      read-only
             STATUS      mandatory
             DESCRIPTION
                "The number of ARP reply bytes
                 that have been counted across all DLCIs."
            ::= { tfrapPerfArpTotalEntry 7 }

      tfrapPerfArpTotalTxArpRep    OBJECT-TYPE
             SYNTAX      Counter
             ACCESS      read-only
             STATUS      mandatory
             DESCRIPTION
                "The number of ARP reply bytes
                 that have been counted across all DLCIs."
            ::= { tfrapPerfArpTotalEntry 8 }

      tfrapPerfArpTotalRxRarpReq    OBJECT-TYPE
             SYNTAX      Counter
             ACCESS      read-only
             STATUS      mandatory
             DESCRIPTION
                "The number of RARP request bytes
                 that have been counted across all DLCIs."
            ::= { tfrapPerfArpTotalEntry 9 }

      tfrapPerfArpTotalTxRarpReq    OBJECT-TYPE
             SYNTAX      Counter
             ACCESS      read-only
             STATUS      mandatory
             DESCRIPTION
                "The number of RARP request bytes
                 that have been counted across all DLCIs."
            ::= { tfrapPerfArpTotalEntry 10 }

      tfrapPerfArpTotalRxRarpRep    OBJECT-TYPE
             SYNTAX      Counter
             ACCESS      read-only
             STATUS      mandatory
             DESCRIPTION
                "The number of RARP reply bytes
                 that have been counted across all DLCIs."
            ::= { tfrapPerfArpTotalEntry 11 }

      tfrapPerfArpTotalTxRarpRep    OBJECT-TYPE
             SYNTAX      Counter
             ACCESS      read-only
             STATUS      mandatory
             DESCRIPTION
                "The number of RARP reply bytes
                 that have been counted across all DLCIs."
            ::= { tfrapPerfArpTotalEntry 12 }

      tfrapPerfArpTotalRxInarpReq    OBJECT-TYPE
             SYNTAX      Counter
             ACCESS      read-only
             STATUS      mandatory
             DESCRIPTION
                "The number of INARP request bytes
                 that have been counted across all DLCIs."
            ::= { tfrapPerfArpTotalEntry 13 }

      tfrapPerfArpTotalTxInarpReq    OBJECT-TYPE
             SYNTAX      Counter
             ACCESS      read-only
             STATUS      mandatory
             DESCRIPTION
                "The number of INARP request bytes
                 that have been counted across all DLCIs."
            ::= { tfrapPerfArpTotalEntry 14 }

      tfrapPerfArpTotalRxInarpRep    OBJECT-TYPE
             SYNTAX      Counter
             ACCESS      read-only
             STATUS      mandatory
             DESCRIPTION
                "The number of INARP reply bytes
                 that have been counted across all DLCIs."
            ::= { tfrapPerfArpTotalEntry 15 }

      tfrapPerfArpTotalTxInarpRep    OBJECT-TYPE
             SYNTAX      Counter
             ACCESS      read-only
             STATUS      mandatory
             DESCRIPTION
                "The number of INARP reply bytes
                 that have been counted across all DLCIs."
            ::= { tfrapPerfArpTotalEntry 16 }

      tfrapPerfArpTotalRxOther    OBJECT-TYPE
             SYNTAX      Counter
             ACCESS      read-only
             STATUS      mandatory
             DESCRIPTION
                "The number of received bytes across all DLCIs
                 from ARP message types that are not counted
                 elsewhere in this table."
            ::= { tfrapPerfArpTotalEntry 17 }

      tfrapPerfArpTotalTxOther    OBJECT-TYPE
             SYNTAX      Counter
             ACCESS      read-only
             STATUS      mandatory
             DESCRIPTION
                "The number of transmitted bytes across all DLCIs
                 from ARP message types that are not counted
                 elsewhere in this table."
            ::= { tfrapPerfArpTotalEntry 18 }



   --  LMI Statistics for each DLCI.

   tfrapPerfLmiPerDlciTable OBJECT-TYPE
         SYNTAX   SEQUENCE OF  TfrapPerfLmiPerDlciEntry
         ACCESS   not-accessible
         STATUS   mandatory
         DESCRIPTION
            "Short Term Statistics on LMI protocol for each DLCI."
         ::= { tfrapPerfNetworkShortTerm  17 }

         tfrapPerfLmiPerDlciEntry OBJECT-TYPE
             SYNTAX   TfrapPerfLmiPerDlciEntry
             ACCESS   not-accessible
             STATUS   mandatory
             DESCRIPTION
                "The LMI Short Term Statistics for a particular DLCI."
             INDEX { tfrapPerfLmiPerDlciInterval, tfrapPerfLmiPerDlciValue }
             ::= { tfrapPerfLmiPerDlciTable 1 }

         TfrapPerfLmiPerDlciEntry ::=
             SEQUENCE {
                 tfrapPerfLmiPerDlciInterval            INTEGER,
                 tfrapPerfLmiPerDlciValue               INTEGER,
                 tfrapPerfLmiPerDlciRxTotalByteCnt      Counter,
                 tfrapPerfLmiPerDlciTxTotalByteCnt      Counter,
                 tfrapPerfLmiPerDlciRxLivoEnqByteCnt    Counter,
                 tfrapPerfLmiPerDlciTxLivoEnqByteCnt    Counter,
                 tfrapPerfLmiPerDlciRxLivoStatByteCnt   Counter,
                 tfrapPerfLmiPerDlciTxLivoStatByteCnt   Counter,
                 tfrapPerfLmiPerDlciRxFullEnqByteCnt    Counter,
                 tfrapPerfLmiPerDlciTxFullEnqByteCnt    Counter,
                 tfrapPerfLmiPerDlciRxFullStatByteCnt   Counter,
                 tfrapPerfLmiPerDlciTxFullStatByteCnt   Counter,
                 tfrapPerfLmiPerDlciRxOtherByteCnt      Counter,
                 tfrapPerfLmiPerDlciTxOtherByteCnt      Counter
             }

      tfrapPerfLmiPerDlciInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfLmiPerDlciEntry 1 }

      tfrapPerfLmiPerDlciValue    OBJECT-TYPE
             SYNTAX      INTEGER 
             ACCESS      read-only
             STATUS      mandatory
             DESCRIPTION
                "The DLCI value with which the Statistics are associated."
            ::= { tfrapPerfLmiPerDlciEntry 2 }

      tfrapPerfLmiPerDlciRxTotalByteCnt    OBJECT-TYPE
             SYNTAX      Counter 
             ACCESS      read-only
             STATUS      mandatory
             DESCRIPTION
                "The total number of received LMI bytes
                 counted on this DLCI."
            ::= { tfrapPerfLmiPerDlciEntry 3 }

      tfrapPerfLmiPerDlciTxTotalByteCnt    OBJECT-TYPE
             SYNTAX      Counter 
             ACCESS      read-only
             STATUS      mandatory
             DESCRIPTION
                "The total number of transmitted LMI bytes
                 counted on this DLCI."
            ::= { tfrapPerfLmiPerDlciEntry 4 }

      tfrapPerfLmiPerDlciRxLivoEnqByteCnt    OBJECT-TYPE
             SYNTAX      Counter  
             ACCESS      read-only
             STATUS      mandatory
             DESCRIPTION
                "The number of bytes received in Link Integrity
                 Verification Only (LIVO) enquiries on this DLCI."
            ::= { tfrapPerfLmiPerDlciEntry 5 }

      tfrapPerfLmiPerDlciTxLivoEnqByteCnt    OBJECT-TYPE
             SYNTAX      Counter  
             ACCESS      read-only
             STATUS      mandatory
             DESCRIPTION
                "The number of bytes transmitted in Link Integrity
                 Verification Only (LIVO) enquiries on this DLCI."
            ::= { tfrapPerfLmiPerDlciEntry 6 }

      tfrapPerfLmiPerDlciRxLivoStatByteCnt    OBJECT-TYPE
             SYNTAX      Counter  
             ACCESS      read-only
             STATUS      mandatory
             DESCRIPTION
                "The number of bytes received in Link Integrity
                 Verification Only (LIVO) statuses on this DLCI."
            ::= { tfrapPerfLmiPerDlciEntry 7 }

      tfrapPerfLmiPerDlciTxLivoStatByteCnt    OBJECT-TYPE
             SYNTAX      Counter  
             ACCESS      read-only
             STATUS      mandatory
             DESCRIPTION
                "The number of bytes transmitted in Link Integrity
                 Verification Only (LIVO) statuses on this DLCI."
            ::= { tfrapPerfLmiPerDlciEntry 8 }

      tfrapPerfLmiPerDlciRxFullEnqByteCnt    OBJECT-TYPE
             SYNTAX      Counter  
             ACCESS      read-only
             STATUS      mandatory
             DESCRIPTION
                "The number of bytes received in 
                 Full Status enquiries on this DLCI."
            ::= { tfrapPerfLmiPerDlciEntry 9 }

      tfrapPerfLmiPerDlciTxFullEnqByteCnt    OBJECT-TYPE
             SYNTAX      Counter  
             ACCESS      read-only
             STATUS      mandatory
             DESCRIPTION
                "The number of bytes transmitted in 
                 Full Status enquiries on this DLCI."
            ::= { tfrapPerfLmiPerDlciEntry 10 }

      tfrapPerfLmiPerDlciRxFullStatByteCnt    OBJECT-TYPE
             SYNTAX      Counter  
             ACCESS      read-only
             STATUS      mandatory
             DESCRIPTION
                "The number of bytes received in 
                 Full Status messages on this DLCI."
            ::= { tfrapPerfLmiPerDlciEntry 11 }

      tfrapPerfLmiPerDlciTxFullStatByteCnt    OBJECT-TYPE
             SYNTAX      Counter  
             ACCESS      read-only
             STATUS      mandatory
             DESCRIPTION
                "The number of bytes transmitted in 
                 Full Status messages on this DLCI."
            ::= { tfrapPerfLmiPerDlciEntry 12 }

      tfrapPerfLmiPerDlciRxOtherByteCnt    OBJECT-TYPE
             SYNTAX      Counter  
             ACCESS      read-only
             STATUS      mandatory
             DESCRIPTION
                "The number of received bytes on this DLCI
                 from LMI protocols that are not counted
                 elsewhere (other than Total) in this table."
            ::= { tfrapPerfLmiPerDlciEntry 13 }

      tfrapPerfLmiPerDlciTxOtherByteCnt    OBJECT-TYPE
             SYNTAX      Counter  
             ACCESS      read-only
             STATUS      mandatory
             DESCRIPTION
                "The number of transmitted bytes on this DLCI
                 from LMI protocols that are not counted
                 elsewhere (other than Total) in this table."
            ::= { tfrapPerfLmiPerDlciEntry 14 }


   --  LMI Statistics for totals.

   tfrapPerfLmiTotalTable OBJECT-TYPE
         SYNTAX   SEQUENCE OF TfrapPerfLmiTotalEntry
         ACCESS   not-accessible
         STATUS   mandatory
         DESCRIPTION
            "Short Term Statistics on LMI protocol across all DLCIs."
         ::= { tfrapPerfNetworkShortTerm 18 }

         tfrapPerfLmiTotalEntry OBJECT-TYPE
             SYNTAX   TfrapPerfLmiTotalEntry
             ACCESS   not-accessible
             STATUS   mandatory
             DESCRIPTION
                "The LMI Short Term Statistics across all DLCIs."
             INDEX { tfrapPerfLmiTotalInterval }
             ::= { tfrapPerfLmiTotalTable 1 }

         TfrapPerfLmiTotalEntry ::=
             SEQUENCE {
                 tfrapPerfLmiTotalInterval            INTEGER,
                 tfrapPerfLmiTotalDlciValue           INTEGER,
                 tfrapPerfLmiTotalRxTotalByteCnt      Counter,
                 tfrapPerfLmiTotalTxTotalByteCnt      Counter,
                 tfrapPerfLmiTotalRxLivoEnqByteCnt    Counter,
                 tfrapPerfLmiTotalTxLivoEnqByteCnt    Counter,
                 tfrapPerfLmiTotalRxLivoStatByteCnt   Counter,
                 tfrapPerfLmiTotalTxLivoStatByteCnt   Counter,
                 tfrapPerfLmiTotalRxFullEnqByteCnt    Counter,
                 tfrapPerfLmiTotalTxFullEnqByteCnt    Counter,
                 tfrapPerfLmiTotalRxFullStatByteCnt   Counter,
                 tfrapPerfLmiTotalTxFullStatByteCnt   Counter,
                 tfrapPerfLmiTotalRxOtherByteCnt      Counter,
                 tfrapPerfLmiTotalTxOtherByteCnt      Counter
             }

      tfrapPerfLmiTotalInterval    OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfLmiTotalEntry 1 }

      tfrapPerfLmiTotalDlciValue    OBJECT-TYPE
             SYNTAX      INTEGER 
             ACCESS      read-only
             STATUS      mandatory
             DESCRIPTION
                "OBSOLETE."
            ::= { tfrapPerfLmiTotalEntry 2 }

      tfrapPerfLmiTotalRxTotalByteCnt    OBJECT-TYPE
             SYNTAX      Counter  
             ACCESS      read-only
             STATUS      mandatory
             DESCRIPTION
                "The total number of received LMI bytes
                 counted across all DLCIs."
            ::= { tfrapPerfLmiTotalEntry 3 }

      tfrapPerfLmiTotalTxTotalByteCnt    OBJECT-TYPE
             SYNTAX      Counter  
             ACCESS      read-only
             STATUS      mandatory
             DESCRIPTION
                "The total number of transmitted LMI bytes
                 counted across all DLCIs."
            ::= { tfrapPerfLmiTotalEntry 4 }

      tfrapPerfLmiTotalRxLivoEnqByteCnt    OBJECT-TYPE
             SYNTAX      Counter  
             ACCESS      read-only
             STATUS      mandatory
             DESCRIPTION
                "The number of bytes received in Link Integrity
                 Verification Only (LIVO) enquiries across all DLCIs."
            ::= { tfrapPerfLmiTotalEntry 5 }

      tfrapPerfLmiTotalTxLivoEnqByteCnt    OBJECT-TYPE
             SYNTAX      Counter  
             ACCESS      read-only
             STATUS      mandatory
             DESCRIPTION
                "The number of bytes transmitted in Link Integrity
                 Verification Only (LIVO) enquiries across all DLCIs."
            ::= { tfrapPerfLmiTotalEntry 6 }

      tfrapPerfLmiTotalRxLivoStatByteCnt    OBJECT-TYPE
             SYNTAX      Counter  
             ACCESS      read-only
             STATUS      mandatory
             DESCRIPTION
                "The number of bytes received in Link Integrity
                 Verification Only (LIVO) statuses across all DLCIs."
            ::= { tfrapPerfLmiTotalEntry 7 }

      tfrapPerfLmiTotalTxLivoStatByteCnt    OBJECT-TYPE
             SYNTAX      Counter  
             ACCESS      read-only
             STATUS      mandatory
             DESCRIPTION
                "The number of bytes transmitted in Link Integrity
                 Verification Only (LIVO) statuses across all DLCIs."
            ::= { tfrapPerfLmiTotalEntry 8 }

      tfrapPerfLmiTotalRxFullEnqByteCnt    OBJECT-TYPE
             SYNTAX      Counter  
             ACCESS      read-only
             STATUS      mandatory
             DESCRIPTION
                "The number of bytes received in 
                 Full Status enquiries across all DLCIs."
            ::= { tfrapPerfLmiTotalEntry 9 }

      tfrapPerfLmiTotalTxFullEnqByteCnt    OBJECT-TYPE
             SYNTAX      Counter  
             ACCESS      read-only
             STATUS      mandatory
             DESCRIPTION
                "The number of bytes transmitted in 
                 Full Status enquiries across all DLCIs."
            ::= { tfrapPerfLmiTotalEntry 10 }

      tfrapPerfLmiTotalRxFullStatByteCnt    OBJECT-TYPE
             SYNTAX      Counter  
             ACCESS      read-only
             STATUS      mandatory
             DESCRIPTION
                "The number of bytes received in 
                 Full Status messages across all DLCIs."
            ::= { tfrapPerfLmiTotalEntry 11 }

      tfrapPerfLmiTotalTxFullStatByteCnt    OBJECT-TYPE
             SYNTAX      Counter  
             ACCESS      read-only
             STATUS      mandatory
             DESCRIPTION
                "The number of bytes transmitted in 
                 Full Status messages across all DLCIs."
            ::= { tfrapPerfLmiTotalEntry 12 }

      tfrapPerfLmiTotalRxOtherByteCnt    OBJECT-TYPE
             SYNTAX      Counter  
             ACCESS      read-only
             STATUS      mandatory
             DESCRIPTION
                "The number of received bytes across all DLCIs
                 from LMI protocols that are not counted
                 elsewhere (other than Total) in this table."
            ::= { tfrapPerfLmiTotalEntry 13 }

      tfrapPerfLmiTotalTxOtherByteCnt   OBJECT-TYPE
             SYNTAX      Counter  
             ACCESS      read-only
             STATUS      mandatory
             DESCRIPTION
                "The number of transmitted bytes across all DLCIs
                 from LMI protocols that are not counted
                 elsewhere (other than Total) in this table."
            ::= { tfrapPerfLmiTotalEntry 14 }




tfrapPerfNetworkLongTerm OBJECT IDENTIFIER ::= { tfrapPerformance 5 }

--
--       Long Term Statistics by DLCI, protocol, and interval.
--

   tfrapPerfNetwLongTermTable OBJECT-TYPE
         SYNTAX   SEQUENCE OF TfrapPerfNetwLongTermEntry
         ACCESS   not-accessible
         STATUS   mandatory
         DESCRIPTION
            "Long Term Statistics by DLCI, protocol, and interval.
             LT statistics are collected on a configurable set
             of DLCIs and protocols. There are 96 intervals maintained
             each with a duration defined by the Long Term Timer. 
             Interval 96 is the current window and Interval 1 is 
             furthest back in time (96xLT Timer seconds ago)."
         ::= { tfrapPerfNetworkLongTerm 1 }

         tfrapPerfNetwLongTermEntry OBJECT-TYPE
             SYNTAX   TfrapPerfNetwLongTermEntry
             ACCESS   not-accessible
             STATUS   mandatory
             DESCRIPTION
                "The Long Term Statistic for a particular DLCI,
                 protocol and interval."
            INDEX { tfrapPerfNetwLongTermDlci,
                    tfrapPerfNetwLongTermProtocol,
                    tfrapPerfNetwLongTermInterval }
            ::= { tfrapPerfNetwLongTermTable 1 }

         TfrapPerfNetwLongTermEntry ::=
             SEQUENCE {
                 tfrapPerfNetwLongTermDlci      INTEGER,
                 tfrapPerfNetwLongTermProtocol  INTEGER,
                 tfrapPerfNetwLongTermInterval  INTEGER,
                 tfrapPerfNetwLongTermValue     Counter
             }

         tfrapPerfNetwLongTermDlci    OBJECT-TYPE
             SYNTAX      INTEGER 
             ACCESS      read-only
             STATUS      mandatory
             DESCRIPTION
               "The DLCI monitored for the statistics. The Long
                Term DLCI filter must first be configured 
                (CfgFrPerfLTDlciFilterEntry)."
            ::= { tfrapPerfNetwLongTermEntry 1 }

         tfrapPerfNetwLongTermProtocol    OBJECT-TYPE
            SYNTAX      INTEGER
            {
               ip-tx-bc                    (1),
               ip-rx-bc                    (2),
               tcp-ip-tx-bc                (3),
               tcp-ip-rx-bc                (4),
               ftp-tcp-ip-tx-bc            (5),
               ftp-tcp-ip-rx-bc            (6),
               telnet-tcp-ip-tx-bc         (7),
               telnet-tcp-ip-rx-bc         (8),
               smtp-tcp-ip-tx-bc           (9),
               smtp-tcp-ip-rx-bc           (10),
--             tftp-tcp-ip-tx-bc           (11),
--             tftp-tcp-ip-rx-bc           (12),
               http-tcp-ip-tx-bc           (13),
               http-tcp-ip-rx-bc           (14),
               netbios-ssn-tcp-ip-tx-bc    (15),
               netbios-ssn-tcp-ip-rx-bc    (16),
--             snmp-tcp-ip-tx-bc           (17),
--             snmp-tcp-ip-rx-bc           (18),
--             snmptrap-tcp-ip-tx-bc       (19),
--             snmptrap-tcp-ip-rx-bc       (20),
               udp-ip-tx-bc                (21),
               udp-ip-rx-bc                (22),
--             ftp-udp-ip-tx-bc            (23),
--             ftp-udp-ip-rx-bc            (24),
--             telnet-udp-ip-tx-bc         (25),
--             telnet-udp-ip-rx-bc         (26),
--             smtp-udp-ip-tx-bc           (27),
--             smtp-udp-ip-rx-bc           (28),
               tftp-udp-ip-tx-bc           (29),
               tftp-udp-ip-rx-bc           (30),
--             http-udp-ip-tx-bc           (31),
--             http-udp-ip-rx-bc           (32),
               netbios-dgm-udp-ip-tx-bc    (33),
               netbios-dgm-udp-ip-rx-bc    (34),
               snmp-udp-ip-tx-bc           (35),
               snmp-udp-ip-rx-bc           (36),
               snmptrap-udp-ip-tx-bc       (37),
               snmptrap-udp-ip-rx-bc       (38),
               rip-udp-ip-tx-bc            (39),
               rip-udp-ip-rx-bc            (40),
               icmp-ip-tx-bc               (41),
               icmp-ip-rx-bc               (42),
               echorep-icmp-ip-tx-bc       (43),
               echorep-icmp-ip-rx-bc       (44),
               dest-unr-icmp-ip-tx-bc      (45),
               dest-unr-icmp-ip-rx-bc      (46),
               src-quench-icmp-ip-tx-bc    (47),
               src-quench-icmp-ip-rx-bc    (48),
               redirect-icmp-ip-tx-bc      (49),
               redirect-icmp-ip-rx-bc      (50),
               echoreq-icmp-ip-tx-bc       (51),
               echoreq-icmp-ip-rx-bc       (52),
               time-excd-icmp-ip-tx-bc     (53),
               time-excd-icmp-ip-rx-bc     (54),
               param-prob-icmp-ip-tx-bc    (55),
               param-prob-icmp-ip-rx-bc    (56),
               timestamp-req-icmp-ip-tx-bc (57),
               timestamp-req-icmp-ip-rx-bc (58),
               timestamp-rep-icmp-ip-tx-bc (59),
               timestamp-rep-icmp-ip-rx-bc (60),
               addr-mask-req-icmp-ip-tx-bc (61),
               addr-mask-req-icmp-ip-rx-bc (62),
               addr-mask-rep-icmp-ip-tx-bc (63),
               addr-mask-rep-icmp-ip-rx-bc (64),
               pkt-too-big-icmp-ip-tx-bc   (65),
               pkt-too-big-icmp-ip-rx-bc   (66),
               gp-mem-query-icmp-ip-tx-bc  (67),
               gp-mem-query-icmp-ip-rx-bc  (68),
               gp-mem-report-icmp-ip-tx-bc (69),
               gp-mem-report-icmp-ip-rx-bc (70),
               gp-mem-reduct-icmp-ip-tx-bc (71),
               gp-mem-reduct-icmp-ip-rx-bc (72),
               ospf-ip-tx-bc               (73),
               ospf-ip-rx-bc               (74),
               other-ip-tx-bc              (75),
               other-ip-rx-bc              (76),
               ipx-tx-bc                   (77),
               ipx-rx-bc                   (78),
               spx-ipx-tx-bc               (79),
               spx-ipx-rx-bc               (80),
               ncp-ipx-tx-bc               (81),
               ncp-ipx-rx-bc               (82),
               sap-ipx-tx-bc               (83),
               sap-ipx-rx-bc               (84),
               rip-ipx-tx-bc               (85),
               rip-ipx-rx-bc               (86),
               netbios-ipx-tx-bc           (87),
               netbios-ipx-rx-bc           (88),
               other-ipx-tx-bc             (89),
               other-ipx-rx-bc             (90),
               arp-tx-bc                   (91),
               arp-rx-bc                   (92),
               arp-req-tx-bc               (93),
               arp-req-rx-bc               (94),
               arp-rep-tx-bc               (95),
               arp-rep-rx-bc               (96),
               rarp-req-tx-bc              (97),
               rarp-req-rx-bc              (98),
               rarp-rep-tx-bc              (99),
               rarp-rep-rx-bc              (100),
               inarp-req-tx-bc             (101),
               inarp-req-rx-bc             (102),
               inarp-rep-tx-bc             (103),
               inarp-rep-rx-bc             (104),
               sna-tx-bc                   (105),
               sna-rx-bc                   (106),
               sna-subarea-tx-bc           (107),
               sna-subarea-rx-bc           (108),
               sna-periph-tx-bc            (109),
               sna-periph-rx-bc            (110),
               sna-appn-tx-bc              (111),
               sna-appn-rx-bc              (112),
               sna-netbios-tx-bc           (113),
               sna-netbios-rx-bc           (114),
               cisco-tx-bc                 (115),
               cisco-rx-bc                 (116),
               other-tx-bc                 (117),
               other-rx-bc                 (118),
               user-defined-1-tx-bc        (119),
               user-defined-1-rx-bc        (120),
               user-defined-2-tx-bc        (121),
               user-defined-2-rx-bc        (122),
               user-defined-3-tx-bc        (123),
               user-defined-3-rx-bc        (124),
               user-defined-4-tx-bc        (125),
               user-defined-4-rx-bc        (126),
               thru-byte-tx-bc             (127),
               thru-byte-rx-bc             (128),
               thru-frame-tx-bc            (129),
               thru-frame-rx-bc            (130),
               thru-fecn-tx-bc             (131),
               thru-fecn-rx-bc             (132),
               thru-becn-tx-bc             (133),
               thru-becn-rx-bc             (134),
               thru-de-tx-bc               (135),
               thru-de-rx-bc               (136),
               cir-percent-range1-tx-bc    (137),
               cir-percent-range1-rx-bc    (138),
               cir-percent-range2-tx-bc    (139),
               cir-percent-range2-rx-bc    (140),
               cir-percent-range3-tx-bc    (141),
               cir-percent-range3-rx-bc    (142),
               cir-percent-range4-tx-bc    (143),
               cir-percent-range4-rx-bc    (144),
               cir-percent-range5-tx-bc    (145),
               cir-percent-range5-rx-bc    (146),
               cir-percent-range6-tx-bc    (147),
               cir-percent-range6-rx-bc    (148),
               cir-percent-range7-tx-bc    (149),
               cir-percent-range7-rx-bc    (150),
               cir-percent-range8-tx-bc    (151),
               cir-percent-range8-rx-bc    (152),
               lmi-tx-bc                   (153),
               lmi-rx-bc                   (154),
               lmi-livo-enq-tx-bc          (155),
               lmi-livo-enq-rx-bc          (156),
               lmi-livo-stat-tx-bc         (157),
               lmi-livo-stat-rx-bc         (158),
               lmi-full-enq-tx-bc          (159),
               lmi-full-enq-rx-bc          (160),
               lmi-full-stat-tx-bc         (161),
               lmi-full-stat-rx-bc         (162),
               lmi-other-tx-bc             (163),
               lmi-other-rx-bc             (164),
               total-uptime                (165),
               total-downtime              (166),
               igrp-tx-bc                  (167),
               igrp-rx-bc                  (168),
               vnip-tx-bc                  (169),
               vnip-rx-bc                  (170),
               annex-g-tx-bc               (171),
               annex-g-rx-bc               (172)
            }
            ACCESS      read-only
            STATUS      mandatory
            DESCRIPTION
             "The type of protocol monitored for the statistics."
            ::= { tfrapPerfNetwLongTermEntry 2 }

         tfrapPerfNetwLongTermInterval    OBJECT-TYPE
             SYNTAX      INTEGER 
             ACCESS      read-only
             STATUS      mandatory
             DESCRIPTION
                "The time interval in which the value was collected.
                 Long Term statistis are maintained for 96 intervals 
                 with the interval duration defined by 
                 (CfgFrPerfTimersLTInterval)."
            ::= { tfrapPerfNetwLongTermEntry 3 }

         tfrapPerfNetwLongTermValue    OBJECT-TYPE
             SYNTAX      Counter
             ACCESS      read-only
             STATUS      mandatory
             DESCRIPTION
                "The statistic collected for the given DLCI and protocol
                 and within the given time interval."
            ::= { tfrapPerfNetwLongTermEntry 4 }


--
--       Long Term Statistics by DLCI: alternative method.
--

   tfrapPerfNetwLongTermAltTable OBJECT-TYPE
         SYNTAX   SEQUENCE OF TfrapPerfNetwLongTermAltEntry
         ACCESS   not-accessible
         STATUS   mandatory
         DESCRIPTION
            "This is an alternative method to access the database of
             long term statistics.  The statistics are indexed by DLCI
             and protocol and are returned in an OCTETSTRING."
         ::= { tfrapPerfNetworkLongTerm 2 }

         tfrapPerfNetwLongTermAltEntry   OBJECT-TYPE
             SYNTAX   TfrapPerfNetwLongTermAltEntry
             ACCESS   not-accessible
             STATUS   mandatory
             DESCRIPTION
                "The Long Term Statistic for a particular
                 DLCI and protocol."
            INDEX { tfrapPerfNetwLongTermAltDlci,
                    tfrapPerfNetwLongTermAltProtocol }
            ::= { tfrapPerfNetwLongTermAltTable 1 }

         TfrapPerfNetwLongTermAltEntry ::=
             SEQUENCE {
                 tfrapPerfNetwLongTermAltDlci      INTEGER,
                 tfrapPerfNetwLongTermAltProtocol  INTEGER,
                 tfrapPerfNetwLongTermAltArray     OCTET STRING
             }

         tfrapPerfNetwLongTermAltDlci    OBJECT-TYPE
             SYNTAX      INTEGER 
             ACCESS      read-only
             STATUS      mandatory
             DESCRIPTION
               "The DLCI monitored for the statistics."
            ::= { tfrapPerfNetwLongTermAltEntry 1 }

         tfrapPerfNetwLongTermAltProtocol   OBJECT-TYPE
             SYNTAX      INTEGER 
             {
               ip-tx-bc                    (1),
               ip-rx-bc                    (2),
               tcp-ip-tx-bc                (3),
               tcp-ip-rx-bc                (4),
               ftp-tcp-ip-tx-bc            (5),
               ftp-tcp-ip-rx-bc            (6),
               telnet-tcp-ip-tx-bc         (7),
               telnet-tcp-ip-rx-bc         (8),
               smtp-tcp-ip-tx-bc           (9),
               smtp-tcp-ip-rx-bc           (10),
--             tftp-tcp-ip-tx-bc           (11),
--             tftp-tcp-ip-rx-bc           (12),
               http-tcp-ip-tx-bc           (13),
               http-tcp-ip-rx-bc           (14),
               netbios-ssn-tcp-ip-tx-bc    (15),
               netbios-ssn-tcp-ip-rx-bc    (16),
--             snmp-tcp-ip-tx-bc           (17),
--             snmp-tcp-ip-rx-bc           (18),
--             snmptrap-tcp-ip-tx-bc       (19),
--             snmptrap-tcp-ip-rx-bc       (20),
               udp-ip-tx-bc                (21),
               udp-ip-rx-bc                (22),
--             ftp-udp-ip-tx-bc            (23),
--             ftp-udp-ip-rx-bc            (24),
--             telnet-udp-ip-tx-bc         (25),
--             telnet-udp-ip-rx-bc         (26),
--             smtp-udp-ip-tx-bc           (27),
--             smtp-udp-ip-rx-bc           (28),
               tftp-udp-ip-tx-bc           (29),
               tftp-udp-ip-rx-bc           (30),
--             http-udp-ip-tx-bc           (31),
--             http-udp-ip-rx-bc           (32),
               netbios-dgm-udp-ip-tx-bc    (33),
               netbios-dgm-udp-ip-rx-bc    (34),
               snmp-udp-ip-tx-bc           (35),
               snmp-udp-ip-rx-bc           (36),
               snmptrap-udp-ip-tx-bc       (37),
               snmptrap-udp-ip-rx-bc       (38),
               rip-udp-ip-tx-bc            (39),
               rip-udp-ip-rx-bc            (40),
               icmp-ip-tx-bc               (41),
               icmp-ip-rx-bc               (42),
               echorep-icmp-ip-tx-bc       (43),
               echorep-icmp-ip-rx-bc       (44),
               dest-unr-icmp-ip-tx-bc      (45),
               dest-unr-icmp-ip-rx-bc      (46),
               src-quench-icmp-ip-tx-bc    (47),
               src-quench-icmp-ip-rx-bc    (48),
               redirect-icmp-ip-tx-bc      (49),
               redirect-icmp-ip-rx-bc      (50),
               echoreq-icmp-ip-tx-bc       (51),
               echoreq-icmp-ip-rx-bc       (52),
               time-excd-icmp-ip-tx-bc     (53),
               time-excd-icmp-ip-rx-bc     (54),
               param-prob-icmp-ip-tx-bc    (55),
               param-prob-icmp-ip-rx-bc    (56),
               timestamp-req-icmp-ip-tx-bc (57),
               timestamp-req-icmp-ip-rx-bc (58),
               timestamp-rep-icmp-ip-tx-bc (59),
               timestamp-rep-icmp-ip-rx-bc (60),
               addr-mask-req-icmp-ip-tx-bc (61),
               addr-mask-req-icmp-ip-rx-bc (62),
               addr-mask-rep-icmp-ip-tx-bc (63),
               addr-mask-rep-icmp-ip-rx-bc (64),
               pkt-too-big-icmp-ip-tx-bc   (65),
               pkt-too-big-icmp-ip-rx-bc   (66),
               gp-mem-query-icmp-ip-tx-bc  (67),
               gp-mem-query-icmp-ip-rx-bc  (68),
               gp-mem-report-icmp-ip-tx-bc (69),
               gp-mem-report-icmp-ip-rx-bc (70),
               gp-mem-reduct-icmp-ip-tx-bc (71),
               gp-mem-reduct-icmp-ip-rx-bc (72),
               ospf-ip-tx-bc               (73),
               ospf-ip-rx-bc               (74),
               other-ip-tx-bc              (75),
               other-ip-rx-bc              (76),
               ipx-tx-bc                   (77),
               ipx-rx-bc                   (78),
               spx-ipx-tx-bc               (79),
               spx-ipx-rx-bc               (80),
               ncp-ipx-tx-bc               (81),
               ncp-ipx-rx-bc               (82),
               sap-ipx-tx-bc               (83),
               sap-ipx-rx-bc               (84),
               rip-ipx-tx-bc               (85),
               rip-ipx-rx-bc               (86),
               netbios-ipx-tx-bc           (87),
               netbios-ipx-rx-bc           (88),
               other-ipx-tx-bc             (89),
               other-ipx-rx-bc             (90),
               arp-tx-bc                   (91),
               arp-rx-bc                   (92),
               arp-req-tx-bc               (93),
               arp-req-rx-bc               (94),
               arp-rep-tx-bc               (95),
               arp-rep-rx-bc               (96),
               rarp-req-tx-bc              (97),
               rarp-req-rx-bc              (98),
               rarp-rep-tx-bc              (99),
               rarp-rep-rx-bc              (100),
               inarp-req-tx-bc             (101),
               inarp-req-rx-bc             (102),
               inarp-rep-tx-bc             (103),
               inarp-rep-rx-bc             (104),
               sna-tx-bc                   (105),
               sna-rx-bc                   (106),
               sna-subarea-tx-bc           (107),
               sna-subarea-rx-bc           (108),
               sna-periph-tx-bc            (109),
               sna-periph-rx-bc            (110),
               sna-appn-tx-bc              (111),
               sna-appn-rx-bc              (112),
               sna-netbios-tx-bc           (113),
               sna-netbios-rx-bc           (114),
               cisco-tx-bc                 (115),
               cisco-rx-bc                 (116),
               other-tx-bc                 (117),
               other-rx-bc                 (118),
               user-defined-1-tx-bc        (119),
               user-defined-1-rx-bc        (120),
               user-defined-2-tx-bc        (121),
               user-defined-2-rx-bc        (122),
               user-defined-3-tx-bc        (123),
               user-defined-3-rx-bc        (124),
               user-defined-4-tx-bc        (125),
               user-defined-4-rx-bc        (126),
               thru-byte-tx-bc             (127),
               thru-byte-rx-bc             (128),
               thru-frame-tx-bc            (129),
               thru-frame-rx-bc            (130),
               thru-fecn-tx-bc             (131),
               thru-fecn-rx-bc             (132),
               thru-becn-tx-bc             (133),
               thru-becn-rx-bc             (134),
               thru-de-tx-bc               (135),
               thru-de-rx-bc               (136),
               cir-percent-range1-tx-bc    (137),
               cir-percent-range1-rx-bc    (138),
               cir-percent-range2-tx-bc    (139),
               cir-percent-range2-rx-bc    (140),
               cir-percent-range3-tx-bc    (141),
               cir-percent-range3-rx-bc    (142),
               cir-percent-range4-tx-bc    (143),
               cir-percent-range4-rx-bc    (144),
               cir-percent-range5-tx-bc    (145),
               cir-percent-range5-rx-bc    (146),
               cir-percent-range6-tx-bc    (147),
               cir-percent-range6-rx-bc    (148),
               cir-percent-range7-tx-bc    (149),
               cir-percent-range7-rx-bc    (150),
               cir-percent-range8-tx-bc    (151),
               cir-percent-range8-rx-bc    (152),
               lmi-tx-bc                   (153),
               lmi-rx-bc                   (154),
               lmi-livo-enq-tx-bc          (155),
               lmi-livo-enq-rx-bc          (156),
               lmi-livo-stat-tx-bc         (157),
               lmi-livo-stat-rx-bc         (158),
               lmi-full-enq-tx-bc          (159),
               lmi-full-enq-rx-bc          (160),
               lmi-full-stat-tx-bc         (161),
               lmi-full-stat-rx-bc         (162),
               lmi-other-tx-bc             (163),
               lmi-other-rx-bc             (164),
               total-uptime                (165),
               total-downtime              (166),
               igrp-tx-bc                  (167),
               igrp-rx-bc                  (168),
               vnip-tx-bc                  (169),
               vnip-rx-bc                  (170),
               annex-g-tx-bc               (171),
               annex-g-rx-bc               (172)
             }
             ACCESS      read-only
             STATUS      mandatory
             DESCRIPTION
               "The protocol monitored for the statistics."
            ::= { tfrapPerfNetwLongTermAltEntry 2 }
          
         tfrapPerfNetwLongTermAltArray    OBJECT-TYPE
          SYNTAX      OCTET STRING
             ACCESS      read-only
             STATUS      mandatory
             DESCRIPTION
                "The statistic collected for the given DLCI and protocol."
            ::= { tfrapPerfNetwLongTermAltEntry 3 }


   tfrapPerfNetworkLongTermCommands OBJECT IDENTIFIER
            ::= { tfrapPerfNetworkLongTerm 3 }

   tfrapPerfNetworkLongTermCmdClear    OBJECT-TYPE
          SYNTAX      INTEGER
          {
              clear-statistics (1)
          }
          ACCESS      write-only
          STATUS      mandatory
          DESCRIPTION
             "Allows the user to zero out all the statistics in
              the long term statistics tables.
              (1) Clear all Long Term statistics"
          ::= { tfrapPerfNetworkLongTermCommands 1 }


tfrapPerfCirPercentUtilization OBJECT IDENTIFIER ::= { tfrapPerformance 6 }

--
--  CIR Percentage Statistics for each DLCI.
--

 tfrapPerfCirPercentUtilizationTable OBJECT-TYPE
         SYNTAX   SEQUENCE OF TfrapPerfCirPercentUtilizationEntry
         ACCESS   not-accessible
         STATUS   mandatory
         DESCRIPTION
            "Short Term Statistics on the percentage of CIR used
             on each DLCI.  Each short term statistics interval,
             the count of bytes transmitted and received is used
             to calculate the percentage of CIR used.  The byte
             count is then added to the appropriate bucket for
             the CIR percentage range."
         ::= { tfrapPerfCirPercentUtilization 1 }

 tfrapPerfCirPercentUtilizationEntry OBJECT-TYPE
             SYNTAX TfrapPerfCirPercentUtilizationEntry
             ACCESS   not-accessible
             STATUS   mandatory
             DESCRIPTION
                "The CIR Percentage Statistics for a particular DLCI.
                 These calculations are done at the completion of each 
                 Short Term interval."
             INDEX { tfrapPerfCirPercentUtilizationInterval,
                     tfrapPerfCirPercentUtilizationDlciValue }
             ::= { tfrapPerfCirPercentUtilizationTable 1 }

         TfrapPerfCirPercentUtilizationEntry ::=
             SEQUENCE {
                 tfrapPerfCirPercentUtilizationInterval    INTEGER,
                 tfrapPerfCirPercentUtilizationDlciValue   INTEGER,
                 tfrapPerfCirRxPercentUtilizationRange1    INTEGER,
                 tfrapPerfCirRxPercentUtilizationRange2    INTEGER,
                 tfrapPerfCirRxPercentUtilizationRange3    INTEGER,
                 tfrapPerfCirRxPercentUtilizationRange4    INTEGER,
                 tfrapPerfCirRxPercentUtilizationRange5    INTEGER,
                 tfrapPerfCirRxPercentUtilizationRange6    INTEGER,
                 tfrapPerfCirRxPercentUtilizationRange7    INTEGER,
                 tfrapPerfCirRxPercentUtilizationRange8    INTEGER,
                 tfrapPerfCirTxPercentUtilizationRange1    INTEGER,
                 tfrapPerfCirTxPercentUtilizationRange2    INTEGER,
                 tfrapPerfCirTxPercentUtilizationRange3    INTEGER,
                 tfrapPerfCirTxPercentUtilizationRange4    INTEGER,
                 tfrapPerfCirTxPercentUtilizationRange5    INTEGER,
                 tfrapPerfCirTxPercentUtilizationRange6    INTEGER,
                 tfrapPerfCirTxPercentUtilizationRange7    INTEGER,
                 tfrapPerfCirTxPercentUtilizationRange8    INTEGER
             }

 tfrapPerfCirPercentUtilizationInterval OBJECT-TYPE
             SYNTAX      INTEGER
             {
                  current-interval  (1),
                  previous-interval (2),
                  cumulative-counts (3)
             } 
             ACCESS      read-only
             STATUS      mandatory
             DESCRIPTION
                "The Short Term statistics model maintains three 
                 intervals: current, previous, and cumulative totals. 
                 Interval duration is defined by the Short Term Timer
                 (CfgFrPerfTimersSTInterval).
                 (1) Currently active short term interval
                 (2) Previously completed short term interval
                 (3) Cumulative total since last cleared."
            ::= { tfrapPerfCirPercentUtilizationEntry 1 }

 tfrapPerfCirPercentUtilizationDlciValue OBJECT-TYPE
             SYNTAX      INTEGER 
             ACCESS      read-only
             STATUS      mandatory
             DESCRIPTION
                "The DLCI value with which the Statistics are associated."
            ::= { tfrapPerfCirPercentUtilizationEntry 2 }

 tfrapPerfCirRxPercentUtilizationRange1 OBJECT-TYPE
             SYNTAX      INTEGER 
             ACCESS      read-only
             STATUS      mandatory
             DESCRIPTION
                "The number of short-term intervals during
                 which rx data throughput on this DLCI compared
                 to CIR was in range 1 (0% of CIR)."
            ::= { tfrapPerfCirPercentUtilizationEntry 21 }

 tfrapPerfCirRxPercentUtilizationRange2 OBJECT-TYPE
             SYNTAX      INTEGER 
             ACCESS      read-only
             STATUS      mandatory
             DESCRIPTION
                "The number of short-term intervals during
                 which rx data throughput on this DLCI compared
                 to CIR was in range 2 (1-10% of CIR)."
            ::= { tfrapPerfCirPercentUtilizationEntry 22 }

 tfrapPerfCirRxPercentUtilizationRange3 OBJECT-TYPE
             SYNTAX      INTEGER 
             ACCESS      read-only
             STATUS      mandatory
             DESCRIPTION
                "The number of short-term intervals during
                 which rx data throughput on this DLCI compared
                 to CIR was in range 3 (11-20% of CIR)."
            ::= { tfrapPerfCirPercentUtilizationEntry 23 }

 tfrapPerfCirRxPercentUtilizationRange4 OBJECT-TYPE
             SYNTAX      INTEGER 
             ACCESS      read-only
             STATUS      mandatory
             DESCRIPTION
                "The number of short-term intervals during
                 which rx data throughput on this DLCI compared
                 to CIR was in range 4 (21-50% of CIR)."
            ::= { tfrapPerfCirPercentUtilizationEntry 24 }

 tfrapPerfCirRxPercentUtilizationRange5 OBJECT-TYPE
             SYNTAX      INTEGER 
             ACCESS      read-only
             STATUS      mandatory
             DESCRIPTION
                "The number of short-term intervals during
                 which rx data throughput on this DLCI compared
                 to CIR was in range 5 (51-80% of CIR)."
            ::= { tfrapPerfCirPercentUtilizationEntry 25 }

 tfrapPerfCirRxPercentUtilizationRange6 OBJECT-TYPE
