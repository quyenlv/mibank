-- extracted from draft-ietf-rmonmib-iftopn-mib-02.txt
-- at Fri Jul  7 07:08:04 2000

   INTERFACETOPN-MIB DEFINITIONS ::= BEGIN

      IMPORTS
           MODULE-IDENTITY, OBJECT-TYPE, Counter32, Integer32, Gauge32
                   FROM SNMPv2-SMI
           RowStatus, TimeStamp, TEXTUAL-CONVENTION
                   FROM SNMPv2-TC

           rmon, OwnerString
                   FROM RMON-MIB
           rmonConformance, probeConfig
                   FROM RMON2-MIB
           CounterBasedGauge64
                   FROM HCNUM-TC
           MODULE-COMPLIANCE, OBJECT-GROUP
                   FROM SNMPv2-CONF;

      interfaceTopNMIB MODULE-IDENTITY
           LAST-UPDATED "200007030000Z"
           ORGANIZATION "IETF RMON MIB Working Group"
           CONTACT-INFO
           "

                   Dan Romascanu
                   Avaya Communication
                   Tel:  +972-3-645-8414
                   Email: dromasca@avaya.com"

          DESCRIPTION
                   "The MIB module for sorting device interfaces for RMON and
                   SMON monitoring in a multiple device implementation."
           ::= { rmon 27 }

   interfaceTopNObjects       OBJECT IDENTIFIER ::= { interfaceTopNMIB 1 }
   interfaceTopNNotifications OBJECT IDENTIFIER ::= { interfaceTopNMIB 2 }
   interfaceTopNConformance   OBJECT IDENTIFIER ::= { interfaceTopNMIB 3 }

      -- The Interface Top N group is used to prepare reports that
      -- describe a list of interfaces (data sources)
      -- ordered by the values of one
      -- of the objects that apply to the interfaces of the respective device.
      -- Those objects are defined by standard MIBs. The exact objects that
      -- are supported by the agent are described by interfaceTopNCaps
      -- The objects must be elements in tables indexed only by an
      -- InterfaceIndex object.
      -- The objects  chosen by the
      -- management station may be sampled over a management
      -- station-specified time interval, making the report rate based.
      -- The management station also specifies the number of interfaces
      -- that are reported.
      --
      -- The interfaceTopNControlTable is used to initiate the generation
      -- of a report.  The management station may select the parameters
      -- of such a report, such as which object, how
      -- many interfaces, and the start & stop times of the sampling.  When
      -- the report is prepared, entries are created in the
      -- interfaceTopNTable associated with the relevant
      -- interfaceTopNControlEntry.  These entries are static for
      -- each report after it has been prepared.

   interfaceTopNCaps   OBJECT-TYPE
       SYNTAX      BITS {
                  usrTopN(0),
                  ifInOctets(1),
                  ifInUcastPkts(2),
                  ifInNUcastPkts(3),
                  ifInDiscards(4),
                  ifInErrors(5),
                  ifInUnknownProtos(6),
                  ifOutOctets(7),
                  ifOutUcastPkts(8),
                  ifOutNUcastPkts(9),
                  ifOutDiscards(10),
                  ifOutErrors(11),
                  ifInMulticastPkts(12),
                  ifInBroadcastPkts(13),
                  ifOutMulticastPkts(14),
                  ifOutBroadcastPkts(15),
                  ifHCInOctets(16),
                  ifHCInUcastPkts(17),
                  ifHCInMulticastPkts(18),
                  ifHCInBroadcastPkts(19),
                  ifHCOutOctets(20),
                  ifHCOutUcastPkts(21),
                  ifHCOutMulticastPkts(22),
                  ifHCOutBroadcastPkts(23),
                  dot3StatsAlignmentErrors(24),
                  dot3StatsFCSErrors(25),
                  dot3StatsSingleCollisionFrames(26),
                  dot3StatsMultipleCollisionFrames(27),
                  dot3StatsSQETestErrors(28),
                  dot3StatsDeferredTransmissions(29),
                  dot3StatsLateCollisions(30),
                  dot3StatsExcessiveCollisions(31),
                  dot3StatsInternalMacTransmitErrors(32),
                  dot3StatsCarrierSenseErrors(33),
                  dot3StatsFrameTooLongs(34),
                  dot3StatsInternalMacReceiveErrors(35),
                  dot3StatsSymbolErrors(36),
                  dot5StatsLineErrors(37),
                  dot5StatsBurstErrors(38),
                  dot5StatsACErrors(39),
                  dot5StatsAbortTransErrors(40),
                  dot5StatsInternalErrors(41),
                  dot5StatsLostFrameErrors(42),
                  dot5StatsReceiveCongestions(43),
                  dot5StatsFrameCopiedErrors(44),
                  dot5StatsTokenErrors(45),
                  dot5StatsSoftErrors(46),
                  dot5StatsHardErrors(47),
                  dot5StatsSignalLoss(48),
                  dot5StatsTransmitBeacons(49),
                  dot5StatsRecoverys(50),
                  dot5StatsLobeWires(51),
                  dot5StatsRemoves(52),
                  dot5StatsSingles(53),
                  dot5StatsFreqErrors(54),
                  etherStatsDropEvents(55),
                  etherStatsOctets(56),
                  etherStatsPkts(57),
                  etherStatsBroadcastPkts(58),
                  etherStatsMulticastPkts(59),
                  etherStatsCRCAlignErrors(60),
                  etherStatsUndersizePkts(61),
                  etherStatsOversizePkts(62),
                  etherStatsFragments(63),
                  etherStatsJabbers(64),
                  etherStatsCollisions(65),
                  etherStatsPkts64Octets(66),
                  etherStatsPkts65to127Octets(67),
                  etherStatsPkts128to255Octets(68),
                  etherStatsPkts256to511Octets(69),
                  etherStatsPkts512to1023Octets(70),
                  etherStatsPkts1024to1518Octets(71),
                  dot1dTpPortInFrames(72),
                  dot1dTpPortOutFrames(73),
                  dot1dTpPortInDiscards(74)
       }
       MAX-ACCESS  read-only
       STATUS      current
       DESCRIPTION
               "The type(s) of sorting capabilities supported by the agent.

               If the agent supports usrTopN functionality, then the 'usrTopN'
               bit will be set. A management application SHOULD NOT try to
               access the usrTopN functionality if this bit is not set.

               If the agent can perform sorting of interfaces according to the
               values of ifInOctets, as defined in [20],
               then the 'ifInOctets' bit will be set.

               If the agent can perform sorting of interfaces according to the
               values of ifInUcastPkts, as defined in [20],
               then the 'ifInUcastPkts' bit will be set.

               If the agent can perform sorting of interfaces according to the
               values of ifInNUcastPkts, as defined in [20],
               then the 'ifInNUcastPkts' bit will be set.

               If the agent can perform sorting of interfaces according to the
               values of ifInDiscards, as defined in [20],
               then the 'ifInDiscards' bit will be set.

               If the agent can perform sorting of interfaces according to the
               values of ifInErrors, as defined in [20],
               then the 'ifInErrors' bit will be set.

               If the agent can perform sorting of interfaces according to the
               values of ifInUnknownProtocols, as defined in [20],
               then the 'ifInUnknownProtocols' bit will be set.

               If the agent can perform sorting of interfaces according to the
               values of ifOutOctets, as defined in [20],
               then the 'ifOutOctets' bit will be set.

               If the agent can perform sorting of interfaces according to the
               values of ifOutUcastPackets, as defined in [20],
               then the 'ifOutUcastPackets' bit will be set.

               If the agent can perform sorting of interfaces according to the
               values of ifOutNUcastPackets, as defined in [20],
               then the 'ifOutNUcastPackets' bit will be set.

               If the agent can perform sorting of interfaces according to the
               values of ifOutDiscards, as defined in [20],
               then the 'ifOutDiscards' bit will be set.

               If the agent can perform sorting of interfaces according to the
               values of ifOutErrors, as defined in [20],
               then the 'ifOutErrors' bit will be set.

               If the agent can perform sorting of interfaces according to the
               values of ifInMulticastPkts, as defined in [20],
               then the 'ifInMulticastPkts' bit will be set.

               If the agent can perform sorting of interfaces according to the
               values of ifInBroadcastPkts, as defined in [20],
               then the 'ifInBroadcastPkts' bit will be set.

               If the agent can perform sorting of interfaces according to the
               values of ifOutMulticastPkts, as defined in [20],
               then the 'ifOutMulticastPkts' bit will be set.

               If the agent can perform sorting of interfaces according to the
               values of ifOutBroadcastPkts, as defined in [20],
               then the 'ifOutBroadcastPkts' bit will be set.

               If the agent can perform sorting of interfaces according to the
               values of ifHCInOctes, as defined in [20],
               then the 'ifHCInOctes' bit will be set.

               If the agent can perform sorting of interfaces according to the
               values of ifHCInMulticastPkts, as defined in [20],
               then the 'ifHCInMulticastPkts' bit will be set.

               If the agent can perform sorting of interfaces according to the
               values of ifHCInBroadcastPkts, as defined in [20],
               then the 'ifHCInBroadcastPkts' bit will be set.

               If the agent can perform sorting of interfaces according to the
               values of ifHCOutOctets, as defined in [20],
               then the 'ifHCOutOctets' bit will be set.

               If the agent can perform sorting of interfaces according to the
               values of ifHCOutUcastPkts, as defined in [20],
               then the 'ifHCOutUcastPkts' bit will be set.

               If the agent can perform sorting of interfaces according to the
               values of ifHCOutMulticastPkts, as defined in [20],
               then the 'ifHCOutMulticastPkts' bit will be set.

               If the agent can perform sorting of interfaces according to the
               values of ifHCOutBroadcastPkts, as defined in [20],
               then the 'ifHCOutBroadcastPkts' bit will be set.

               If the agent can perform sorting of interfaces according to the
               values of dot3StatsAlignementErrors, as defined in [23],
               then the 'dot3StatsAlignementErrors' bit will be set.

               If the agent can perform sorting of interfaces according to the
               values of dot3StatsFCSErrors, as defined in [23],
               then the 'dot3StatsFCSErrors' bit will be set.

               If the agent can perform sorting of interfaces according to the
               values of dot3StatsSingleCollisionFrames, as defined in [23],
               then the 'dot3StatsSingleCollisionFrames' bit will be set.

               If the agent can perform sorting of interfaces according to the
               values of dot3StatsSQETestErrors, as defined in [23],
               then the 'dot3StatsSQETestErrors' bit will be set.

               If the agent can perform sorting of interfaces according to the
               values of dot3StatsDeferredTransmissions, as defined in [23],
               then the 'dot3StatsDeferredTransmissions' bit will be set.

               If the agent can perform sorting of interfaces according to the
               values of dot3StatsLateCollisions, as defined in [23],
               then the 'dot3StatsLateCollisions' bit will be set.

               If the agent can perform sorting of interfaces according to the
               values of dot3StatsExcessiveCollisions, as defined in [23],
               then the 'dot3StatsExcessiveCollisions' bit will be set.

               If the agent can perform sorting of interfaces according to the
               values of dot3StatsInternalMacTransmitErrors, as defined in [23],
               then the 'dot3StatsInternalMacTransmitErrors' bit will be set.

               If the agent can perform sorting of interfaces according to the
               values of dot3StatsCarrierSenseErrors, as defined in [23],
               then the 'dot3StatsCarrierSenseErrors' bit will be set.

               If the agent can perform sorting of interfaces according to the
               values of dot3StatsFrameTooLongs, as defined in [23],
               then the 'dot3StatsFrameTooLongs' bit will be set.

               If the agent can perform sorting of interfaces according to the
               values of dot3StatsInternalMacReceiveErrors, as defined in [23],
               then the 'dot3StatsInternalMacReceiveErrors' bit will be set.

               If the agent can perform sorting of interfaces according to the
               values of dot3StatsSymbolErrors, as defined in [23],
               then the 'dot3StatsSymbolErrors' bit will be set.

               If the agent can perform sorting of interfaces according to the
               values of dot5StatsLineErrors, as defined in [24],
               then the 'dot5StatsLineErrors' bit will be set.

               If the agent can perform sorting of interfaces according to the
               values of dot5StatsBurstErrors, as defined in [24],
               then the 'dot5StatsBurstErrors' bit will be set.

               If the agent can perform sorting of interfaces according to the
               values of dot5StatsACErrors, as defined in [24],
               then the 'dot5StatsACErrors' bit will be set.

               If the agent can perform sorting of interfaces according to the
               values of dot5StatsAbortTransErrors, as defined in [24],
               then the 'dot5StatsAbortTransErrors' bit will be set.

               If the agent can perform sorting of interfaces according to the
               values of dot5StatsInternalErrors, as defined in [24],
               then the 'dot5StatsInternalErrors' bit will be set.

               If the agent can perform sorting of interfaces according to the
               values of dot5StatsLostFrameErrors, as defined in [24],
               then the 'dot5StatsLostFrameErrors' bit will be set.

               If the agent can perform sorting of interfaces according to the
               values of dot5StatsReceiveCongestionErrors, as defined in [24],
               then the 'dot5StatsReceiveCongestionErrors' bit will be set.

               If the agent can perform sorting of interfaces according to the
               values of dot5StatsFrameCopiedErrors, as defined in [24],
               then the 'dot5StatsFrameCopiedErrors' bit will be set.

               If the agent can perform sorting of interfaces according to the
               values of dot5StatsTokenErrors, as defined in [24],
               then the 'dot5StatsTokenErrors' bit will be set.

               If the agent can perform sorting of interfaces according to the
               values of dot5StatsSoftErrors, as defined in [24],
               then the 'dot5StatsSoftErrors' bit will be set.

               If the agent can perform sorting of interfaces according to the
               values of dot5StatsHardErrors, as defined in [24],
               then the 'dot5StatsHardErrors' bit will be set.

               If the agent can perform sorting of interfaces according to the
               values of dot5StatsSignalLoss, as defined in [24],
               then the 'dot5StatsSignalLoss' bit will be set.

               If the agent can perform sorting of interfaces according to the
               values of dot5StatsTransmitBeacons, as defined in [24],
               then the 'dot5StatsTransmitBeacons' bit will be set.

               If the agent can perform sorting of interfaces according to the
               values of dot5StatsRecoverys, as defined in [24],
               then the 'dot5StatsRecoverys' bit will be set.

               If the agent can perform sorting of interfaces according to the
               values of dot5StatsLobeWires, as defined in [24],
               then the 'dot5StatsLobeWires' bit will be set.

               If the agent can perform sorting of interfaces according to the
               values of dot5StatsRemoves, as defined in [24],
               then the 'dot5StatsRemoves' bit will be set.

               If the agent can perform sorting of interfaces according to the
               values of dot5StatsSingles, as defined in [24],
               then the 'dot5StatsSingles' bit will be set.

               If the agent can perform sorting of interfaces according to the
               values of dot5StatsFreqErrors, as defined in [24],
               then the 'dot5StatsFreqErrors' bit will be set.

               If the agent can perform sorting of interfaces according to the
               values of etherStatsDropEvents, as defined in [17],
               then the 'etherStatsDropEvents' bit will be set.

               If the agent can perform sorting of interfaces according to the
               values of etherStatsOctets, as defined in [17],
               then the 'etherStatsOctets' bit will be set.

               If the agent can perform sorting of interfaces according to the
               values of etherStatsPkts, as defined in [17],
               then the 'etherStatsPkts' bit will be set.

               If the agent can perform sorting of interfaces according to the
               values of etherStatsBroadcastPkts, as defined in [17],
               then the 'etherStatsBroadcastPkts' bit will be set.

               If the agent can perform sorting of interfaces according to the
               values of etherStatsMulticastPkts, as defined in [17],
               then the 'etherStatsMulticastPkts' bit will be set.

               If the agent can perform sorting of interfaces according to the
               values of etherStatsCRCAlignErrors, as defined in [17],
               then the 'etherStatsCRCAlignErrors' bit will be set.

               If the agent can perform sorting of interfaces according to the
               values of etherStatsUndersizePkts, as defined in [17],
               then the 'etherStatsUndersizePkts' bit will be set.

               If the agent can perform sorting of interfaces according to the
               values of etherStatsOversizePkts, as defined in [17],
               then the 'etherStatsOversizePkts' bit will be set.

               If the agent can perform sorting of interfaces according to the
               values of etherStatsFragments, as defined in [17],
               then the 'etherStatsFragments' bit will be set.

               If the agent can perform sorting of interfaces according to the
               values of etherStatsJabbers, as defined in [17],
               then the 'etherStatsJabbers' bit will be set.

               If the agent can perform sorting of interfaces according to the
               values of etherStatsCollisions, as defined in [17],
               then the 'etherStatsCollisions' bit will be set.

               If the agent can perform sorting of interfaces according to the
               values of etherStatsPkts64Octets, as defined in [17],
               then the 'etherStatsPkts64Octets' bit will be set.

               If the agent can perform sorting of interfaces according to the
               values of etherStatsPkts65to127Octets, as defined in [17],
               then the 'etherStatsPkts65to127Octets' bit will be set.

               If the agent can perform sorting of interfaces according to the
               values of etherStatsPkts128to255Octets, as defined in [17],
               then the 'etherStatsPkts128to255Octets' bit will be set.

               If the agent can perform sorting of interfaces according to the
               values of etherStatsPkts256to511Octets, as defined in [17],
               then the 'etherStatsPkts256to511Octets' bit will be set.

               If the agent can perform sorting of interfaces according to the
               values of etherStatsPkts512to1023Octets, as defined in [17],
               then the 'etherStatsPkts512to1023Octets' bit will be set.

               If the agent can perform sorting of interfaces according to the
               values of etherStatsPkts1024to1518Octets, as defined in [17],
               then the 'etherStatsPkts1024to1518Octets' bit will be set.


               If the agent can perform sorting of interfaces according to the
               values of dot1dTpPortInFrames, as defined in [25],
               then the 'dot1dTpPortInFrames' bit will be set.

               If the agent can perform sorting of interfaces according to the
               values of dot1dTpPortOutFrames, as defined in [25],
               then the 'dot1dTpPortOutFrames' bit will be set.

               If the agent can perform sorting of interfaces according to the
               values of dot1dTpPortInDiscards, as defined in [25],
               then the 'dot1dTpPortInDiscards' bit will be set."

       ::= { interfaceTopNObjects 1 }

     interfaceTopNControlTable OBJECT-TYPE
          SYNTAX      SEQUENCE OF InterfaceTopNControlEntry
          MAX-ACCESS  not-accessible
          STATUS      current
          DESCRIPTION
              "A table of control records for reports on the top `N'
              interfaces for the value or rate of a selected object.
              The number of entries depends on the configuration of the agent.
              The maximum number of entries is implementation
              dependent."
          ::= { interfaceTopNObjects 2 }

      interfaceTopNControlEntry OBJECT-TYPE
          SYNTAX      InterfaceTopNControlEntry
          MAX-ACCESS  not-accessible
          STATUS      current
          DESCRIPTION
                  "A set of parameters that control the creation of a
                  report of the top N ports according to several metrics."
          INDEX    { interfaceTopNControlIndex }
          ::= { interfaceTopNControlTable 1 }

      InterfaceTopNControlEntry ::= SEQUENCE {
          interfaceTopNControlIndex
              Integer32,
          interfaceTopNObjectVariable
              INTEGER,
          interfaceTopNObjectSampleType
              INTEGER,
          interfaceTopNNormalization
              INTEGER,
          interfaceTopNNormalizationFactor
              INTEGER,
          interfaceTopNControlGeneratedReports
              Counter32,
          interfaceTopNTimeRemaining
              Integer32,
          interfaceTopNDuration
              Integer32,
          interfaceTopNRequestedSize
              Integer32,
          interfaceTopNGrantedSize
              Integer32,
          interfaceTopNStartTime
              TimeStamp,
          interfaceTopNOwner
              OwnerString,
          interfaceTopNRowStatus
              RowStatus
      }

      interfaceTopNControlIndex OBJECT-TYPE
          SYNTAX      Integer32 (1 .. 65535)
          MAX-ACCESS  not-accessible
          STATUS      current
          DESCRIPTION
                  "An index that uniquely identifies an entry in the
                  interfaceTopNControl table.  Each such entry defines
                  one top N report prepared for a probe."
          ::= { interfaceTopNControlEntry 1 }


   interfaceTopNObjectVariable OBJECT-TYPE
       SYNTAX INTEGER   {
                  ifInOctets(1),
                  ifInUcastPkts(2),
                  ifInNUcastPkts(3),
                  ifInDiscards(4),
                  ifInErrors(5),
                  ifInUnknownProtos(6),
                  ifOutOctets(7),
                  ifOutUcastPkts(8),
                  ifOutNUcastPkts(9),
                  ifOutDiscards(10),
                  ifOutErrors(11),
                  ifInMulticastPkts(12),
                  ifInBroadcastPkts(13),
                  ifOutMulticastPkts(14),
                  ifOutBroadcastPkts(15),
                  ifHCInOctets(16),
                  ifHCInUcastPkts(17),
                  ifHCInMulticastPkts(18),
                  ifHCInBroadcastPkts(19),
                  ifHCOutOctets(20),
                  ifHCOutUcastPkts(21),
                  ifHCOutMulticastPkts(22),
                  ifHCOutBroadcastPkts(23),
                  dot3StatsAlignmentErrors(24),
                  dot3StatsFCSErrors(25),
                  dot3StatsSingleCollisionFrames(26),
                  dot3StatsMultipleCollisionFrames(27),
                  dot3StatsSQETestErrors(28),
                  dot3StatsDeferredTransmissions(29),
                  dot3StatsLateCollisions(30),
                  dot3StatsExcessiveCollisions(31),
                  dot3StatsInternalMacTransmitErrors(32),
                  dot3StatsCarrierSenseErrors(33),
                  dot3StatsFrameTooLongs(34),
                  dot3StatsInternalMacReceiveErrors(35),
                  dot3StatsSymbolErrors(36),
                  dot5StatsLineErrors(37),
                  dot5StatsBurstErrors(38),
                  dot5StatsACErrors(39),
                  dot5StatsAbortTransErrors(40),
                  dot5StatsInternalErrors(41),
                  dot5StatsLostFrameErrors(42),
                  dot5StatsReceiveCongestions(43),
                  dot5StatsFrameCopiedErrors(44),
                  dot5StatsTokenErrors(45),
                  dot5StatsSoftErrors(46),
                  dot5StatsHardErrors(47),
                  dot5StatsSignalLoss(48),
                  dot5StatsTransmitBeacons(49),
                  dot5StatsRecoverys(50),
                  dot5StatsLobeWires(51),
                  dot5StatsRemoves(52),
                  dot5StatsSingles(53),
                  dot5StatsFreqErrors(54),
                  etherStatsDropEvents(55),
                  etherStatsOctets(56),
                  etherStatsPkts(57),
                  etherStatsBroadcastPkts(58),
                  etherStatsMulticastPkts(59),
                  etherStatsCRCAlignErrors(60),
                  etherStatsUndersizePkts(61),
                  etherStatsOversizePkts(62),
                  etherStatsFragments(63),
                  etherStatsJabbers(64),
                  etherStatsCollisions(65),
                  etherStatsPkts64Octets(66),
                  etherStatsPkts65to127Octets(67),
                  etherStatsPkts128to255Octets(68),
                  etherStatsPkts256to511Octets(69),
                  etherStatsPkts512to1023Octets(70),
                  etherStatsPkts1024to1518Octets(71),
                  dot1dTpPortInFrames(72),
                  dot1dTpPortOutFrames(73),
                  dot1dTpPortInDiscards(74)
              }
       MAX-ACCESS read-create
       STATUS current
       DESCRIPTION
           "The particular variable to be sampled.
           Values between 1 and 23, point to MIB objects defined in
           IF-MIB [20].

           Values between 24 and 36, point to MIB objects defined in
           EtherLike-MIB [23].

           Values between 37 and 54, point to MIB objects defined in
           TOKENRING-MIB [24].

           Values between 55 and 71, point to MIB objects defined in
           RMON-MIB [17].

           Values between 72 and 74, point to MIB objects defined in
           BRIDGE-MIB [25].

           Because SNMP access control is articulated entirely in terms
           of the contents of MIB views, no access control mechanism
           exists that can restrict the value of this object to identify
           only those objects that exist in a particular MIB view.
           Because there is thus no acceptable means of restricting the
           read access that could be obtained through the TopN
           mechanism, the probe must only grant write access to this
           object in those views that have read access to all objects on
           the probe.

           During a set operation, if the supplied variable name is not
           available in the selected MIB view, or does not conform the
           other conditions mentioned above, a badValue error must be
           returned.

           This object may not be modified if the associated
           interfaceTopNControlStatus object is equal to active(1)."
       ::= { interfaceTopNControlEntry 2 }

   interfaceTopNObjectSampleType OBJECT-TYPE
       SYNTAX INTEGER {
                  absoluteValue(1),
                  deltaValue(2),
                  bandwidthPercentage(3)
              }
       MAX-ACCESS read-create
       STATUS current
       DESCRIPTION
           "The method of sampling the selected variable for storage in
           the interfaceTopNTable.

           If the value of this object is absoluteValue(1), the value of
           the selected variable will be copied directly into the topNValue.
           If the value of this object is deltaValue(2), the value of the
           selected variable at the last sample will be subtracted from
           the current value, and the difference will be stored in topNValue.

           If the value of this object is bandwidthPercentage(3), the agent
           records the total number of octets sent over an interval divided
           by the total number of octets that represent '100% bandwidth'
           for that interface. This ratio is multiplied by 1000 to
           retain a 3 digit integer (0..1000) in units of
           'tenth of one percent'. This type of computation is accurate for
           the octet counters. The usage of this option with respect to
           packets or error counters is not recommended.

           This object may not be modified if the associated
           interfaceTopNControlStatus object is equal to active(1)."
       ::= { interfaceTopNControlEntry 3 }


   interfaceTopNNormalization OBJECT-TYPE
       SYNTAX INTEGER {
                  normalizationRequired(1),
                  normalizationNotRequired(2)
              }
       MAX-ACCESS read-create
       STATUS current
       DESCRIPTION
           "The method of normalization in computation of the selected
            value.

           If the value of this object is normalizationRequired(1), the value of
           the selected variable will be multiplied by a factor equal to the
           effective speed of the interface divided by the value of
           interfaceTopNNormalizationFactor.

           If the value of this object is normalizationNot Required(2),
           the value of the selected variable will be taken 'as is' in
           the TopN computation.

           This object may not be modified if the associated
           interfaceTopNControlStatus object is equal to active(1)."
       ::= { interfaceTopNControlEntry 4 }

   interfaceTopNNormalizationFactor OBJECT-TYPE
       SYNTAX INTEGER
       MAX-ACCESS read-create
       STATUS current
       DESCRIPTION
           "The value used for normalization if interfaceTopNNormalization
           has the value normalizationRequired(1)."
       DEFVAL { 1 }
   ::= { interfaceTopNControlEntry 5 }

   interfaceTopNControlGeneratedReports OBJECT-TYPE
       SYNTAX     Counter32
       MAX-ACCESS read-only
       STATUS     current
       DESCRIPTION
           "The number of reports that have been generated by this entry."
       ::= { interfaceTopNControlEntry 6 }

     interfaceTopNTimeRemaining OBJECT-TYPE
          SYNTAX      Integer32 (0..2147483647)
          MAX-ACCESS  read-create
          STATUS      current
          DESCRIPTION
                  "The number of seconds left in the report
                  currently being collected.  When this object
                  is modified by the management station, a new
                  collection is started, possibly aborting a
                  currently running report.  The new value is
                  used as the requested duration of this report,
                  which is loaded into the associated
                  interfaceTopNDuration object.

                  When this object is set to a non-zero value,
                  any associated interfaceTopNEntries shall be
                  made inaccessible by the agent.  While the value
                  of this object is non-zero, it decrements by one
                  per second until it reaches zero.  During this
                  time, all associated interfaceTopNEntries shall
                  remain inaccessible.  At the time that this object
                  decrements to zero, the report is made accessible
                  in the interfaceTopNTable.  Thus, the interfaceTopN
                  table needs to be created only at the end of the
                  collection interval.

                  If the value of this object is set to zero
                  while the associated report is running, the
                  running report is aborted and no associated
                  interfaceTopNEntries are created."
          DEFVAL { 0 }
          ::= { interfaceTopNControlEntry 7 }

      interfaceTopNDuration OBJECT-TYPE
          SYNTAX      Integer32 (0..2147483647)
          MAX-ACCESS  read-only
          STATUS      current
          DESCRIPTION
                  "The number of seconds that this report has
                  collected during the last sampling interval,
                  or if this report is currently being collected,
                  the number of seconds that this report is being
                  collected during this sampling interval.

                  When the associated interfaceTopNTimeRemaining
                  object is set, this object shall be set by the
                  agent to the same value and shall not be modified
                  until the next time the interfaceTopNTimeRemaining
                  is set.

                  This value shall be zero if no reports have been
                  requested for this interfaceTopNControlEntry."
          ::= { interfaceTopNControlEntry 8 }

      interfaceTopNRequestedSize OBJECT-TYPE
          SYNTAX      Integer32
          MAX-ACCESS  read-create
          STATUS      current
          DESCRIPTION
                  "The maximum number of interfaces requested
                  for the Top N Table.

                  When this object is created or modified, the
                  agent should set interfaceTopNGrantedSize as close
                  to this object as is possible for the particular
                  implementation and available resources."
          DEFVAL { 10 }
          ::= { interfaceTopNControlEntry 9 }

      interfaceTopNGrantedSize OBJECT-TYPE
          SYNTAX      Integer32 (0..65535)
          MAX-ACCESS  read-only
          STATUS      current
          DESCRIPTION
                  "The maximum number of interfaces in the
                  top N table.

                  When the associated interfaceTopNRequestedSize object is
                  created or modified, the agent should set this object as
                  closely to the requested value as is possible for the
                  particular implementation and available resources.  The
                  agent must not lower this value except as a result of a
                  set to the associated interfaceTopNRequestedSize object."
          ::= { interfaceTopNControlEntry 10 }

      interfaceTopNStartTime OBJECT-TYPE
          SYNTAX      TimeStamp
          MAX-ACCESS  read-only
          STATUS      current
          DESCRIPTION
                  "The value of sysUpTime when this top N report was
                  last started.  In other words, this is the time that
                  the associated interfaceTopNTimeRemaining object was
                  modified to start the requested report.

                  If the report has not yet been started, the value
                  of this object is zero."
          ::= { interfaceTopNControlEntry 11 }

      interfaceTopNOwner OBJECT-TYPE
          SYNTAX      OwnerString
          MAX-ACCESS  read-create
          STATUS      current
          DESCRIPTION
                  "The entity that configured this entry and is
                  using the resources assigned to it."
          ::= { interfaceTopNControlEntry 12 }

      interfaceTopNRowStatus OBJECT-TYPE
          SYNTAX      RowStatus
          MAX-ACCESS  read-create
          STATUS      current
          DESCRIPTION
                 "The status of this row.

                 If the value of this object is not equal to
                 active(1), all associated entries in the
                 interfaceTopNTable shall be deleted by the
                 agent."
          ::= { interfaceTopNControlEntry 13 }


      -- Interface Top "N" reports

      interfaceTopNTable OBJECT-TYPE
          SYNTAX      SEQUENCE OF InterfaceTopNEntry
          MAX-ACCESS  not-accessible
          STATUS      current
          DESCRIPTION
                  "A table of reports for the top `N' ports based on
                  setting of associated control table entries. The
                  maximum number of entries depends on the number
                  of entries in table interfaceTopNControlTable and
                  the value of object interfaceTopNGrantedSize for
                  each entry.

                  For each entry in the interfaceTopNControlTable,
                  interfaces with the highest value of
                  interfaceTopNValue shall be placed in this table
                  in decreasing order of that rate until there is
                  no more room or until there are no more ports."
          ::= { interfaceTopNObjects 3 }

      interfaceTopNEntry OBJECT-TYPE
          SYNTAX      InterfaceTopNEntry
          MAX-ACCESS  not-accessible
          STATUS      current
          DESCRIPTION
                  "A set of statistics for an interface that is
                  part of a top N report."
          INDEX    { interfaceTopNControlIndex,
                     interfaceTopNIndex }
          ::= { interfaceTopNTable 1 }

      InterfaceTopNEntry ::= SEQUENCE {
          interfaceTopNIndex
              Integer32,
          interfaceTopNDataSourceIndex
              Integer32,
          interfaceTopNValue
              Gauge32,
          interfaceTopNValue64
              CounterBasedGauge64
      }

      interfaceTopNIndex OBJECT-TYPE
          SYNTAX      Integer32 (1..65535)
          MAX-ACCESS  not-accessible
          STATUS      current
          DESCRIPTION
                  "An index that uniquely identifies an entry in
                  the interfaceTopN table among those in the same
                  report.  This index is between 1 and N, where N
                  is the number of entries in this report.  Increasing
                  values of interfaceTopNIndex shall be assigned to
                  entries with decreasing values of interfaceTopNValue
                  until index N is assigned to the entry with the
                  lowest value of interfaceTopNValue or there are no
                  more interfaceTopNEntries.

                  No ports are included in a report where their
                  value of interfaceTopNValue would be zero."
          ::= { interfaceTopNEntry 1 }

      interfaceTopNDataSourceIndex OBJECT-TYPE
          SYNTAX      Integer32  (1..2147483647)
          MAX-ACCESS  read-only
          STATUS      current
          DESCRIPTION
                  "This object identifies the index corresponding
                   to the dataSource for this entry.

                   For sorted values of variables belonging to the
                   IF-MIB, EtherLike-MIB or TOKENRING-MIB, this value
                   equals the ifIndex of the interface.

                   For sorted values of variables belonging to the
                   RMON-MIB, this value equals the interface corresponding
                   to the data source, pointed to by the value
                   of etherStatsDataSource.

                   For sorted values of variables belonging to the
                   BRIDGE-MIB, this value equals the interface corresponding
                   to the bridge port, pointed to by the value
                   of dot1dBasePortIfIndex."
          ::= { interfaceTopNEntry 2 }

      interfaceTopNValue OBJECT-TYPE
          SYNTAX      Gauge32
          MAX-ACCESS  read-only
          STATUS      current
          DESCRIPTION
                  "The value at the end of the sampling interval, or
                  the amount of change in the selected variable
                  during this sampling interval for the identified
                  interface.  The selected variable is that interfaces's
                  instance of the object selected by
                  interfaceTopNObjectVariable.
                  This value of this object will be computed for all
                  cases when interfaceTopNObjectVariable points to a
                  32-bit counter or Gauge or when
                  interfaceTopNObjectSampleType equals bandwidthPercentage(3),
                  and will be zero for all other cases."
          ::= { interfaceTopNEntry 3 }

      interfaceTopNValue64 OBJECT-TYPE
          SYNTAX      CounterBasedGauge64
          MAX-ACCESS  read-only
          STATUS      current
          DESCRIPTION
                  "The value at the end of the sampling interval, or
                  the amount of change in the selected variable
                  during this sampling interval for the identified
                  interface.  The selected variable is that interfaces's
                  instance of the object selected by
                  interfaceTopNObjectVariable.
                  This value of this object will be computed for all
                  cases when interfaceTopNObjectVariable points to
                  a 64-bit counter, and will be zero for all other cases."
          ::= { interfaceTopNEntry 4 }


   --
   -- Notifications Section
   -- (none defined)
   --

   --
   -- Conformance Section
   --

   interfaceTopNCompliances OBJECT IDENTIFIER ::= { interfaceTopNConformance 1 }
   interfaceTopNGroups      OBJECT IDENTIFIER ::= { interfaceTopNConformance 2 }

   interfaceTopNCompliance MODULE-COMPLIANCE
       STATUS  current
       DESCRIPTION
               "Describes the requirements for conformance to the
               InterfaceTopN MIB."
           MODULE  -- this module
           MANDATORY-GROUPS { interfaceTopNGroup }
         ::= { interfaceTopNCompliances 1 }

   interfaceTopNGroup OBJECT-GROUP
       OBJECTS {
          interfaceTopNCaps,
          interfaceTopNControlIndex,
          interfaceTopNObjectVariable,
          interfaceTopNObjectSampleType,
          interfaceTopNNormalization,
          interfaceTopNNormalizationFactor,
          interfaceTopNControlGeneratedReports,
          interfaceTopNTimeRemaining,
          interfaceTopNDuration,
          interfaceTopNRequestedSize,
          interfaceTopNGrantedSize,
          interfaceTopNStartTime,
          interfaceTopNOwner,
          interfaceTopNRowStatus,
          interfaceTopNIndex,
          interfaceTopNDataSourceIndex,
          interfaceTopNValue,
          interfaceTopNValue64
       }
       STATUS  current
       DESCRIPTION
               "A collection of objects providing interfaceTopN data for
               a multiple interfaces device."
   ::= { interfaceTopNGroups 1 }



   END

-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
