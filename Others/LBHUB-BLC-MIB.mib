-- Copyright 1995 by 3Com Corporation.  All rights reserved.
-- MIB file name:  lbhub-blc.mib
-- available in these 3Com devices:  MSH hubs with bridge module
-- For support or more info, check 3Com's web page at http://www.3com.com


-- --------------------------------------------------------------------
-- ************ THE STARTING POINT FOR ALL MIB DEFINITIONS ************
-- --------------------------------------------------------------------


          LBHUB-BLC-MIB DEFINITIONS ::= BEGIN

          IMPORTS
   		mgmt,  NetworkAddress, IpAddress, Counter,
  	 	Gauge, TimeTicks, OBJECT-TYPE
   		FROM RFC1155-SMI
			TRAP-TYPE FROM RFC-1215;


          --  MIB-II (same prefix as MIB-I)

          mib-2      OBJECT IDENTIFIER ::= { mgmt 1 }

          -- textual conventions

          DisplayString ::= OCTET STRING
          -- This data type is used to model textual information taken
          -- from the NVT ASCII character set.  By convention, objects
          -- with this syntax are declared as having
          --
          --      SIZE (0..255)

          PhysAddress ::= OCTET STRING
          -- This data type is used to model media addresses.  For many
          -- types of media, this will be in a binary representation.
          -- For example, an ethernet address would be represented as
          -- a string of 6 octets.

-- groups in MIB-II

   system     			OBJECT IDENTIFIER ::= { mib-2 1 }
   interfaces 			OBJECT IDENTIFIER ::= { mib-2 2 }
   at         			OBJECT IDENTIFIER ::= { mib-2 3 }
   ip         			OBJECT IDENTIFIER ::= { mib-2 4 }
   icmp       			OBJECT IDENTIFIER ::= { mib-2 5 }
   udp        			OBJECT IDENTIFIER ::= { mib-2 7 }
   egp        			OBJECT IDENTIFIER ::= { mib-2 8 }
   cmot       			OBJECT IDENTIFIER ::= { mib-2 9 }
   transmission  		OBJECT IDENTIFIER ::= { mib-2 10 }
   snmp          		OBJECT IDENTIFIER ::= { mib-2 11 }


-- This part of the MIB handles RFC 1229
-- (Extensions to the Generic Interface MIB)
-- with mib node assignment from RFC 1239

   ifExtensions  		OBJECT IDENTIFIER ::= { mib-2 12 }


--  this is the MIB module for ethernet-like objects (RFC1284)

    dot3    OBJECT IDENTIFIER ::= { transmission 7 }

   --  802.3 Hardware Chipsets

   -- The object ifExtnsChipSet is provided in [11] to identify the
   -- MAC hardware used to communcate on an interface.  The following
   -- hardware chipsets are provided for 802.3:

   dot3ChipSets          OBJECT IDENTIFIER ::= { dot3 8 }
   dot3ChipSetAMD        OBJECT IDENTIFIER ::= { dot3ChipSets 1 }
   dot3ChipSetAMD7990    OBJECT IDENTIFIER ::= { dot3ChipSetAMD 1 }


-- IETF Bridge MIB, as defined bu RFC1286

   dot1dBridge                  OBJECT IDENTIFIER ::= { mib-2 17 }

-- groups in the Bridge MIB

   dot1dBase                    OBJECT IDENTIFIER ::= { dot1dBridge 1 }

   dot1dStp                     OBJECT IDENTIFIER ::= { dot1dBridge 2 }

   dot1dTp                      OBJECT IDENTIFIER ::= { dot1dBridge 4 }

   dot1dStatic                  OBJECT IDENTIFIER ::= { dot1dBridge 5 }


-- groups in 3Com Enterprise

   private       		OBJECT IDENTIFIER ::= { internet 4 }
   enterprises   		OBJECT IDENTIFIER ::= { private 1 }

   a3Com                        OBJECT IDENTIFIER ::= { enterprises 43 }

   products          	        OBJECT IDENTIFIER ::= { a3Com 1 }

   brouter                     	OBJECT IDENTIFIER ::= { products 4 }
   lBridgeECS                   OBJECT IDENTIFIER ::= { brouter 3 }

   blc                     	OBJECT IDENTIFIER ::= { a3Com 12 }
   blcAgent                	OBJECT IDENTIFIER ::= { blc 1 }
   blcControl                	OBJECT IDENTIFIER ::= { blc 2 }
   blcDataBase                	OBJECT IDENTIFIER ::= { blc 3 }
   blcPcolFilter  		OBJECT IDENTIFIER ::= { blc 4 }
   accessGroupDBase 		OBJECT IDENTIFIER ::= { blc 5 }

   ecsXENDOFMIB			OBJECT IDENTIFIER ::= { blc 255 }


-- MIB-II Definition for the bridge line card


-- RFC 1229 Extensions to the Generic Interface Table

--          ifExtensions  OBJECT IDENTIFIER ::= { mib-2 6 }


          --   Generic Interface Extension Table
          --
          --  This group of objects is mandatory for all types of
          --  subnetwork interface.

          ifExtnsTable  OBJECT-TYPE
                  SYNTAX SEQUENCE OF IfExtnsEntry
                  ACCESS not-accessible
                  STATUS mandatory
                  DESCRIPTION
                         "A list of interfaces extension entries.
                          The number of entries is given by the value
                          of ifNumber, defined in [4,6]."
                  ::= { ifExtensions 1 }

          ifExtnsEntry  OBJECT-TYPE
                  SYNTAX IfExtnsEntry
                  ACCESS not-accessible
                  STATUS mandatory
                  DESCRIPTION
                         "An extension to the interfaces entry,
                          defined in [4,6], containing additional
                          objects at the subnetwork layer and below
                          for a particular interface."
                  INDEX  { ifExtnsIfIndex }
                  ::= { ifExtnsTable 1 }

          IfExtnsEntry ::=
                  SEQUENCE {
                      ifExtnsIfIndex
                          INTEGER,
                      ifExtnsChipSet
                          OBJECT IDENTIFIER,
                      ifExtnsRevWare
                          DisplayString,
                      ifExtnsMulticastsTransmittedOks
                          Counter,
                      ifExtnsBroadcastsTransmittedOks
                          Counter,
                      ifExtnsMulticastsReceivedOks
                          Counter,
                      ifExtnsBroadcastsReceivedOks
                          Counter,
                      ifExtnsPromiscuous
                          INTEGER
                  }

          ifExtnsIfIndex  OBJECT-TYPE
                  SYNTAX INTEGER
                  ACCESS read-only
                  STATUS mandatory
                  DESCRIPTION
                         "The value of this object identifies the
                          interface for which this entry contains
                          extended management information.  The value
                          of this object for a particular interface
                          has the same value as the ifIndex object,
                          defined in [4,6], for the same interface."
                  ::= { ifExtnsEntry 1 }

          ifExtnsChipSet  OBJECT-TYPE
                  SYNTAX OBJECT IDENTIFIER
                  ACCESS read-only
                  STATUS mandatory
                  DESCRIPTION
                         "This object identifies the hardware chip
                          set being used in the interface.  The
                          assignment of OBJECT IDENTIFIERs to various
                          types of hardware chip sets is managed
                          by the IANA.  If the hardware chip set is
                          unknown, the object identifier

                          unknownChipSet OBJECT IDENTIFIER ::= { 0 0 }

                          is returned.  Note that unknownChipSet is a
                          syntactically valid object identifier, and
                          any conformant implementation of ASN.1 and
                          the BER must be able to generate and
                          recognize this value."
                  ::= { ifExtnsEntry 2 }

          ifExtnsRevWare  OBJECT-TYPE
                  SYNTAX DisplayString (SIZE (0..255))
                  ACCESS read-only
                  STATUS mandatory
                  DESCRIPTION
                         "An arbitrary octet string that describes
                          the firmware version of this interface.
                          It is intended that this should be human
                          readable.  It must only contain ASCII
                          printable characters.  Typically this
                          will be the firmware version of the main
                          interface software."
                  ::= { ifExtnsEntry 3 }

          ifExtnsMulticastsTransmittedOks OBJECT-TYPE
                  SYNTAX Counter
                  ACCESS read-only
                  STATUS mandatory
                  DESCRIPTION
                         "The count of frames successfully
                          transmitted to a subnetwork or link-layer
                          multicast destination address other than a
                          broadcast address.  For a MAC layer protocol,
                          this includes both Group and Functional
                          addresses."
                  ::= { ifExtnsEntry 4 }

          ifExtnsBroadcastsTransmittedOks OBJECT-TYPE
                  SYNTAX Counter
                  ACCESS read-only
                  STATUS mandatory
                  DESCRIPTION
                         "The count of frames successfully
                          transmitted to a subnetwork or link-layer
                          broadcast addresses.  It does not include
                          frames sent to a multicast address."
                  ::= { ifExtnsEntry 5 }

          ifExtnsMulticastsReceivedOks OBJECT-TYPE
                  SYNTAX Counter
                  ACCESS read-only
                  STATUS mandatory
                  DESCRIPTION
                         "The count of frames successfully received
                          that are directed to an active subnetwork
                          or link-layer multicast address (for a MAC
                          layer protocol, this includes both Group and
                          Functional addresses). This does not include
                          frames directed to a broadcast address, nor
                          frames received with errors."
                  ::= { ifExtnsEntry 6 }

          ifExtnsBroadcastsReceivedOks OBJECT-TYPE
                  SYNTAX Counter
                  ACCESS read-only
                  STATUS mandatory
                  DESCRIPTION
                         "The count of frames successfully received
                          that are directed to a subnetwork or
                          link-layer broadcast address.  This does not
                          include frames received with errors."
                  ::= { ifExtnsEntry 7 }

          ifExtnsPromiscuous  OBJECT-TYPE
                  SYNTAX INTEGER {
                              true(1),
                              false(2)
                         }
                  ACCESS read-only  -- Note: agent implementors are
                                    -- encouraged to extend this
                                    -- access to read-write if that
                                    -- makes sense in their agent.
                  STATUS mandatory
                  DESCRIPTION
                         "This object has a value of false(2) if
                          this interface only accepts packets/frames
                          that are addressed to this station. This
                          object has a value of true(1) when the
                          station accepts all packets/frames
                          transmitted on the media.  The value
                          true(1) is only legal on certain types of
                          media.  If legal, setting this object to a
                          value of true(1) may require the interface
                          to be reset before becoming effective."
                 ::= { ifExtnsEntry 8 }

          --
          --   The  Generic Interface Test Table is not implemented
	  --


          --   Generic Receive Address Table
          --
          -- This group of objects is mandatory for all types of
          -- interfaces which can receive packets/frames addressed to
          -- more than one address.

          ifExtnsRcvAddrTable  OBJECT-TYPE
                  SYNTAX SEQUENCE OF IfExtnsRcvAddrEntry
                  ACCESS not-accessible
                  STATUS mandatory
                  DESCRIPTION
                         "This table contains an entry for each
                          address (broadcast, multicast, or uni-cast)
                          for which the system will receive packets/
                          frames on a particular interface.  When an
                          interface is operating in promiscuous mode,
                          entries are only required for those addresses
                          for which the system would receive frames
                          were it not operating in promiscuous mode."
                  ::= { ifExtensions 3 }

          ifExtnsRcvAddrEntry  OBJECT-TYPE
                  SYNTAX IfExtnsRcvAddrEntry
                  ACCESS not-accessible
                  STATUS mandatory
                  DESCRIPTION
                         "A list of objects identifying an address
                          for which the system will accept packets/
                          frames on a particular interface."
                  INDEX  { ifExtnsRcvAddrIfIndex, ifExtnsRcvAddress }
                  ::= { ifExtnsRcvAddrTable 1 }

          IfExtnsRcvAddrEntry ::=
                  SEQUENCE {
                      ifExtnsRcvAddrIfIndex
                          INTEGER,
                      ifExtnsRcvAddress
                          PhysAddress,
                      ifExtnsRcvAddrStatus
                          INTEGER
                  }

          ifExtnsRcvAddrIfIndex  OBJECT-TYPE
                  SYNTAX INTEGER
                  ACCESS read-only
                  STATUS mandatory
                  DESCRIPTION
                         "The value of ifIndex, defined in [4,6], of an
                          interface which recognizes this entry's
                          address."
                  ::= { ifExtnsRcvAddrEntry 1 }

          ifExtnsRcvAddress OBJECT-TYPE
                  SYNTAX OCTET STRING
                  ACCESS read-only
                  STATUS mandatory
                  DESCRIPTION
                         "An address for which the system will accept
                          packets/frames on this entry's interface."
                  ::= { ifExtnsRcvAddrEntry 2 }

          ifExtnsRcvAddrStatus OBJECT-TYPE
                  SYNTAX INTEGER {
                             other(1),
                             invalid(2),
                             volatile(3),
                             nonVolatile(4)
                         }
                  ACCESS read-write
                  STATUS mandatory
                  DESCRIPTION
                         "This object has the value nonVolatile(4)
                          for those entries in the table which are
                          valid and will not be deleted by the next
                          restart of the managed system.  Entries
                          having the value volatile(3) are valid
                          and exist, but have not been saved, so
                          that will not exist after the next
                          restart of the managed system.  Entries
                          having the value other(1) are valid and
                          exist but are not classified as to whether
                          they will continue to exist after the next
                          restart.  Entries having the value invalid(2)
                          are invalid and do not represent an address
                          for which an interface accepts frames.
                              Setting an object instance to one of
                          the values other(1), volatile(3), or
                          nonVolatile(4) causes the corresponding
                          entry to exist or continue to exist, and
                          to take on the respective status as regards
                          the next restart of the managed system.
                              Setting an object instance to the value
                          invalid(2) causes the corresponding entry
                          to become invalid or cease to exist.
                              It is an implementation-specific matter
                          as to whether the agent removes an
                          invalidated entry from the table.
                          Accordingly, management stations must be
                          prepared to receive tabular information
                          from agents that corresponds to entries not
                          currently in use.  Proper interpretation of
                          such entries requires examination of the
                          relevant ifExtnsRcvAddrStatus object
                          instance."
--                  DEFVAL  { volatile }
                  ::= { ifExtnsRcvAddrEntry 3 }


-- RFC 1286
-- (Definitions of Managed Objects for the Ethernet-like Interface Types)



    -- the Generic Ethernet-like group

    dot3Table OBJECT-TYPE
        SYNTAX  SEQUENCE OF Dot3Entry
        ACCESS  not-accessible
        STATUS  mandatory
        DESCRIPTION
                "Status information and control variables for a
                collection of ethernet-like interfaces attached to
                a particular system."
        ::= { dot3 1 }

    dot3Entry OBJECT-TYPE
        SYNTAX  Dot3Entry
        ACCESS  not-accessible
        STATUS  mandatory
        DESCRIPTION
                "Status information and control variables for a
                particular interface to an ethernet-like medium."
        INDEX   { dot3Index }
        ::= { dot3Table 1 }

    Dot3Entry ::=
        SEQUENCE {
            dot3Index
                INTEGER,
            dot3InitializeMac
                INTEGER,
            dot3MacSubLayerStatus
                INTEGER,
            dot3MulticastReceiveStatus
                INTEGER,
            dot3TxEnabled
                INTEGER,
            dot3TestTdrValue
                Gauge
       }

    dot3Index OBJECT-TYPE
        SYNTAX  INTEGER
        ACCESS  read-only
        STATUS  mandatory
        DESCRIPTION
                "An index value that uniquely identifies an
                interface to an ethernet-like medium.  The
                interface identified by a particular value of this
                index is the same interface as identified by the
                same value of ifIndex."
        ::= { dot3Entry 1 }

    dot3InitializeMac OBJECT-TYPE
        SYNTAX  INTEGER { initialized(1), uninitialized(2) }
        ACCESS  read-write
        STATUS  mandatory
        DESCRIPTION
                "The initialization status of the MAC and PLS
                (Physical Layer Signalling) subsystems for a
                particular interface. The value initialized(1)
                signifies that the subsystems for a particular
                interface have been previously initialized; the
                value uninitialized(2) signifies that they have
                not been previously initialized.

                Each alteration of an instance of this object to
                either of the values initialized(1) or
                uninitialized(2) is analogous to an invocation of
                the initializeMAC action defined in [9] and has
                the effect of (re-)initializing the MAC and PLS
                subsystems for the associated interface. In
                particular,

                     all management counters pertaining to the MAC
                     and PLS subsystems for said interface are
                     reset to zero;

                     the receive and transmit layer management
                     state variables (receiveEnabled and
                     transmitEnabled in [9]) are set to enable
                     reception and transmission of frames;

                     the promiscuous receive function is disabled;
                     and

                     multicast reception is disabled."
        ::= { dot3Entry 2 }

    dot3MacSubLayerStatus OBJECT-TYPE
        SYNTAX  INTEGER { enabled(1), disabled(2) }
        ACCESS  read-write
        STATUS  mandatory
        DESCRIPTION
                "The operational status of the MAC sublayer for a
                particular interface.  The value enabled(1)
                signifies that the MAC sublayer for said interface
                is operational for both transmitting and receiving
                frames -- that is, that the value of both the
                receive and transmit layer management state
                variables (receiveEnabled and transmitEnabled in
                [9]) for said interface are true.  The value
                disabled(2) signifies that the MAC sublayer for
                said interface is not operational for either
                transmitting or receiving frames. In particular,
                the value of an instance of this object is
                disabled(2) whenever the value of the
                corresponding instance of the dot3Enabled object
                is false(2).

                Each alteration of an instance of this object to
                the value enabled(1) is analogous to an invocation
                of the enableMACSublayer action defined in [9] and
                has the effect of starting normal transmit and
                receive operations (from the ``idle'' state) on
                the associated interface. In particular, such an
                alteration has the effect of resetting the PLS for
                said interface and of setting the receive and
                transmit layer management state variables
                (receiveEnabled and transmitEnabled in [9]) to be
                true.

                Each alteration of an instance of this object to
                the value disabled(2) is analogous to an
                invocation of the disableMACSublayer action
                defined in [9] and has the effect of terminating
                transmit and receive operations on the associated
                interface. In particular, such an alteration has
                the effect of setting the receive and transmit
                layer management state variables (receiveEnabled
                and transmitEnabled in [9]) to be false. Any
                transmissions/receptions in progress are completed
                before operation is terminated."
        ::= { dot3Entry 3 }

    dot3MulticastReceiveStatus OBJECT-TYPE
        SYNTAX  INTEGER { enabled(1), disabled(2) }
        ACCESS  read-write
        STATUS  mandatory
        DESCRIPTION
                "The multicast receive status for a particular
                interface.  The value enabled(1) signifies that
                reception of multicast frames by the MAC sublayer
                is enabled on said interface. The value
                disabled(2) signifies that reception of multicast
                frames by the MAC sublayer is not enabled on said
                interface.

                Each alteration of an instance of this object to
                the value enabled(1) is analogous to an invocation
                of the enableMulticastReceive action defined in
                [9] and has the effect of enabling multicast frame
                reception on the associated interface. Actual
                reception of multicast frames is only possible on
                an interface when the values for the associated
                instances of the dot3MulticastReceiveStatus and
                dot3MacSubLayerStatus objects are enabled(1) and
                enabled(1), respectively.

                Each alteration of an instance of this object to
                the value disabled(2) is analogous to an
                invocation of the disableMulticastReceive action
                defined in [9] and has the effect of inhibiting
                multicast frame reception on the associated
                interface."
        ::= { dot3Entry 4 }

    dot3TxEnabled OBJECT-TYPE
        SYNTAX  INTEGER { true(1), false(2)  }
        ACCESS  read-write
        STATUS  mandatory
        DESCRIPTION
                "The transmit layer management state variable
                (transmitEnabled as defined in [9]) for a
                particular interface.  The value true(1) signifies
                that the MAC frame transmission is enabled on said
                interface. The value false(2) signifies that the
                MAC frame transmission is inhibited on said
                interface. In particular, the value of an instance
                of this object is false(2) whenever the value of
                the corresponding instance of the
                dot3MacSubLayerStatus object is disabled(2).

                Each alteration of an instance of this object to
                the value true(1) is analogous to an invocation of
                the enableTransmit action defined in [9] and has
                the effect of enabling MAC sublayer frame
                transmission on the associated interface. In
                particular, such an alteration has the effect of
                setting the transmit layer management state
                variable (transmitEnabled in [9]) for said
                interface to be true.

                Each alteration of an instance of this object to
                the value false(2) is analogous to an invocation
                of the disableTransmit action defined in [9] and
                has the effect of inhibiting MAC sublayer frame
                transmission on the associated interface. In
                particular, such an alteration has the effect of
                setting the transmit layer management state
                variable (transmitEnabled in [9]) for said
                interface to be false. Any transmissions in
                progress are completed before transmission is
                inhibited."
        ::= { dot3Entry 5 }

    dot3TestTdrValue OBJECT-TYPE
        SYNTAX  Gauge
        ACCESS  read-only
        STATUS  mandatory
        DESCRIPTION
               "The number of 10 MHz ticks which elapsed between
               the beginning of a TDR measurement and the
               collision which ended it, for the most recently
               executed TDR test.  If no TDR test has been
               executed, or the last TDR value is not available,
              this object has the value 0."
        ::= { dot3Entry 6 }

    -- the Ethernet-like Statistics group

    -- Implementation of this group is mandatory

    -- Due to implementation restrictions (e.g. in the
    -- instrumentation provided by a chipset, or a device
    -- driver), some of the counters in this group may be
    -- difficult or impossible to implement.
    -- In such cases, an implementator should apply reasonable
    -- best effort to detect as many occurrences as possible.
    -- In any case, the value of a counter will be the number
    -- actually detected, which will always be less or equal
    -- to the number of actual occurrences.  In the extreme
    -- case of a total inability to detect occurrences, the
    -- counter will always be zero.

    -- Vendors are strongly encouraged to document in user guides and
    -- other appropriate documentation the conditions under which the
    -- values of the counters in this group may represent an
    -- underestimate of the true count.

    dot3StatsTable OBJECT-TYPE
        SYNTAX  SEQUENCE OF Dot3StatsEntry
        ACCESS  not-accessible
        STATUS  mandatory
        DESCRIPTION
                "Statistics for a collection of ethernet-like
                interfaces attached to a particular system."
        ::= { dot3 2 }

    dot3StatsEntry OBJECT-TYPE
        SYNTAX  Dot3StatsEntry
        ACCESS  not-accessible
        STATUS  mandatory
        DESCRIPTION
                "Statistics for a particular interface to an
                ethernet-like medium."
        INDEX   { dot3StatsIndex }
        ::= { dot3StatsTable 1 }

    Dot3StatsEntry ::=
        SEQUENCE {
            dot3StatsIndex
                INTEGER,
            dot3StatsAlignmentErrors
                Counter,
            dot3StatsFCSErrors
                Counter,
            dot3StatsSingleCollisionFrames
                Counter,
            dot3StatsMultipleCollisionFrames
                Counter,
            dot3StatsSQETestErrors
                Counter,
            dot3StatsDeferredTransmissions
                Counter,
            dot3StatsLateCollisions
                Counter,
            dot3StatsExcessiveCollisions
                Counter,
            dot3StatsInternalMacTransmitErrors
                Counter,
            dot3StatsCarrierSenseErrors
                Counter,
            dot3StatsExcessiveDeferrals
                Counter,
            dot3StatsFrameTooLongs
                Counter,
            dot3StatsInRangeLengthErrors
                Counter,
            dot3StatsOutOfRangeLengthFields
                Counter,
            dot3StatsInternalMacReceiveErrors
                Counter
        }

    dot3StatsIndex OBJECT-TYPE
        SYNTAX  INTEGER
        ACCESS  read-only
        STATUS  mandatory
        DESCRIPTION
                "An index value that uniquely identifies an
                interface to an ethernet-like medium.  The
                interface identified by a particular value of this
                index is the same interface as identified by the
                same value of ifIndex."
        ::= { dot3StatsEntry 1 }

    dot3StatsAlignmentErrors OBJECT-TYPE
        SYNTAX  Counter
        ACCESS  read-only
        STATUS  mandatory
        DESCRIPTION
                "A count of frames received on a particular
                interface that are not an integral number of
                octets in length and do not pass the FCS check.
                The count represented by an instance of this
                object is incremented when the alignmentError
                status is returned by the MAC service to the LLC
                (or other MAC user). Received frames for which
                multiple error conditions obtain are, according to
                the conventions of [9], counted exclusively
                according to the error status presented to the
                LLC."
        ::= { dot3StatsEntry 2 }

    dot3StatsFCSErrors OBJECT-TYPE
        SYNTAX  Counter
        ACCESS  read-only
        STATUS  mandatory
        DESCRIPTION
                "A count of frames received on a particular
                interface that are an integral number of octets in
                length but do not pass the FCS check.

                The count represented by an instance of this
                object is incremented when the frameCheckError
                status is returned by the MAC service to the LLC
                (or other MAC user). Received frames for which
                multiple error conditions obtain are, according to
                the conventions of [9], counted exclusively
                according to the error status presented to the
                LLC."
        ::= { dot3StatsEntry 3 }

    dot3StatsSingleCollisionFrames OBJECT-TYPE
        SYNTAX  Counter
        ACCESS  read-only
        STATUS  mandatory
        DESCRIPTION
                "A count of successfully transmitted frames on a
                particular interface for which transmission is
                inhibited by exactly one collision.

                A frame that is counted by an instance of this
                object is also counted by the corresponding
                instance of either the ifOutUcastPkts or
                ifOutNUcastPkts object and is not counted by the
                corresponding instance of the
                dot3StatsMultipleCollisionFrames object."
       ::= { dot3StatsEntry 4 }

    dot3StatsMultipleCollisionFrames OBJECT-TYPE
        SYNTAX  Counter
        ACCESS  read-only
        STATUS  mandatory
        DESCRIPTION
                "A count of successfully transmitted frames on a
                particular interface for which transmission is
                inhibited by more than one collision.

                A frame that is counted by an instance of this
                object is also counted by the corresponding
                instance of either the ifOutUcastPkts or
                ifOutNUcastPkts object and is not counted by the
                corresponding instance of the
                dot3StatsSingleCollisionFrames object."
        ::= { dot3StatsEntry 5 }

    dot3StatsSQETestErrors OBJECT-TYPE
        SYNTAX  Counter
        ACCESS  read-only
        STATUS  mandatory
        DESCRIPTION
                "A count of times that the SQE TEST ERROR message
                is generated by the PLS sublayer for a particular
                interface. The SQE TEST ERROR message is defined
                in section 7.2.2.2.4 of [12] and its generation is
                described in section 7.2.4.6 of the same
                document."
        ::= { dot3StatsEntry 6 }

    dot3StatsDeferredTransmissions OBJECT-TYPE
        SYNTAX  Counter
        ACCESS  read-only
        STATUS  mandatory
        DESCRIPTION
                "A count of frames for which the first
                transmission attempt on a particular interface is
                delayed because the medium is busy.

                The count represented by an instance of this
                object does not include frames involved in
                collisions."
        ::= { dot3StatsEntry 7 }

    dot3StatsLateCollisions OBJECT-TYPE
        SYNTAX  Counter
        ACCESS  read-only
        STATUS  mandatory
        DESCRIPTION
                "The number of times that a collision is detected
                on a particular interface later than 512 bit-times
                into the transmission of a packet.

                Five hundred and twelve bit-times corresponds to
                51.2 microseconds on a 10 Mbit/s system. A (late)
                collision included in a count represented by an
                instance of this object is also considered as a
                (generic) collision for purposes of other
                collision-related statistics."
        ::= { dot3StatsEntry 8 }

    dot3StatsExcessiveCollisions OBJECT-TYPE
        SYNTAX  Counter
        ACCESS  read-only
        STATUS  mandatory
        DESCRIPTION
                "A count of frames for which transmission on a
                particular interface fails due to excessive
                collisions."
        ::= { dot3StatsEntry 9 }

    dot3StatsInternalMacTransmitErrors OBJECT-TYPE
        SYNTAX  Counter
        ACCESS  read-only
        STATUS  mandatory
        DESCRIPTION
                "A count of frames for which transmission on a
                particular interface fails due to an internal MAC
                sublayer transmit error. A frame is only counted
                by an instance of this object if it is not counted
                by the corresponding instance of either the
                dot3StatsLateCollisions object, the
                dot3StatsExcessiveCollisions object, the
                dot3StatsCarrierSenseErrors object, or the
                dot3StatsExcessiveDeferrals object.

                The precise meaning of the count represented by an
                instance of this object is implementation-
                specific.  In particular, an instance of this
                object may represent a count of transmission
                errors on a particular interface that are not
                otherwise counted."
        ::= { dot3StatsEntry 10 }


    dot3StatsCarrierSenseErrors OBJECT-TYPE
        SYNTAX  Counter
        ACCESS  read-only
        STATUS  mandatory
        DESCRIPTION
                "The number of times that the carrier sense
                condition was lost or never asserted when
                attempting to transmit a frame on a particular
                interface.

                The count represented by an instance of this
                object is incremented at most once per
                transmission attempt, even if the carrier sense
                condition fluctuates during a transmission
                attempt."
        ::= { dot3StatsEntry 11 }

    dot3StatsExcessiveDeferrals OBJECT-TYPE
        SYNTAX  Counter
        ACCESS  read-only
        STATUS  mandatory
        DESCRIPTION
                "A count of frames for which transmission on a
                particular interface is deferred for an excessive
                period of time."
        ::= { dot3StatsEntry 12 }

    dot3StatsFrameTooLongs OBJECT-TYPE
        SYNTAX  Counter
        ACCESS  read-only
        STATUS  mandatory
        DESCRIPTION
                "A count of frames received on a particular
                interface that exceed the maximum permitted frame
                size.

                The count represented by an instance of this
                object is incremented when the frameTooLong status
                is returned by the MAC service to the LLC (or
                other MAC user). Received frames for which
                multiple error conditions obtain are, according to
                the conventions of [9], counted exclusively
                according to the error status presented to the
                LLC."
        ::= { dot3StatsEntry 13 }


    dot3StatsInRangeLengthErrors OBJECT-TYPE
        SYNTAX  Counter
        ACCESS  read-only
        STATUS  mandatory
        DESCRIPTION
                "A count of frames received on a particular
                interface with a length field value that falls
                between the minimum unpadded LLC data size and the
                maximum allowed LLC data size inclusive and that
                does not match the number of LLC data octets
                received.

                The count represented by an instance of this
                object also includes frames for which the length
                field value is less than the minimum unpadded LLC
                data size."
        ::= { dot3StatsEntry 14 }

    dot3StatsOutOfRangeLengthFields OBJECT-TYPE
        SYNTAX  Counter
        ACCESS  read-only
        STATUS  mandatory
        DESCRIPTION
                "A count of frames received on a particular
                interface for which the length field value exceeds
                the maximum allowed LLC data size.

                The count represented by an instance of this
                object is not incremented in implementations that
                observe Ethernet encapsulation conventions (by
                which the IEEE 802.3 length field is interpreted
                as the Ethernet Type field)."
        ::= { dot3StatsEntry 15 }

    dot3StatsInternalMacReceiveErrors OBJECT-TYPE
        SYNTAX  Counter
        ACCESS  read-only
        STATUS  mandatory
        DESCRIPTION
                "A count of frames for which reception on a
                particular interface fails due to an internal MAC
                sublayer receive error. A frame is only counted by
                an instance of this object if it is not counted by
                the corresponding instance of either the
                dot3StatsFrameTooLongs object, the
                dot3StatsAlignmentErrors object, the
                dot3StatsFCSErrors object, the
                dot3StatsInRangeLengthErrors object, or the
                dot3StatsOutOfRangeLengthFields object.

                The precise meaning of the count represented by an
                instance of this object is implementation-
                specific.  In particular, an instance of this
                object may represent a count of receive errors on
                a particular interface that are not otherwise
                counted."
        ::= { dot3StatsEntry 16 }



-- Bridge Line Card Extensions




--  BLC SPECIFIC GROUPS FOR THE AGENT

-- The blcAgent Group (blc 1)

              blcAgentIpAddr OBJECT-TYPE
                       SYNTAX 		IpAddress
                       ACCESS read-write
                       STATUS mandatory
 		       DESCRIPTION
 		       "The network management module's administrative IpAddress. The
                       current operational IpAddress can be obtained from the
                       ipAdEntAddr entry in the ipAddrTable."
                       ::=  { blcAgent 1 }

               blcAgentIpNetmask OBJECT-TYPE
                       SYNTAX 		IpAddress
                       ACCESS read-write
                       STATUS mandatory
 		       DESCRIPTION
 		       "The network management module's administrative subnet mask.
                       The current operational subnet mask can be obtained from
                       the ipAdEntNetMask entry in the ipAddrTable."
                       ::=  { blcAgent 2 }

             blcAgentIpBroadAddr OBJECT-TYPE
                       SYNTAX 		IpAddress
                       ACCESS read-write
                       STATUS mandatory
 		       DESCRIPTION
 		       "The network management module's adminstrative default
                       broadcast address"
                       ::=  { blcAgent 3 }

               blcAgentDefaultGateway OBJECT-TYPE
                       SYNTAX 		IpAddress
                       ACCESS read-write
                       STATUS mandatory
 		       DESCRIPTION
 		       "The network management module's administrative default
                       gateway IpAddress. The current operational default
                       gateway's IpAddress can be obtained from the ipRoutingTable."
                       ::=  { blcAgent 4 }

               blcAgentMACAddress OBJECT-TYPE
                       SYNTAX OCTET STRING
                       ACCESS read-only
                       STATUS mandatory
 		       DESCRIPTION
 		       "The  MAC address of the BLC Agent."
                       ::=  { blcAgent 5 }

               blcAgentAuthenticationStatus OBJECT-TYPE
                       SYNTAX INTEGER {
                                   enabled(1),  -- the address checking of management frames inhibited
                                   disabled(2)    -- the address checking of management frames enabled
	   	              }
                       ACCESS read-only
                       STATUS mandatory
 		       DESCRIPTION
 		       "Indicates whether management frames are checked against entries
 			in the management tranmiter table."
                       ::=  { blcAgent 6 }

              blcAgentResetDevice OBJECT-TYPE
                       SYNTAX INTEGER {
			                 notreset(1),	-- not resetting
			                 reset(2)	-- resetting
		              }
                       ACCESS read-write
                       STATUS mandatory
 		       DESCRIPTION
 		       "Network management module reset status. Writing a 2 to this
                       object will reset the management agent."
                       ::=  { blcAgent 7 }

               blcAgentDefaultConfig OBJECT-TYPE
                       SYNTAX INTEGER {
			                normal(1),		-- not reverting to original
						                -- configuration
			                reverting(2)		-- reverting to orig config
		             }
                       ACCESS read-write
                       STATUS mandatory
 		       DESCRIPTION
 		       "The device is returned to its factory settings."
                       ::=  { blcAgent 8 }

-- blcAgentManagementTable Object Type Names


               blcAgentManagementTable OBJECT-TYPE
                       SYNTAX SEQUENCE OF BLCAgentManagementEntry
                       ACCESS not-accessible
                       STATUS mandatory
 		       DESCRIPTION
 		       "This entity's management address table. (10 entries)"
                       ::=  { blcAgent 9 }

               blcAgentManagementEntry OBJECT-TYPE
                       SYNTAX BLCAgentManagementEntry
                       ACCESS  not-accessible
                       STATUS mandatory
 		       DESCRIPTION
 		       "A source address address and privileges of a particular
                       management station."
                       INDEX   { blcAgentManagementAddr }
                       ::=   { blcAgentManagementTable 1 }

               BLCAgentManagementEntry ::= SEQUENCE {
		       blcAgentManagementAddr
			  IpAddress,
		       blcAgentManagementAccess
		          INTEGER
	       }


               blcAgentManagementAddr OBJECT-TYPE
                       SYNTAX 	IpAddress
                       ACCESS read-write
                       STATUS mandatory
		       DESCRIPTION
 		       "IpAddress of the manager."
                       ::=  { blcAgentManagementEntry 1 }

               blcAgentManagementAccess OBJECT-TYPE
                       SYNTAX INTEGER {
					invalid(1),	-- entry is deleted
			                off(2),		-- management packets will
					superread(3),	-- allowed to view ecsAgent group table
					superreadwrite(4),	-- allowed to view and change Agent group table
			                readonly(5),	-- only read requests (GET) will be accepted
					readwrite(6)
		              }
                       ACCESS read-write
                       STATUS mandatory
  		       DESCRIPTION
 		       "Setting this object to the value invalid(2) invalidates the
                       corresponding entry in the   ECSAgentTrapReceiverTable.
                       That is, it effectively disassociates the address
                       identified with the entry by removing the entry from the table."
                       ::=   { blcAgentManagementEntry 2 }

-- blcAgentTrapReceiverTable Object Type Names



               blcAgentTrapReceiverTable OBJECT-TYPE
                       SYNTAX SEQUENCE OF BLCAgentTrapReceiverEntry
                       ACCESS not-accessible
                       STATUS mandatory
   		       DESCRIPTION
 		       "This entity's Trap Receiver Table. (10 entries)"
                       ::=  { blcAgent 10 }

               blcAgentTrapReceiverEntry OBJECT-TYPE
                       SYNTAX BLCAgentTrapReceiverEntry
                       ACCESS not-accessible
                       STATUS mandatory
 		       DESCRIPTION
 		       "A destination address and community string for a
			particular trap receiver."
                       INDEX   { blcAgentTrapReceiverAddr }
                       ::=   { blcAgentTrapReceiverTable 1 }

               BLCAgentTrapReceiverEntry ::= SEQUENCE {
		       blcAgentTrapReceiverAddr
			  IpAddress,
		       blcAgentTrapType
		          INTEGER,
		       blcAgentTrapReceiverComm
		          DisplayString (SIZE(0..20)),
		       blcAgentTrapLevel
			  INTEGER
	       }


               blcAgentTrapReceiverAddr OBJECT-TYPE
                       SYNTAX 		IpAddress
                       ACCESS read-write
                       STATUS mandatory
 		       DESCRIPTION
 		       "IpAddress for trap receiver."
                        ::=  { blcAgentTrapReceiverEntry 1 }

               blcAgentTrapType OBJECT-TYPE
                       SYNTAX INTEGER {
					invalid(1),	-- entry is deleted
			                off-on(2),      -- traps will not be sent to this address
			                generic(3),	-- only generic traps will be sent to this address
			                dot1d(4),
			                databasefull(5),
			                cug-violation(6)

		       }
                       ACCESS write-only
                       STATUS mandatory
 		       DESCRIPTION
 		       "Setting this object to the value invalid(2) invalidates the
                       corresponding entry in the   blcAgentTrapReceiverTable.
                       That is, it effectively disassociates the address
                       identified with the entry by removing the entry from the table."
                       ::=   { blcAgentTrapReceiverEntry 2 }

               blcAgentTrapReceiverComm OBJECT-TYPE
                       SYNTAX 		DisplayString (SIZE (0..20))
                       ACCESS read-write
                       STATUS mandatory
 		       DESCRIPTION
 		       "Community string used for traps."
                       ::=  { blcAgentTrapReceiverEntry 3 }

               blcAgentTrapLevel OBJECT-TYPE
                       SYNTAX INTEGER
                       ACCESS read-only
                       STATUS mandatory
 		       DESCRIPTION
 		       "Indicates the type of traps that will be sent to this
 			address."
                       ::=   { blcAgentTrapReceiverEntry 4 }


--               blcAgentFrontPanelSetupPassword OBJECT-TYPE
--                       ::=  {  blcAgent  12 }

--               blcAgentFrontPanelDisplay OBJECT-TYPE
--                       ::=  {  blcAgent  13 }

--               blcAgentFrontPanelPassword OBJECT-TYPE
--                       ::=  {  blcAgent  14 }

--               blcAgentFrontPanelLock OBJECT-TYPE
--                       ::=  {  blcAgent  15 }





-- blc Control Group

               blcForwardingMode OBJECT-TYPE
                       SYNTAX INTEGER {
				filtering(1),
				transparent(2),
				isolated(3)
		       }
                       ACCESS read-write
                       STATUS mandatory
  		       DESCRIPTION
 		       "Determines the forwarding mode of the bridge. If set to filtering
 			then the bridge is filtering and forwarding packets by destination
 			address, if transparent then the bridge is forwarding all packets
 			and if set to isolated the bridge is forwarding no packets."
                       ::=  { blcControl 1 }


               blcSTAPMode OBJECT-TYPE
                       SYNTAX INTEGER {
				off(1),
				on(2)
		       }
                       ACCESS read-write
                       STATUS mandatory
 		       DESCRIPTION
 		       "Determines whether the STAP algorithm is on or off."
                       ::=  { blcControl 2 }

               blcAccessGroupCheckingMode OBJECT-TYPE
                       SYNTAX INTEGER {
				off(1),
				on(2)
		       }
                       ACCESS read-write
                       STATUS mandatory
 		       DESCRIPTION
 		       "Determines whether access group checking is on or off."
                       ::=  { blcControl 3 }


               blcLearnMode OBJECT-TYPE
                       SYNTAX INTEGER {
				off(1),
				learn-into-no-accessgroup(2),
				learn-into-free-accessgroup(3)
		       }
                       ACCESS read-write
                       STATUS mandatory
 		       DESCRIPTION
 		       "Determines whether the bridge is not learning addresses
			(off), learning into free access group or the null
			access group."
                       ::=  { blcControl 4 }

		blcProtocolFilterMode OBJECT-TYPE
			SYNTAX	INTEGER {
					off(1),
					on(2)
			}
			ACCESS read-write
			STATUS mandatory
			DESCRIPTION
			"A flag to specify whether the bridge relay will
			 soft filter frames passing through it."
			::= { blcControl 5 }

              blcAgingMode OBJECT-TYPE
                       SYNTAX INTEGER {
				off(1),
				on(2)
		       }
                       ACCESS read-write
                       STATUS mandatory
 		       DESCRIPTION
 		       "Determines whether the addresses held in the filtering database
			are aged (on) or not-aged (off)."
                       ::=  { blcControl 6 }

               blcBroadcastForward OBJECT-TYPE
                       SYNTAX INTEGER {
				filter(1),
				forward(2)
		       }
                       ACCESS read-write
                       STATUS mandatory
 		       DESCRIPTION
 		       "Determines whether the bridge will forward packets with the
 			broadcast address."
                       ::=  { blcControl 7 }

               blcDuplicateAddressCheckingMode OBJECT-TYPE
                       SYNTAX INTEGER {
				off(1),
				on(2)
		       }
                       ACCESS read-write
                       STATUS mandatory
 		       DESCRIPTION
 		       "Determines whether the bridge will forward packets with the
 			same source and destination address."
                       ::=  { blcControl 8 }

               blcReportAccessGroupViolationMode OBJECT-TYPE
                       SYNTAX INTEGER {
				no-reports(1),
				reports(2)
		       }
                       ACCESS read-write
                       STATUS mandatory
 		       DESCRIPTION
 		       "Determines whether Access Group Violations are reported or not."
                       ::=  { blcControl 9 }


--   	blcDataBase   	{ blc 3 }

		blcSizeOfTransparentDataBase OBJECT-TYPE
			SYNTAX INTEGER
			ACCESS read-only
			STATUS mandatory
			DESCRIPTION
			"The maximum possible number of the Transparent database entries."
			::= { blcDataBase 1 }

		blcNumberOfStaticEntries OBJECT-TYPE
			SYNTAX INTEGER
			ACCESS read-only
			STATUS mandatory
			DESCRIPTION
			"The number of  entries currently in the transparent database
			 that cannot be aged out, and are not in the permanent database."
			::= { blcDataBase 2 }

		blcNumberOfDynamicEntries OBJECT-TYPE
			SYNTAX INTEGER
			ACCESS read-only
			STATUS mandatory
			DESCRIPTION
			"The number of entries currently in the transparent database
			 that can be aged out, and not held in the permanent database."
			::= { blcDataBase 3 }

		blcClearTransparentDataBase OBJECT-TYPE
			SYNTAX INTEGER {
				normal(1),
				clear(2)
			}
			ACCESS read-write
			STATUS mandatory
			DESCRIPTION
			"An attribute to clear all entries in the transparent database
			 except for those which are permanent."
			::= { blcDataBase 4 }

		blcMaxNumberOfPermanentEntries OBJECT-TYPE
			SYNTAX INTEGER
			ACCESS read-only
			STATUS mandatory
			DESCRIPTION
			"The maximum number of entries in the filtering database that can
			 be permanent."
			::= { blcDataBase 5 }

		blcNumberOfPermanentEntries OBJECT-TYPE
			SYNTAX INTEGER
			ACCESS read-only
			STATUS mandatory
			DESCRIPTION
			"The number of permanent entries in the filtering database."
			::= { blcDataBase 6 }

		blcClearPermanentEntries OBJECT-TYPE
			SYNTAX INTEGER {
				normal(1),
				clear(2)
			}
			ACCESS read-write
			STATUS mandatory
			DESCRIPTION
			"An attribute to clear the permanent entries from the filtering database."
			::= { blcDataBase 7 }

		blcSaveLearntAddresses OBJECT-TYPE
			SYNTAX INTEGER {
				normal(1),
				save(2)
			}
			ACCESS read-write
			STATUS mandatory
			DESCRIPTION
			"An attribute to make the leanrt addresses held in the
			 transparent database to become permanent entries."
			::= { blcDataBase 8 }


-- 	blcPcolFilter		{ blc 4 }



	blcNumberOfProtocolFilters OBJECT-TYPE
		SYNTAX	INTEGER
		ACCESS read-only
		STATUS mandatory
		DESCRIPTION
		"The maximum number of protocol filters that can be used."
		::= { blcPcolFilter 1 }


	blcProtocolFilterOperation OBJECT-TYPE
		SYNTAX INTEGER {
			and(1),
			or(2)
		}
		ACCESS read-write
		STATUS mandatory
		DESCRIPTION
		"An attribute to determine whether the resultant filter
		 is a composite OR or AND operation of the
		 individual protocol filters."
		::= { blcPcolFilter 2 }

	blcProtocolFilterTable OBJECT-TYPE
		SYNTAX	SEQUENCE OF BlcProtocolFilterEntry
		ACCESS not-accessible
		STATUS mandatory
		DESCRIPTION
		"A list of protocol filter entries. The maximum number
		 of entries is given by blcNumberOfProtocolFilters."
		::= { blcPcolFilter 3 }

	blcProtocolFilterEntry OBJECT-TYPE
		SYNTAX BlcProtocolFilterEntry
		ACCESS not-accessible
		STATUS mandatory
		DESCRIPTION
		"A protocol filter entry."
		INDEX { blcProtocolIndex }
		::= { blcProtocolFilterTable 1 }


	BlcProtocolFilterEntry ::= SEQUENCE {
		blcProtocolIndex
			INTEGER,
		blcProtocolValid
			INTEGER,
		blcProtocolState
			INTEGER,
		blcProtocolIdentifier
			OCTET STRING (SIZE(0..16)),
		blcProtocolOffset
			INTEGER,
		blcProtocolMask
			OCTET STRING (SIZE(4)),
		blcProtocolMatch
			OCTET STRING (SIZE(4)),
		blcProtocolDecision
			INTEGER,
		blcProtocolAction
			INTEGER
	}

	blcProtocolIndex OBJECT-TYPE
		SYNTAX INTEGER
		ACCESS read-only
		STATUS mandatory
		DESCRIPTION
		"A unique value for each protocol filter. Its value
		 ranges from 1 to blcNumberOfProtocolFilters."
		::= { blcProtocolFilterEntry 1 }


	blcProtocolValid OBJECT-TYPE
		SYNTAX INTEGER {
			invalid(1),
			valid(2)
		}
		ACCESS read-write
		STATUS mandatory
		DESCRIPTION
		"The object is valid for valid protocol filter entries.
		 The object is removed from the table by setting the
		 value to invalid."
		::= { blcProtocolFilterEntry 2 }

	blcProtocolState OBJECT-TYPE
		SYNTAX INTEGER {
			off(1),
			on(2)
		}
		ACCESS read-write
		STATUS mandatory
		DESCRIPTION
		"The object is on if the protocol filter is being
		 used for filtering frames. The filter is not used,
		 but remains in the table if the value is set to off."
		::= { blcProtocolFilterEntry 3 }


	blcProtocolIdentifier OBJECT-TYPE
		SYNTAX DisplayString (SIZE(0..16))
		ACCESS read-write
		STATUS mandatory
		DESCRIPTION
		"A string used to identify this protocol filter."
		::= { blcProtocolFilterEntry 4 }

	blcProtocolOffset OBJECT-TYPE
		SYNTAX INTEGER
		ACCESS read-write
		STATUS mandatory
		DESCRIPTION
		"Offset within the frame of the 4-byte field on
		 which filtering is to be performed."
		::= { blcProtocolFilterEntry 5 }


	blcProtocolMask OBJECT-TYPE
		SYNTAX OCTET STRING
		ACCESS read-write
		STATUS mandatory
		DESCRIPTION
		"This object is ANDed with the 4-byte field in the frame.
		 The result is compared with blcProtocolMatch."
		::= { blcProtocolFilterEntry 6 }

	blcProtocolMatch OBJECT-TYPE
		SYNTAX OCTET STRING
		ACCESS read-write
		STATUS mandatory
		DESCRIPTION
		"This object is compared with the reault of the ANDing.
		 with blcProtocolMask."
		::= { blcProtocolFilterEntry 7 }

	blcProtocolDecision OBJECT-TYPE
		SYNTAX INTEGER {
			nomatch(1),
			match(2)
		}
		ACCESS read-write
		STATUS mandatory
		DESCRIPTION
		"Determines whether the comparison of blcProtocolMatch
		 and the masked data field will cause the action specified
		 in blcProtocolAction to be taken on a match, or not."
		::= { blcProtocolFilterEntry 8 }

	blcProtocolAction OBJECT-TYPE
		SYNTAX INTEGER {
			filter(1),
			forward(2)
		}
		ACCESS read-write
		STATUS mandatory
		DESCRIPTION
		"As a result of the descision made in blcProtocolDecision
		 the frame will be either filterd or forwarded, depending
		 on the setting of this object."
		::= { blcProtocolFilterEntry 9 }

	blcProtocolFilterDefaultAction OBJECT-TYPE
		SYNTAX INTEGER {
			filter(1),
			forward(2)
		}
		ACCESS read-write
		STATUS mandatory
		DESCRIPTION
		"The action to be taken if the filters specified in the protocol
		 filter table are not satisfied."
		::= { blcPcolFilter 4 }

-- Based Heavily on the Spider Implementation of Access Groups
--
--	The differences are:
--		accessGroupMembers has become an OCTET STRING
--			rather than an INTEGER to allow upgrade
--			to any number of access groups.
--
--		accessGroupNamedIdIndex is bigger (32 rather than 20).
--	All access Groups can be named, so the accessGroupNamedIdTable
--		applies to all groups, not just the Named Access Groups.
--
--	A new table has been added to look at the access groups,
--		this table has three columns, accessgroupid and MAC address,
--		and a third entry which is just used to delete entries. If
--		you index by groupid and MAC address it should be possible
--		to list all the MAC addresses in that group by only
--		specifying the group id as an index and then use GET_NEXT.
--
--	Some cosmetic renaming.
--



-- accessGroupDBase	OBJECT IDENTIFIER ::=	{ blc 5 }

	accessGroupDBMaxEntries OBJECT-TYPE
		SYNTAX	INTEGER
		ACCESS	read-only
		STATUS	mandatory
		DESCRIPTION
		"The maximum number of entries in the access group table."
		::= { accessGroupDBase 1 }

	accessGroupDBValidEntries OBJECT-TYPE
		SYNTAX	INTEGER
		ACCESS	read-only
		STATUS	mandatory
		DESCRIPTION
		"The current number of user group
		 entries in the access group table."
		::= { accessGroupDBase 2 }

	accessGroupDBShortTable OBJECT-TYPE
		SYNTAX	SEQUENCE OF AccessGroupMemberShortTableEntry
		ACCESS	not-accessible
		STATUS	mandatory
		DESCRIPTION
		"A list of Access Group entries."
		::= { accessGroupDBase 3 }


	accessGroupMemberShortTableEntry OBJECT-TYPE
		SYNTAX 	AccessGroupMemberShortTableEntry
		ACCESS	not-accessible
		STATUS	mandatory
		INDEX { agsMemberAddress }
		::= { accessGroupDBShortTable 1 }


	AccessGroupMemberShortTableEntry ::= SEQUENCE {
		agsMemberAddress
			OCTET STRING (SIZE(6)),
		agsMemberValid
			INTEGER,
		agsMembers
			OCTET STRING (SIZE(2))
	}

	agsMemberAddress OBJECT-TYPE
		SYNTAX	OCTET STRING
		ACCESS	read-write
		STATUS	mandatory
		DESCRIPTION
		"The MAC address of this entry."
		::= { accessGroupMemberShortTableEntry 1 }

	agsMemberValid OBJECT-TYPE
		SYNTAX	INTEGER {
			invalid(1),
			valid(2)
		}
		ACCESS	read-write
		STATUS	mandatory
		DESCRIPTION
		"This object specifies whether the MAC address
		 is a member of the access groups database (valid).
		 To remove the MAC address from the access group
		 database set the value to invalid for this entry."
		::= { accessGroupMemberShortTableEntry 2 }

	agsMembers OBJECT-TYPE
		SYNTAX	OCTET STRING
		ACCESS	read-write
		STATUS	mandatory
		DESCRIPTION
		"This corresponds to a bit map of the access group membership
		 for the associated address. This includes normal Closed User
		 Groups (CUGs) the Free Access Group and the Management Group.
		 Access groups 1-8 are described by the first OCTET and 9-16
		 by the second OCTET, as more access groups become available
		 in future products, more OCTETS will become available."
		::= { accessGroupMemberShortTableEntry 3 }


-- Access Group DataBase (Full Form)

	accessGroupDBFullTable OBJECT-TYPE
		SYNTAX	SEQUENCE OF AccessGroupMemberFullTableEntry
		ACCESS	not-accessible
		STATUS	mandatory
		DESCRIPTION
		"A list of Access Group entries."
		::= { accessGroupDBase 4 }


	accessGroupMemberFullTableEntry OBJECT-TYPE
		SYNTAX 	AccessGroupMemberFullTableEntry
		ACCESS	not-accessible
		STATUS	mandatory
		INDEX { agfMemberAddress }
		::= { accessGroupDBFullTable 1 }


	AccessGroupMemberFullTableEntry ::= SEQUENCE {
		agfMemberAddress
			OCTET STRING (SIZE(6)),
		agfMemberValid
			INTEGER,
		agfMemberFreeUserGroup
			INTEGER,
		agfMemberUserGroup1
			INTEGER,
		agfMemberUserGroup2
			INTEGER,
		agfMemberUserGroup3
			INTEGER,
		agfMemberUserGroup4
			INTEGER,
		agfMemberUserGroup5
			INTEGER,
		agfMemberUserGroup6
			INTEGER,
		agfMemberUserGroup7
			INTEGER,
		agfMemberUserGroup8
			INTEGER
	}

	agfMemberAddress OBJECT-TYPE
		SYNTAX	OCTET STRING
		ACCESS	read-write
		STATUS	mandatory
		DESCRIPTION
		"The MAC address of this entry."
		::= { accessGroupMemberFullTableEntry 1 }


	agfMemberValid OBJECT-TYPE
		SYNTAX	INTEGER {
			invalid(1),
			valid(2)
		}
		ACCESS	read-write
		STATUS	mandatory
		DESCRIPTION
		"This object specifies whether the MAC address
		 can be a memember of access groups (enabled) or not.
		 To remove the MAC address from the access groups
		 database set the value to invalid for this entry."
		::= { accessGroupMemberFullTableEntry 2 }

	agfMemberFreeUserGroup OBJECT-TYPE
		SYNTAX	INTEGER {
			no(1),
			yes(2)
		}
		ACCESS	read-write
		STATUS	mandatory
		DESCRIPTION
		"This object specifies whether the MAC address
		 is a member of the free access group (free) or
		 the closed access group."
		::= { accessGroupMemberFullTableEntry 3 }

	agfMemberUserGroup1 OBJECT-TYPE
		SYNTAX	INTEGER {
			no(1),
			yes(2)
		}
		ACCESS	read-write
		STATUS	mandatory
		DESCRIPTION
		"This object specifies whether the MAC address
		 is a memember of access user group 1 (yes) or not (no).
		 To remove the MAC address from this access group
		 set the value to no for this entry."
		::= { accessGroupMemberFullTableEntry 4 }

	agfMemberUserGroup2 OBJECT-TYPE
		SYNTAX	INTEGER {
			no(1),
			yes(2)
		}
		ACCESS	read-write
		STATUS	mandatory
		DESCRIPTION
		"This object specifies whether the MAC address
		 is a memember of access user group 2 (yes) or not (no).
		 To remove the MAC address from this access group
		 set the value to no for this entry."
		::= { accessGroupMemberFullTableEntry 5 }

	agfMemberUserGroup3 OBJECT-TYPE
		SYNTAX	INTEGER {
			no(1),
			yes(2)
		}
		ACCESS	read-write
		STATUS	mandatory
		DESCRIPTION
		"This object specifies whether the MAC address
		 is a memember of access user group 3 (yes) or not (no).
		 To remove the MAC address from this access group
		 set the value to no for this entry."
		::= { accessGroupMemberFullTableEntry 6 }

	agfMemberUserGroup4 OBJECT-TYPE
		SYNTAX	INTEGER {
			no(1),
			yes(2)
		}
		ACCESS	read-write
		STATUS	mandatory
		DESCRIPTION
		"This object specifies whether the MAC address
		 is a memember of access user group 4 (yes) or not (no).
		 To remove the MAC address from this access group
		 set the value to no for this entry."
		::= { accessGroupMemberFullTableEntry 7 }

	agfMemberUserGroup5 OBJECT-TYPE
		SYNTAX	INTEGER {
			no(1),
			yes(2)
		}
		ACCESS	read-write
		STATUS	mandatory
		DESCRIPTION
		"This object specifies whether the MAC address
		 is a memember of access user group 5 (yes) or not (no).
		 To remove the MAC address from this access group
		 set the value to no for this entry."
		::= { accessGroupMemberFullTableEntry 8 }

	agfMemberUserGroup6 OBJECT-TYPE
		SYNTAX	INTEGER {
			no(1),
			yes(2)
		}
		ACCESS	read-write
		STATUS	mandatory
		DESCRIPTION
		"This object specifies whether the MAC address
		 is a memember of access user group 6 (yes) or not (no).
		 To remove the MAC address from this access group
		 set the value to no for this entry."
		::= { accessGroupMemberFullTableEntry 9 }

	agfMemberUserGroup7 OBJECT-TYPE
		SYNTAX	INTEGER {
			no(1),
			yes(2)
		}
		ACCESS	read-write
		STATUS	mandatory
		DESCRIPTION
		"This object specifies whether the MAC address
		 is a memember of access user group 7 (yes) or not (no).
		 To remove the MAC address from this access group
		 set the value to no for this entry."
		::= { accessGroupMemberFullTableEntry 10 }

	agfMemberUserGroup8 OBJECT-TYPE
		SYNTAX	INTEGER {
			no(1),
			yes(2)
		}
		ACCESS	read-write
		STATUS	mandatory
		DESCRIPTION
		"This object specifies whether the MAC address
		 is a memember of access user group 8 (yes) or not (no).
		 To remove the MAC address from this access group
		 set the value to no for this entry."
		::= { accessGroupMemberFullTableEntry 11 }

--  Number of User Access Groups

	accessUserGroupCount OBJECT-TYPE
		SYNTAX	INTEGER
		ACCESS	read-only
		STATUS 	mandatory
		DESCRIPTION
		"The maximum number of User Access Groups
		 supported by the system."
		::= { accessGroupDBase 5 }

-- Access User Group Name Table, allows you to provide a name for each of
-- the access groups (except the free and closed access groups)

	accessUserGroupNameTable OBJECT-TYPE
		SYNTAX	SEQUENCE OF AccessUserGroupNameTableEntry
		ACCESS	not-accessible
		STATUS	mandatory
		DESCRIPTION
		"A list of names for each access group."
		::= { accessGroupDBase 6 }


	accessUserGroupNameTableEntry OBJECT-TYPE
		SYNTAX 	AccessUserGroupNameTableEntry
		ACCESS	not-accessible
		STATUS	mandatory
		INDEX { accessUserGroupNameIndex }
		::= { accessUserGroupNameTable 1 }


	AccessUserGroupNameTableEntry ::= SEQUENCE {
		accessUserGroupNameIndex
			INTEGER,
		accessUserGroupNameIdentifier
			DisplayString (SIZE(0..32))
	}

	accessUserGroupNameIndex OBJECT-TYPE
		SYNTAX	INTEGER
		ACCESS	read-only
		STATUS	mandatory
		DESCRIPTION
		"A unique value for each Access Group.
		 Its value ranges between 1 and the value of the
		 accessGroupEntries."
		::= { accessUserGroupNameTableEntry 1 }

	accessUserGroupNameIdentifier OBJECT-TYPE
		SYNTAX	DisplayString (SIZE(0..32))
		ACCESS	read-write
		STATUS	mandatory
		DESCRIPTION
		"The name associated with this access group."
		::= { accessUserGroupNameTableEntry 2 }


-- Access Group Violation Table. Indicates the number of attempts of
-- packets that would have normally have been forwarded, but were not
-- because the source and destination had no common access group.
-- The count is incremented for the received port

	accessGroupViolationTable OBJECT-TYPE
		SYNTAX	SEQUENCE OF AccessGroupViolationTableEntry
		ACCESS	not-accessible
		STATUS	mandatory
		DESCRIPTION
		"The number of access group violations on a per port basis."
		::= { accessGroupDBase 7 }


	accessGroupViolationTableEntry OBJECT-TYPE
		SYNTAX 	AccessGroupViolationTableEntry
		ACCESS	not-accessible
		STATUS	mandatory
		INDEX { agViolationPort }
		::= { accessGroupViolationTable 1 }


	AccessGroupViolationTableEntry ::= SEQUENCE {
		agViolationPort
			INTEGER,
		agViolations
			Counter
	}

	agViolationPort OBJECT-TYPE
		SYNTAX	INTEGER
		ACCESS	read-only
		STATUS	mandatory
		DESCRIPTION
		"The port for which cug violations have been detected."
		::= { accessGroupViolationTableEntry 1 }

	agViolations OBJECT-TYPE
		SYNTAX	Counter
		ACCESS	read-only
		STATUS	mandatory
		DESCRIPTION
		"The number of CUG violations that have been attempted on
		 the port indicated by agViolationPort"
		::= { accessGroupViolationTableEntry 2 }


-- End of Enterprise Extensions

          -- Traps for use by Bridges

          -- Traps for the Spanning Tree Protocol

          newRoot TRAP-TYPE
               ENTERPRISE  dot1dBridge
               DESCRIPTION
                       "The newRoot trap indicates that the sending agent
                       has become the new root of the Spanning Tree; the
                       trap is sent by a bridge soon after its election
                       as the new root, e.g., upon expiration of the
                       Topology Change Timer immediately subsequent to
                       its election."
               ::= 1

           topologyChange TRAP-TYPE
               ENTERPRISE  dot1dBridge
               DESCRIPTION
                       "A topologyChange trap is sent by a bridge when
                       any of its configured ports transitions from the
                       Learning state to the Forwarding state, or from
                       the Forwarding state to the Blocking state.  The
                       trap is not sent if a newRoot trap is sent for the
                       same transition."
               ::= 2

           filteringDataBaseFull TRAP-TYPE
               ENTERPRISE  lBridgeECS
               DESCRIPTION
                       "The filtering database within the bridge
			has become overloaded or full."
               ::= 1

           permanentDataBaseFull TRAP-TYPE
               ENTERPRISE  lBridgeECS
               DESCRIPTION
                       "The maximum number of permanent entries in the
			filtering database has been exceeded."
               ::= 2

           accessGroupViolation TRAP-TYPE
               ENTERPRISE  lBridgeECS
               DESCRIPTION
                       "A recent attempt has been made to violate the access
			groups in the bridge."
               ::= 3

END
