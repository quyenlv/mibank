BLUESOCKET-PRODUCTS DEFINITIONS ::= BEGIN

IMPORTS
    MODULE-IDENTITY
        FROM SNMPv2-SMI
    blueSocket
        FROM BLUESOCKET-ROOT;

-- Bluesocket gateways with pre-4.0 software do not have the ability
-- to determine what kind of gateway they are. These devices return
-- a generic sysObjectID value of:
-- iso.org.dod.internet.private.enterprises.bluesocket (1.3.6.1.4.1.9967)


blueProducts    MODULE-IDENTITY
    LAST-UPDATED "200404200000Z"
    ORGANIZATION "Bluesocket Inc."
    CONTACT-INFO
            "   John Yeaman
                Bluesocket, Inc.
                Burlington, MA 01803
                jyeaman@bluesocket.com
            "
    DESCRIPTION
       "This MIB is DRAFT-ONLY and is subject to change.
        Management Information Base for Blueserver."

    ::= { blueSocket 100 }

blue1000        OBJECT IDENTIFIER ::= { blueProducts 1000 }
blue1100        OBJECT IDENTIFIER ::= { blueProducts 1100 }
blue2000        OBJECT IDENTIFIER ::= { blueProducts 2000 }
blue2100        OBJECT IDENTIFIER ::= { blueProducts 2100 }
blue5000        OBJECT IDENTIFIER ::= { blueProducts 5000 }

gw1000-810      OBJECT IDENTIFIER ::= { blue1000 1 }
gw1000-815      OBJECT IDENTIFIER ::= { blue1000 2 }

gw1100          OBJECT IDENTIFIER ::= { blue1100 1 }

gw2000          OBJECT IDENTIFIER ::= { blue2000 1 }
gw2000-TF       OBJECT IDENTIFIER ::= { blue2000 2 }
gw2000-FT       OBJECT IDENTIFIER ::= { blue2000 3 }
gw2000-FF       OBJECT IDENTIFIER ::= { blue2000 4 }

gw2100          OBJECT IDENTIFIER ::= { blue2100 1 }
gw2100-TF       OBJECT IDENTIFIER ::= { blue2100 2 }
gw2100-FT       OBJECT IDENTIFIER ::= { blue2100 3 }
gw2100-FF       OBJECT IDENTIFIER ::= { blue2100 4 }

gw5000          OBJECT IDENTIFIER ::= { blue5000 1 }
gw5000-TF       OBJECT IDENTIFIER ::= { blue5000 2 }
gw5000-FT       OBJECT IDENTIFIER ::= { blue5000 3 }
gw5000-FF       OBJECT IDENTIFIER ::= { blue5000 4 }

END
