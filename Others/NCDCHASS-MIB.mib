NCDCHASS-MIB DEFINITIONS ::= BEGIN

IMPORTS
		DisplayString FROM SNMPv2-TC
	TRAP-TYPE FROM RFC-1215
    OBJECT-TYPE
   FROM RFC-1212
    TimeTicks, IpAddress, Counter
   FROM RFC1155-SMI
    ncdMibs
   FROM A3Com-products-MIB;



ncdMibsConfChange TRAP-TYPE
ENTERPRISE ncdMibs
DESCRIPTION
    "An unsolicited change in device configuration"
::= 1

ncdMibsFault TRAP-TYPE
ENTERPRISE ncdMibs
DESCRIPTION
    "An unsolicited fault in device"
::= 2


ncdchass                 OBJECT IDENTIFIER ::= { ncdMibs 1 }


-- Groups within the ncdchass MIB

ncdchassInfo        OBJECT IDENTIFIER ::= { ncdchass 1 }
ncdchassPhysical    OBJECT IDENTIFIER ::= { ncdchass 2 }
ncdchassEntity      OBJECT IDENTIFIER ::= { ncdchass 3 }
ncdchassPowerSupply OBJECT IDENTIFIER ::= { ncdchass 4 }
ncdchassAdmin       OBJECT IDENTIFIER ::= { ncdchass 5 }
ncdchassEnviron     OBJECT IDENTIFIER ::= { ncdchass 6 }


-- ncdchass admin ids for hardware

ncdchassN2000      OBJECT IDENTIFIER ::= { ncdchassAdmin 1 }
ncdchassLowCost    OBJECT IDENTIFIER ::= { ncdchassAdmin 2 }
ncdchassSwitchMod  OBJECT IDENTIFIER ::= { ncdchassAdmin 3 }
ncdchass4Oc3       OBJECT IDENTIFIER ::= { ncdchassAdmin 4 }
ncdchass4Ds3       OBJECT IDENTIFIER ::= { ncdchassAdmin 5 }
ncdchassCp7200     OBJECT IDENTIFIER ::= { ncdchassAdmin 6 }
ncdchassCp4Utp5    OBJECT IDENTIFIER ::= { ncdchassAdmin 7 }
ncdchassCp7400     OBJECT IDENTIFIER ::= { ncdchassAdmin 8 }
ncdchassCp7200f    OBJECT IDENTIFIER ::= { ncdchassAdmin 9 }
ncdchassCp7600f    OBJECT IDENTIFIER ::= { ncdchassAdmin 10 }
ncdchassCp7600     OBJECT IDENTIFIER ::= { ncdchassAdmin 11 }
ncdchass8Oc3       OBJECT IDENTIFIER ::= { ncdchassAdmin 12 }
ncdchass2Oc12      OBJECT IDENTIFIER ::= { ncdchassAdmin 13 }
ncdchassCp7436     OBJECT IDENTIFIER ::= { ncdchassAdmin 14 }
ncdchassCp7400FBus OBJECT IDENTIFIER ::= { ncdchassAdmin 15 }
ncdchassCp7600FBus OBJECT IDENTIFIER ::= { ncdchassAdmin 16 }

ncdchassSS1Box     OBJECT IDENTIFIER ::= { ncdchassAdmin 100 }
ncdchassSS2Box     OBJECT IDENTIFIER ::= { ncdchassAdmin 101 }
ncdchassCp7000Box  OBJECT IDENTIFIER ::= { ncdchassAdmin 102 }

ncdchassFanSensor  OBJECT IDENTIFIER ::= { ncdchassAdmin 200 }
ncdchassTemperSensor  OBJECT IDENTIFIER ::= { ncdchassAdmin 201 }


-- ncdchassInfo group (ncdchasssis information group).
-- Implementation of this group is mandatory.

ncdchassType  OBJECT-TYPE
    SYNTAX  OBJECT IDENTIFIER
    ACCESS  read-only
    STATUS  mandatory
    DESCRIPTION
  "An authoritative identification of the type of
  hub-based or standalone ncdchasssis.  By convention
  this value is allocated within the SMI enterprises
  subtree(1.3.6.1.4.1), and provides an easy and
  unambiguous means for determining `what kind of
  box' is being managed.  If this information is not
  present or unknown, its value should be set to the
  value: ncdchassTypeUnknown."
    ::= { ncdchassInfo 1 }

ncdchassPhysicalChanges  OBJECT-TYPE
    SYNTAX   Counter
    ACCESS   read-only
    STATUS   mandatory
    DESCRIPTION
  "The number of physical changes that have occurred
  in the ncdchasssis since the agent was warm/cold
  started.  This includes additions and removal of
  modules and entities.  Other uses are
  implementation specific."
    ::= { ncdchassInfo 2 }


ncdchassChasssisSerialNumber   OBJECT-TYPE
    SYNTAX    DisplayString (SIZE (0..32))
    ACCESS    read-only
    STATUS    mandatory
    DESCRIPTION
  "The serial number of the ncdchasssis. If no serial
  number is available then this object should be the
  zero length string."
    ::= { ncdchassInfo 3 }

-- ncdchassPhysical group (physical configuration group).
-- Implementation of this group is mandatory.

ncdchassModuleTable OBJECT-TYPE
    SYNTAX SEQUENCE OF NcdchassPhyModuleEntry
    ACCESS not-accessible
    STATUS mandatory
    DESCRIPTION
  "This table defines the physical modules within a
  ncdchasssis.  This is done by defining the type
  physical modules and the physical location where
  it resides.  This table also provides a mapping
  from between physical modules and their location
  within the ncdchasssis."
    ::= { ncdchassPhysical 2 }

ncdchassModuleEntry OBJECT-TYPE
    SYNTAX NcdchassPhyModuleEntry
    ACCESS not-accessible
    STATUS mandatory
    DESCRIPTION
  "An entry in this table that describes a physical
  module that resides at a given physcial location
  within the ncdchasssis."
    INDEX { ncdchassModuleLocation }
    ::= { ncdchassModuleTable 1 }

NcdchassPhyModuleEntry ::= SEQUENCE {
    ncdchassModuleLocation
   INTEGER,
    ncdchassModuleType
   OBJECT IDENTIFIER,
    ncdchassModuleSwVersion
   DisplayString,
    ncdchassModuleHwVersion
   DisplayString,
    ncdchassModuleSerialNumber
   DisplayString,
    ncdchassModuleDescription
   DisplayString,
    ncdchassModuleLastChangeTime
   TimeTicks,
    ncdchassModuleAdminStatus
   INTEGER,
    ncdchassModuleOperStatus
   INTEGER
    }


ncdchassModuleLocation  OBJECT-TYPE
   SYNTAX INTEGER
   ACCESS read-only
   STATUS mandatory
   DESCRIPTION
  "An instance of a module is identified by the
  slot number."
   ::= { ncdchassModuleEntry 1 }

ncdchassModuleType OBJECT-TYPE
    SYNTAX OBJECT IDENTIFIER
    ACCESS read-only
    STATUS mandatory
    DESCRIPTION
  "An authoritative identification of the type of
  physcial module in this physical location.  A
  value of ncdchassModuleUnknown indicates that the type
  of physical module is unknown."
    ::= { ncdchassModuleEntry 2 }

ncdchassModuleSwVersion OBJECT-TYPE
    SYNTAX DisplayString (SIZE (0..32))
    ACCESS read-only
    STATUS mandatory
    DESCRIPTION
  "A textual description of the version/revision
  level for this module's software.  If not realized
  this value should be set to the zero-length
  string."
    ::= { ncdchassModuleEntry 3 }

ncdchassModuleHwVersion OBJECT-TYPE
    SYNTAX DisplayString (SIZE (0..32))
    ACCESS read-only
    STATUS mandatory
    DESCRIPTION
  "A textual description of the version/revision
  level for this module's firmware.  If not realized
  this value should be set to the zero-length
  string."
    ::= { ncdchassModuleEntry 4 }

ncdchassModuleSerialNumber OBJECT-TYPE
    SYNTAX DisplayString (SIZE (0..32))
    ACCESS read-only
    STATUS mandatory
    DESCRIPTION
  "The serial number of the physical module present
  in this physical location.  If the physical
  location table is implemented as dense and the
  slot is empty this value will be the zero length
  string.  If no serial number is available for a
  physical module this value should set to a zero
  length string."
    ::= { ncdchassModuleEntry 5 }

ncdchassModuleDescription OBJECT-TYPE
    SYNTAX DisplayString (SIZE (0..32))
    ACCESS read-only
    STATUS mandatory
    DESCRIPTION
  "A textual description of the physical module
  plugged that resides in this physical location.
  If not available this value should be set to a
  zero length string."
    ::= { ncdchassModuleEntry 6 }

ncdchassModuleLastChangeTime OBJECT-TYPE
    SYNTAX TimeTicks
    ACCESS read-only
    STATUS mandatory
    DESCRIPTION
  "The value of MIB-II's sysUpTime (in the agent
  supporting this ncdchasssis MIB) at which a module was
  last inserted or initialized.  If the module has
  not changed since the last network managment
  system reinitialized then this object has a zero
  value."
    ::= { ncdchassModuleEntry 7 }

ncdchassModuleAdminStatus OBJECT-TYPE
    SYNTAX INTEGER {
   enable(2),
   disable(3),
   reset(4),
   programLoad(5),
   test(6)
    }
    ACCESS read-write
    STATUS mandatory
    DESCRIPTION
  "Provides desired state of the given physical
  module.  Notice that not all values may be
  supported by the specified physical module.  In
  this case an SNMP error will be returned when the
  set is attempted.
  A physical module may be activated by writing a
  value of enable(2).

  A physical module may be de-activated by writing a
  value of disable(3).  In a disabled state a
  physical module is present in the ncdchasssis but is
  benign.

  Writing a value of reset(4) initiates a reset
  sequence.

  A value of programLoad(5) initiates a software
  load sequences.

  Writing a value of test(6) should start a self
  test sequence within the physical module."
    ::= { ncdchassModuleEntry 8 }

ncdchassModuleOperStatus OBJECT-TYPE
    SYNTAX INTEGER {
   other(1),
   invalid(2),
   test(3),
   operational(4),
   resetInProgress(5),
   warning(6),
   nonFatalError(7),
   fatalError(8)
    }
    ACCESS read-only
    STATUS mandatory
    DESCRIPTION
  "Provides operational status of the module.  The
  following are possible definitions of the values.
  The exact definition of the values is
  implementation specific.  A value of other(1)
  implies some undetermined state, possibly as a
  result of setting ncdchassModuleAdminStatus to a value
  of disable(3).  A value of invalid(2) could have
  the possible meaning that the module exists but
  the ncdchasssis manager has no direct control over the
  module.  A value of testing(3) may be a diagnostic
  state.  A value of operational(4) implies that the
  entity is running with no errors or warnings.
  State resetInProgress(5) implies equivalent of
  setting ncdchassModuleAdminStatus to reset(4). The
  states of warning(6), nonFatalError(7),
  fatalError(8) reflect conditions detected during
  operation.  The entity may or may not be still
  functional.

  For example if a modules value of
  ncdchassModuleAdminStatus is disable(3) and is set to
  enable(2) then ncdchassModuleOperStatus may enter a
  state of testing(3) then change to a value of
  operational(4)."
    ::= { ncdchassModuleEntry 9 }


-- The ncdchassEntity group.  Implementation of the ncdchassEntity group
-- is mandatory.

-- Entity Table

ncdchassEntityTable OBJECT-TYPE
    SYNTAX  SEQUENCE OF NcdchassEntityEntry
    ACCESS  not-accessible
    STATUS  mandatory
    DESCRIPTION
  "A table that contains information about the
  'logical' networking devices (entities) in this
  ncdchasssis."
    ::= { ncdchassEntity 1 }

ncdchassEntityEntry OBJECT-TYPE
    SYNTAX  NcdchassEntityEntry
    ACCESS  not-accessible
    STATUS  mandatory
    DESCRIPTION
  "Information concerning an entity in the ncdchasssis.
  Conceptual rows may not be created or deleted with
  SNMP operations."
    INDEX  { ncdchassEntityIndex }
    ::= { ncdchassEntityTable 1 }

NcdchassEntityEntry ::=
    SEQUENCE {
   ncdchassEntityIndex
  INTEGER,
   ncdchassEntityObjectID
  OBJECT IDENTIFIER,
   ncdchassEntityDescr
  DisplayString,
   ncdchassEntityAdminStatus
  INTEGER,
   ncdchassEntityOperStatus
  INTEGER,
   ncdchassEntityTimeStamp
  TimeTicks
    }

ncdchassEntityIndex OBJECT-TYPE
    SYNTAX  INTEGER (1..65535)
    ACCESS  read-only
    STATUS  mandatory
    DESCRIPTION
  "A unique index for the entity for which this
  entry contains information."
    ::= { ncdchassEntityEntry 1 }

ncdchassEntityObjectID  OBJECT-TYPE
    SYNTAX  OBJECT IDENTIFIER
    ACCESS  read-only
    STATUS  mandatory
    DESCRIPTION
  "The specific type of entity.  The value of this
  object is analagous to MIB-II's sysObjectId."
    ::= { ncdchassEntityEntry 2 }


ncdchassEntityDescr  OBJECT-TYPE
    SYNTAX  DisplayString (SIZE (0..255))
    ACCESS  read-write
    STATUS  mandatory
    DESCRIPTION
  "A textual description of the entity.  The value
  of this object is analagous to MIB-II's sysDescr."
    ::= { ncdchassEntityEntry 3 }

ncdchassEntityAdminStatus OBJECT-TYPE
    SYNTAX  INTEGER {
   unknown(1),   --  none of the following
   enable(2),
   disable(3),
   reset(4),
   programload(5),
   test(6)
    }
    ACCESS  read-write
    STATUS  mandatory
    DESCRIPTION
  "Provides the administratively desired state of
  the given entity.

  An entity is activated by writing a value of
  enable(2).

  An entity may be de-activated by writing a value
  of disable(3).  In a disabled state, a entity does
  exist within the given ncdchasssis, but is benign.  A
  disabled entity is available for subsequent
  activation.

  Writing a value of reset(4) specifies an entity
  should initiate a reset sequence.

  Writing a value of programload(5) specifies an
  entity should initiate a program load sequence.

  Writing a value of test(6) specifies an entity
  should initiate a testing sequence.

  Agent support of the writing of any of the values
  of this object is implementation-specific.  For
  example, this object might be read only for
  entities that disabling would compromise the
  integrity of the ncdchasssis."
    ::= { ncdchassEntityEntry 4 }

ncdchassEntityOperStatus OBJECT-TYPE
    SYNTAX  INTEGER {
   other(1),--  none of the following
   invalid(2),
   testing(3),
   operational(4),
   resetInProgress(5),
   warning(6),
   nonFatalError(7),
   fatalError(8),
   loading(10)
    }
    ACCESS  read-only
    STATUS  mandatory
    DESCRIPTION
  "Provides operational status of the entity.  The
  following are possible definitions of the values.
  The exact definition of the values is
  implementation specific.  A value of other(1)
  implies some undetermined state, possibly as a
  result of setting ncdchassEntityAdminStatus to a value
  of disable(3).  A value of invalid(2) could have
  the possible meaning that the entity exists but
  the ncdchasssis manager has no direct control of the
  entity.  A value of testing(3) may be a diagnostic
  state.  A value of operational(4) implies that the
  entity is running with no errors or warnings.
  State resetInProgress(5) implies equivalent of
  setting ncdchassEntityAdminStatus to reset(4). The
  states of warning(6), nonFatalError(7),
  fatalError(8) reflect conditions detected during
  operation.  The entity may or may not be still
  functional.  State loading(10) is a result of
  asserting programload(5) in ncdchassEntityAdminStatus.

  For example if an entities value of
  ncdchassEntityAdminStatus is disable(3) and is set to
  enable(2) then ncdchassEntityOperStatus may enter a
  state of testing(3) then change to a value of
  operational(4)."
    ::= { ncdchassEntityEntry 5 }


ncdchassEntityTimeStamp  OBJECT-TYPE
    SYNTAX  TimeTicks
    ACCESS  read-only
    STATUS  mandatory
    DESCRIPTION
  "The value of MIB-II's sysUpTime (in the agent
  supporting this MIB) at which this entity was last
  (re-)initialized.  If the entity has not been
  initialized then this object has a zero value."
    ::= { ncdchassEntityEntry 6 }



-- The ncdchassEntityViewTable is used to provide the different MIB views
-- for each entity.  In it's simpliest form a MIB view provides
-- read-write access to all of the MIBs realized by the given entity.
-- For example a bridge entity may realize the bridge MIB as defined
-- by RFC-1286. The MIB view table may include entries for a read-only
-- view, a read-write vies.  It may also include entries for specific
-- groups within the bridge MIB.

ncdchassEntityViewTable  OBJECT-TYPE
    SYNTAX SEQUENCE OF NcdchassEntityViewEntry
    ACCESS not-accessible
    STATUS mandatory
    DESCRIPTION
  "A table of all MIB views orgainized by entity.
  Each entity may have a number of MIB views
  associated with it."
    ::= { ncdchassEntity 2 }

ncdchassEntityViewEntry  OBJECT-TYPE
    SYNTAX NcdchassEntityViewEntry
    ACCESS not-accessible
    STATUS mandatory
    DESCRIPTION
  "Defines a specific MIB view."
    INDEX { ncdchassEntityViewEntityId, ncdchassEntityViewIndex }
::= { ncdchassEntityViewTable 1 }

NcdchassEntityViewEntry  ::= SEQUENCE {
    ncdchassEntityViewEntityId
   INTEGER,
    ncdchassEntityViewIndex
   INTEGER,
    ncdchassEntityCommunity
   OCTET STRING,
    ncdchassEntityIpAddress
   IpAddress
    }

ncdchassEntityViewEntityId  OBJECT-TYPE
    SYNTAX  INTEGER (1..65535)
    ACCESS  read-only
    STATUS  mandatory
    DESCRIPTION
  "The unique entity for which this MIB view is
  defined.  This is an instance of  ncdchassEntityIndex
  within the ncdchassEntityTable."
    ::= { ncdchassEntityViewEntry 1 }

ncdchassEntityViewIndex  OBJECT-TYPE
    SYNTAX  INTEGER (1..127)
    ACCESS  read-only
    STATUS  mandatory
    DESCRIPTION
  "Defines a unique MIB view for this entity."
    ::= { ncdchassEntityViewEntry 2 }

ncdchassEntityCommunity  OBJECT-TYPE
    SYNTAX  OCTET STRING (SIZE (0..255))
    ACCESS  read-only
    STATUS  mandatory
    DESCRIPTION
  "The SNMP Community which executes at the address
  ncdchassEntityIpAddress, and provides access to the
  detailed management information for this entity.

  For an entity which is not managed through access
  to a SNMP Community, the value of this object is
  the zero-length string."
    ::= { ncdchassEntityViewEntry 3 }

ncdchassEntityIpAddress  OBJECT-TYPE
    SYNTAX  IpAddress
    ACCESS  read-only
    STATUS  mandatory
    DESCRIPTION
  "The address of the SNMP agent which responds to
  messages for the SNMP Community identified by
  ncdchassEntityCommunity.  When access is via proxy,
  this variable contains the address of the proxy
  agent.

  For an entity which is not managed through access
  to a SNMP Community, the value of this object is
  0.0.0.0."
    ::= { ncdchassEntityViewEntry 4 }


-- The ncdchassPowerSupply (Power Supply) group, implementation of
-- the power supply group is optional.

-- the Power Supply table

ncdchassPowerSupplyTable OBJECT-TYPE
    SYNTAX SEQUENCE OF NcdchassPowerSupplyEntry
    ACCESS not-accessible
    STATUS mandatory
    DESCRIPTION
  "A list of power supply entries, one for each
  power supply in the ncdchasssis."
    ::= { ncdchassPowerSupply 1 }

ncdchassPowerSupplyEntry OBJECT-TYPE
    SYNTAX NcdchassPowerSupplyEntry
    ACCESS not-accessible
    STATUS mandatory
    DESCRIPTION
  "Values for a power supply."
    INDEX { ncdchassPowerSupplyIndex }
    ::= { ncdchassPowerSupplyTable 1 }

NcdchassPowerSupplyEntry ::=
    SEQUENCE {
   ncdchassPowerSupplyIndex
  INTEGER,
   ncdchassPowerSupplyDescr
  DisplayString,
   ncdchassPowerSupplyAdminStatus
  INTEGER,
   ncdchassPowerSupplyOperStatus
  INTEGER,
   ncdchassPowerSupplyHealthText
  DisplayString,
   ncdchassPowerSupplyWarnings
  Counter,
   ncdchassPowerSupplyFailures
  Counter,
   ncdchassPowerSupplyLocationType
  INTEGER,
   ncdchassPowerSupplyLocationIndex
  INTEGER
    }

ncdchassPowerSupplyIndex OBJECT-TYPE
    SYNTAX INTEGER
    ACCESS read-only
    STATUS mandatory
    DESCRIPTION
  "An index value that uniquely identifies a power
  supply."
    ::= { ncdchassPowerSupplyEntry 1 }

ncdchassPowerSupplyDescr OBJECT-TYPE
    SYNTAX DisplayString (SIZE (0..255))
    ACCESS read-only
    STATUS mandatory
    DESCRIPTION
  "A textual description of the power supply,
  including the vendor's name and version."
    ::= { ncdchassPowerSupplyEntry 2 }

ncdchassPowerSupplyAdminStatus OBJECT-TYPE
    SYNTAX INTEGER {
   unknown(1),
   enable(2),
   disable(3) }
    ACCESS read-write
    STATUS mandatory
    DESCRIPTION
  "Desired status of the power supply."
    ::= { ncdchassPowerSupplyEntry 3 }

ncdchassPowerSupplyOperStatus OBJECT-TYPE
    SYNTAX INTEGER {
   unknown(1),
   empty(2),
   disabled(3),
   bad(4),
   warning(5),
   standby(6),
   engaged(7),
   redundant(8) }
    ACCESS read-only
    STATUS mandatory
    DESCRIPTION
  "Actual status of the power supply:
  - unknown(1) - status not known.
  - empty(2) - no power supply installed in slot
  - disabled(3) - unable to supply power due to ncdchassPowerSupplyAdminStatus
  - bad(4) - unable to supply power due to failure
  - warning(5) - supplying power but an output or sensor is bad or warning
  - standby(6) - believed usable but not supplying power
  - engaged(7) - supplying power
  - redundant(8) - supplying power but not needed

  It is an implementation specific matter whether
  the agent keeps entries with status unknown(1) or
  empty(2) in the table."
    ::= { ncdchassPowerSupplyEntry 4 }

ncdchassPowerSupplyHealthText OBJECT-TYPE
    SYNTAX DisplayString (SIZE (0..255))
    ACCESS read-only
    STATUS mandatory
    DESCRIPTION
  "A textual description of the power supply's
  operational status. Agents may use this string to
  provide detailed information on current failures,
  including how they were detected, and/or
  instructions for problem resolution. The contents
  are agent-specific."
    ::= { ncdchassPowerSupplyEntry 5 }

ncdchassPowerSupplyWarnings OBJECT-TYPE
    SYNTAX Counter
    ACCESS read-only
    STATUS mandatory
    DESCRIPTION
  "The number of times ncdchassPowerSupplyOperStatus has
  gone to warning(5)."
    ::= { ncdchassPowerSupplyEntry 6 }

ncdchassPowerSupplyFailures OBJECT-TYPE
    SYNTAX Counter
    ACCESS read-only
    STATUS mandatory
    DESCRIPTION
  "The number of times ncdchassPowerSupplyOperStatus has
  gone to bad(4)."
    ::= { ncdchassPowerSupplyEntry 7 }

ncdchassPowerSupplyLocationType OBJECT-TYPE
    SYNTAX INTEGER
    ACCESS read-only
    STATUS mandatory
    DESCRIPTION
  "This defines the instance of a physical location
  type of the power supply.  Location Type together
  with location index completely defines the
  location of a power supply."
    ::= { ncdchassPowerSupplyEntry 8 }

ncdchassPowerSupplyLocationIndex  OBJECT-TYPE
   SYNTAX  INTEGER
   ACCESS  read-only
   STATUS  mandatory
   DESCRIPTION
  "Defines a particular instance of a physical
  location type."
   ::= { ncdchassPowerSupplyEntry 9 }

  -- the Environment table.

ncdchassEnvironTable OBJECT-TYPE
    SYNTAX SEQUENCE OF NcdchassEnvironEntry
    ACCESS not-accessible
    STATUS mandatory
    DESCRIPTION
            "A list of environmental entries, one for
            each environmental sensor in the ncdchasssis."
   ::= { ncdchassEnviron 1 }

               ncdchassEnvironEntry OBJECT-TYPE
   SYNTAX NcdchassEnvironEntry
   ACCESS not-accessible
   STATUS mandatory
   DESCRIPTION
           "Values for a environmental sensor."
  INDEX { ncdchassEnvironIndex }
  ::= { ncdchassEnvironTable 1 }

              NcdchassEnvironEntry ::= SEQUENCE {
  ncdchassEnvironIndex
      INTEGER,
  ncdchassEnvironSensor
      OBJECT IDENTIFIER,
  ncdchassEnvironStatus
      INTEGER,
  ncdchassEnvironWarnings
      Counter,
  ncdchassEnvironFailures
      Counter,
  ncdchassEnvironLocationType
      INTEGER,
  ncdchassEnvironLocationIndex
      INTEGER
  }

ncdchassEnvironIndex OBJECT-TYPE
    SYNTAX  INTEGER (1..65535)
    ACCESS  read-only
    STATUS  mandatory
    DESCRIPTION
  "A unique index for the environment for which this
  entry contains information."
    ::= { ncdchassEnvironEntry 1 }

ncdchassEnvironSensor OBJECT-TYPE
  SYNTAX OBJECT IDENTIFIER
  ACCESS read-only
  STATUS mandatory
  DESCRIPTION
          "The identification of an environmental
          sensor.  Other AutonomousType values may be
          defined elsewhere, in association with
          specific protocols."
 ::= { ncdchassEnvironEntry 2 }

ncdchassEnvironStatus OBJECT-TYPE
              SYNTAX INTEGER {
               unknown(1),
               bad(2),
               warning(3),
               good(4) }
               ACCESS read-only
               STATUS mandatory
              DESCRIPTION
         "Actual status indicated by the sensor.  It is
         an implementation specific matter whether the
         agent keeps entries with status unknown(1) in
         the table.  If unknown(1), counters are"
::= { ncdchassEnvironEntry 3 }

ncdchassEnvironWarnings OBJECT-TYPE
             SYNTAX Counter
             ACCESS read-only
             STATUS mandatory
             DESCRIPTION
        "The number of times ncdchassEnvironStatus has gone
        to warning(3)."
               ::= { ncdchassEnvironEntry 4 }

ncdchassEnvironFailures OBJECT-TYPE
             SYNTAX Counter
             ACCESS read-only
             STATUS mandatory
             DESCRIPTION
       "The number of times ncdchassEnvironStatus has gone
       to bad(2)."
              ::= { ncdchassEnvironEntry 5 }

ncdchassEnvironLocationType OBJECT-TYPE
            SYNTAX INTEGER
            ACCESS read-only
            STATUS mandatory
            DESCRIPTION
      "Defines the actual type of physical location that
      this environmental sensor occupies."
              ::= { ncdchassEnvironEntry 6 }

ncdchassEnvironLocationIndex OBJECT-TYPE
            SYNTAX INTEGER
            ACCESS read-only
            STATUS mandatory
            DESCRIPTION
      "This defines the particular instance of a
      physical location type which this environmental
      sensor occupies."
              ::= { ncdchassEnvironEntry 7 }


END
