-- *------------------------------------------------------------------
-- * ALTIGA-CAP.my:  The Altiga Networks capabilities MIB.
-- *
-- * Altiga Networks was acquired by Cisco Systems on March 29, 2000
-- *
-- * Copyright (c) 2002 by Cisco Systems, Inc.
-- * All rights reserved.
-- *
-- *------------------------------------------------------------------

ALTIGA-CAP DEFINITIONS ::= BEGIN

   IMPORTS
      MODULE-IDENTITY
         FROM SNMPv2-SMI
      AGENT-CAPABILITIES
         FROM SNMPv2-CONF
      altigaCaps, alCapModule
         FROM ALTIGA-GLOBAL-REG;

   altigaCapModule MODULE-IDENTITY
      LAST-UPDATED   "200209091200Z"
      ORGANIZATION   "Cisco Systems, Inc."
      CONTACT-INFO
         "Cisco Systems
          170 W Tasman Drive
          San Jose, CA  95134
          USA

          Tel: +1 800 553-NETS
          E-mail: cs-cvpn3000@cisco.com"

      DESCRIPTION
         "The Altiga Networks capabilities MIB models counters and
          objects that are of management interest for networks
          capabilities.
         
          Acronyms
          The following acronyms are used in this document:

            DHCP:       Dynamic Host Configuration Protocol

            DNS:        Domain Name Service

            FTP:        File Transfer Protocol

            HTTP:       HyperText Transfer Protocol

            ICMP:       Internet Control Message Protocol

            IP:         Internet Protocol

            L2TP:       Layer-2 Tunneling Protocol

            MIB:        Management Information Base

            PPP:        Point-to-Point Protocol

            PPTP:       Point-to-Point Tunneling Protocol

            SEP:        Scalable Encryption Processor

            SNMP:       Simple Network Management Protocol

            SSL:        Secure Sockets Layer

            TCP:        Transmission Control Protocol

            UDP:        User Datagram Protocol

         "

        REVISION "200209091200Z"
        DESCRIPTION
                "Updated MIB to comply to Cisco MIB Police standards.
                 Added missing supports for new Altiga MIBs.
                "

        REVISION "200207100000Z"
        DESCRIPTION
                "Updated with new header"

      ::= { alCapModule 1 }

-- +++++++++++++++++++++++++++++++++++++++++++++++++++++++
-- MIB Objects
-- +++++++++++++++++++++++++++++++++++++++++++++++++++++++

altigaBasicAgent AGENT-CAPABILITIES
   PRODUCT-RELEASE      "Altiga Agent v1.0"
   STATUS               obsolete
   DESCRIPTION          "Altiga SNMP Agent"

   SUPPORTS             SNMPv2-MIB
      INCLUDES          { snmpGroup, snmpSetGroup, systemGroup,
                          snmpBasicNotificationsGroup }

   SUPPORTS IP-MIB
      INCLUDES          { ipGroup, icmpGroup }

   SUPPORTS UDP-MIB
      INCLUDES          { udpGroup }

   SUPPORTS ALTIGA-VERSION-STATS-MIB
      INCLUDES          { altigaVersionStatsGroup }

   SUPPORTS ALTIGA-PPTP-STATS-MIB
      INCLUDES          { altigaPptpStatsGroup }

   SUPPORTS ALTIGA-PPP-STATS-MIB
      INCLUDES          { altigaPppStatsGroup }

   SUPPORTS ALTIGA-HTTP-STATS-MIB
      INCLUDES          { altigaHttpStatsGroup }

   SUPPORTS ALTIGA-L2TP-STATS-MIB
      INCLUDES          { altigaL2tpStatsGroup }

   SUPPORTS ALTIGA-SESSION-STATS-MIB
      INCLUDES          { altigaSessionStatsGroup }

   SUPPORTS ALTIGA-TELNET-STATS-MIB
      INCLUDES          { altigaTelnetStatsGroup }

   SUPPORTS ALTIGA-DHCP-STATS-MIB
      INCLUDES          { altigaDhcpStatsGroup }

   SUPPORTS ALTIGA-DNS-STATS-MIB
      INCLUDES          { altigaDnsStatsGroup }

   SUPPORTS ALTIGA-CERT-STATS-MIB
      INCLUDES          { altigaCertStatsGroup }

   SUPPORTS ALTIGA-SEP-STATS-MIB
      INCLUDES          { altigaSepStatsGroup }

   SUPPORTS ALTIGA-SYNC-STATS-MIB
      INCLUDES          { altigaSyncStatsGroup }

   SUPPORTS ALTIGA-T1E1-STATS-MIB
      INCLUDES          { altigaT1E1StatsGroup }

   SUPPORTS ALTIGA-SSL-STATS-MIB
      INCLUDES          { altigaSslStatsGroup }

   SUPPORTS ALTIGA-EVENT-STATS-MIB
      INCLUDES          { altigaEventStatsGroup }

   SUPPORTS ALTIGA-FILTER-STATS-MIB
      INCLUDES          { altigaFilterStatsGroup }

   SUPPORTS ALTIGA-FTP-STATS-MIB
      INCLUDES          { altigaFtpStatsGroup }

   SUPPORTS ALTIGA-GENERAL-STATS-MIB
      INCLUDES          { altigaGeneralStatsGroup }

   SUPPORTS ALTIGA-HARDWARE-STATS-MIB
      INCLUDES          { altigaHardwareStatsGroup }

   ::= { altigaCaps 1 }

altigaBasicAgentRev1 AGENT-CAPABILITIES
   PRODUCT-RELEASE      "Altiga Agent v1.1"
   STATUS               current
   DESCRIPTION          "Altiga SNMP Agent"

   SUPPORTS SNMPv2-MIB
      INCLUDES          { snmpGroup, snmpSetGroup, systemGroup,
                          snmpBasicNotificationsGroup }

   SUPPORTS ALTIGA-ADDRESS-STATS-MIB
      INCLUDES          { altigaAddressStatsGroup }

   SUPPORTS ALTIGA-CERT-STATS-MIB
      INCLUDES          { altigaCertStatsGroup }

   SUPPORTS ALTIGA-DHCP-SERVER-STATS-MIB
      INCLUDES          { altigaDhcpServerStatsGroup }

   SUPPORTS ALTIGA-DHCP-STATS-MIB
      INCLUDES          { altigaDhcpStatsGroup }

   SUPPORTS ALTIGA-DNS-STATS-MIB
      INCLUDES          { altigaDnsStatsGroup }

   SUPPORTS ALTIGA-EVENT-STATS-MIB
      INCLUDES          { altigaEventStatsGroup }

   SUPPORTS ALTIGA-FILTER-STATS-MIB
      INCLUDES          { altigaFilterStatsGroup }

   SUPPORTS ALTIGA-FTP-STATS-MIB
      INCLUDES          { altigaFtpStatsGroup }

   SUPPORTS ALTIGA-GENERAL-STATS-MIB
      INCLUDES          { altigaGeneralStatsGroup }

   SUPPORTS ALTIGA-HARDWARE-STATS-MIB
      INCLUDES          { altigaHardwareStatsGroup }

   SUPPORTS ALTIGA-HTTP-STATS-MIB
      INCLUDES          { altigaHttpStatsGroup }

   SUPPORTS ALTIGA-IP-STATS-MIB
      INCLUDES          { altigaIpStatsGroup }

   SUPPORTS ALTIGA-L2TP-STATS-MIB
      INCLUDES          { altigaL2tpStatsGroup }

   SUPPORTS ALTIGA-LBSSF-STATS-MIB
      INCLUDES          { altigaStatsLBSSFGroup }

   SUPPORTS ALTIGA-MULTILINK-STATS-MIB
      INCLUDES          { altigaMultiLinkStatsGroup }

   SUPPORTS ALTIGA-NAT-STATS-MIB
      INCLUDES          { altigaNatStatsGroup }

   SUPPORTS ALTIGA-PPP-STATS-MIB
      INCLUDES          { altigaPppStatsGroup }

   SUPPORTS ALTIGA-PPPOE-STATS-MIB
      INCLUDES          { altigaPPPoEStatsGroup }

   SUPPORTS ALTIGA-PPTP-STATS-MIB
      INCLUDES          { altigaPptpStatsGroup }

   SUPPORTS ALTIGA-SDI-ACE-STATS-MIB
      INCLUDES          { altigaACEServerGroup }

   SUPPORTS ALTIGA-SEP-STATS-MIB
      INCLUDES          { altigaSepStatsGroup }

   SUPPORTS ALTIGA-SESSION-STATS-MIB
      INCLUDES          { altigaSessionStatsGroup }

   SUPPORTS ALTIGA-SSH-STATS-MIB
      INCLUDES          { altigaSshStatsGroup }

   SUPPORTS ALTIGA-SSL-STATS-MIB
      INCLUDES          { altigaSslStatsGroup }

   SUPPORTS ALTIGA-SYNC-STATS-MIB
      INCLUDES          { altigaSyncStatsGroup }

   SUPPORTS ALTIGA-T1E1-STATS-MIB
      INCLUDES          { altigaT1E1StatsGroup }

   SUPPORTS ALTIGA-TELNET-STATS-MIB
      INCLUDES          { altigaTelnetStatsGroup }

   SUPPORTS ALTIGA-VERSION-STATS-MIB
      INCLUDES          { altigaVersionStatsGroup }

   SUPPORTS IP-MIB
      INCLUDES          { ipGroup, icmpGroup }

   SUPPORTS UDP-MIB
      INCLUDES          { udpGroup }

   ::= { altigaCapModule 1 }
END
