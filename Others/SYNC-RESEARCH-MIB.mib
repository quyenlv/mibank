-- $Revision:   1.8  $
SYNC-RESEARCH-MIB DEFINITIONS ::= BEGIN

  IMPORTS
    -- If any of the MIB compilers have problems with the
    -- internet, mgmt, NetworkAddress, IpAddess, Counter, Gauge,
    -- TimeTicks, enterprises, uncomment the next two lines and\
    -- comment the next third and forth line.

    --internet, mgmt, NetworkAddress, IpAddress, Counter, Gauge,
    --TimeTicks, enterprises

    enterprises, IpAddress, Counter, Gauge
      FROM RFC1155-SMI
    OBJECT-TYPE
      FROM RFC-1212
    --syncResearch
    --FROM SYNC-RESEARCH-COMMUNITY-MIB
    TRAP-TYPE
      FROM RFC-1215;
  --
  -- Sync Research interNode MIB Version 4.0
  --
  -- The MIB was developed by Sync Research. It is not compatible
  -- with versions prior to 3.1 of MIBs published by Sync Research.
  --
  --
  -- Last Modification:
  --
  -- 08/21/95 Suketu Pandya version 4.0.3
  --    Added cable type variable for lineStatusChanged trap.
  -- 08/14/95 Suketu Pandya version 4.0.2
  --    Added new values for unitModel,
  --          brStatsGroup, and
  --          lineSwitchedConnection (VAR in linePhysicalGroup)
  --          frameRelayExcessBurst
  --          frameRelayCommittedBurst
  -- 07/18/95 Suketu Pandya version 4.0.1
  --    Added sysobjectids for R4 (Sync, Cabletron and 3Com)
  -- 06/23/95 Suketu Pandya version 4.0.0
  --    Added the following new MIB vriables:
  --         excessBurstGovernor            [unitConfigGroup]
  --         measurementPeriod              [unitConfigGroup]
  --         markDEBit                      [unitConfigGroup]
  --         frExtCircuitTxDe               [frExtCircuitEntry]
  --         frExtCircuitRxDe               [frExtCircuitEntry]
  --         frExtCircuitMinBits            [frExtCircuitEntry]
  --         frExtCircuitMaxBits            [frExtCircuitEntry]
  --         frExtCircuitQOctets            [frExtCircuitEntry]
  --         frameRelaySessSwitchThreshold  [frameRelayConfigEntry]
  --         frameRelaySwitchedBackup       [frameRelayConfigEntry]
  --         frameRelaySwitchedLineWaitTimer[frameRelayConfigEntry]
  --         frameRelayDedLineWaitTimer     [frameRelayConfigEntry]
  --         frameRelayTxDe                 [frameRelayStatsEntry]
  --         frameRelayRxDe                 [frameRelayStatsEntry]
  --         frameRelaySwitchedAttempts     [frameRelayStatsEntry]
  --         frameRelaySwitchedAttemptsSuccessful
  --                                        [frameRelayStatsEntry]
  --
  --    Also added the following TRAPs:
  --         lostUNI
  --         restoredUNI
  --         switchedToBackup
  --         switchedToDed
  --
  --
  --
  -- 07/18/95 Suketu Pandya  Version 3.2
  --    Added QLLC CN sysobject id for Cabletron and added
  --    R3 Object IDs.
  -- 06/12/95 Kevin Wong
  --    Change frExtCircuitTable entries Ignored and Acknowledged to yes/no.
  --    Chnage values of consolidated status constants in the unitControlGroup.
  --    Change description for puCurrentMAC in the puControlGroup.
  --    Change description for puLastClearCode in the puControlGroup.
  -- 02/28/95 Kevin Wong and Suketu Pandya,
  --    Obsolete puMappingGroup with puRemoteGroup.
  --    Added t7ConfigGroup for T7 protocol support.
  --    Added lineAsyncGroup, and puAsyncGroup for Async support.
  --    Added variables to unitConfigGroup and for best WAN support.
  --    Added variable to the unitControlGroup, lineControlGroup,
  --       and puControlGroup consolidated status support.
  --    Added nodeFrCirGroup  to support consolidated status for
  --       frame relay virtual circuits.
  --    Added sessSwitchedToPrimaryDLCI TRAP.
  --    Added sessSwitchedToParallelDLCI TRAP.
  --    Added sessUpOnPrimaryDLCI TRAP.
  --    Added sessUpOnParallelDLCI TRAP.
  --    Added sessUpOnAlternateDLCI TRAP.
  --    Added sessUpOnBroadCastDLCI TRAP.
  --    Added sessUpOnAlternateMAC TRAP.
  --    Obolete puConnectionStatusUp and puConnectionStatusDown Traps.
  --
  -- 01/27/95 Pam Tossey, Added variables to puControlGroup, and
  -- netviewControlGroup to count connection attempts.
  -- Addeded two new traps, puConnectionStatusUp and
  -- puConnectionStatusDown if the connection state changes for PU, netview
   -- PUs, and alternate netview PUs. Trap number 808 is no longer generated.
  -- The varbind list for port and PU traps was changed to include port and
  -- PU ids.
  --
  -- 12/27/94 Pam Tossey, Modified IMPORTS definitions of the MIB module
  -- (synccomb.mib) so that it is compiled using Sync's tools (amc).
  -- MIB module synccomb.mib contains all objects for Sync's MIB and
  -- Sync Community MIB and Traps.
  --
  -- 12/21/94 Steve Christle, corrected bug in msExtBoardType definition.
  --
  -- 11/17/94 Pam Tossey, Modified password and configpassword to have
  -- read-write access.
  --
  -- 11/08/94 Pam Tossey, Modified Sync's MIBs to include our OEM partners
  -- new products.
  --
  -- 08/31/94 Pam Tossey, changed variable access of dateTimeField to
  -- read-write.
  --
  -- 06/13/94 Steve Christle, Pam Tossey, Sync Research, Version 2.0
  -- initial definition supporting FN4R2, CN4
  --
  --  This MIB module uses the extended OBJECT-TYPE macro as
  --  defined in RFC1212.
  --
  -- If any of the MIB compilers have problems with the DisplayString
  -- or PhysAddress, uncomment the next two lines.
  --
  DisplayString    ::=  OCTET STRING
  PhysAddress      ::=  OCTET STRING

  -- internet        OBJECT IDENTIFIER ::= { iso org(3) dod(6) 1 }
  -- directory       OBJECT IDENTIFIER ::= { internet 1 }
  -- mgmt            OBJECT IDENTIFIER ::= { internet 2 }
  -- experimental    OBJECT IDENTIFIER ::= { internet 3 }
  -- private         OBJECT IDENTIFIER ::= { internet 4 }
  -- enterprises     OBJECT IDENTIFIER ::= { private 1 }

  syncResearch    OBJECT IDENTIFIER ::= { enterprises 485 }

  -- The next variable agent object ID.

  syncResearchAgent  OBJECT IDENTIFIER ::= { syncResearch 1 }

  -- The syncProducts group contains both Sync Research's Frame Node and
  -- Conversion Node.

  syncProducts    OBJECT IDENTIFIER ::= { syncResearchAgent 1 }

  -- The oemProducts group contains Sync Research's OEM products

  oemProducts    OBJECT IDENTIFIER ::= { syncResearchAgent 2 }

  -- Subgroup of syncProducts

  boundary      OBJECT IDENTIFIER ::= { syncProducts 1 }
  centralSite    OBJECT IDENTIFIER ::= { syncProducts 2 }

  -- Subgroups of the Boundary Group

  syncCN2R2b    OBJECT IDENTIFIER ::= { boundary 1 }
  syncFN2R2b    OBJECT IDENTIFIER ::= { boundary 2 }
  syncCN4R2b    OBJECT IDENTIFIER ::= { boundary 3 }
  syncFN4R2b    OBJECT IDENTIFIER ::= { boundary 4 }
  syncQN4R2b    OBJECT IDENTIFIER ::= { boundary 5 }
  syncCN4R3b    OBJECT IDENTIFIER ::= { boundary 6 }
  syncFN4R3b    OBJECT IDENTIFIER ::= { boundary 7 }
  syncQN4R3b    OBJECT IDENTIFIER ::= { boundary 8 }
  syncCN4R4b    OBJECT IDENTIFIER ::= { boundary 9 }
  syncFN4R4b    OBJECT IDENTIFIER ::= { boundary 10 }
  syncQN4R4b    OBJECT IDENTIFIER ::= { boundary 11 }
  syncCN4R4bu   OBJECT IDENTIFIER ::= { boundary 12 }
  syncFN4R4bu   OBJECT IDENTIFIER ::= { boundary 13 }
  syncQN4R4bu   OBJECT IDENTIFIER ::= { boundary 14 }
  syncCN4R4du   OBJECT IDENTIFIER ::= { boundary 15 }
  syncFN4R4du   OBJECT IDENTIFIER ::= { boundary 16 }
  syncQN4R4du   OBJECT IDENTIFIER ::= { boundary 17 }
  syncCN2R2du   OBJECT IDENTIFIER ::= { boundary 18 }
  syncFN2R2du   OBJECT IDENTIFIER ::= { boundary 19 }
  syncCN3R4bu   OBJECT IDENTIFIER ::= { boundary 20 }
  syncFN3R4bu   OBJECT IDENTIFIER ::= { boundary 21 }
  syncCN3R4du   OBJECT IDENTIFIER ::= { boundary 22 }
  syncFN3R4du   OBJECT IDENTIFIER ::= { boundary 23 }
  syncCN4R5b    OBJECT IDENTIFIER ::= { boundary 24 }
  syncFN4R5b    OBJECT IDENTIFIER ::= { boundary 25 }
  syncQN4R5b    OBJECT IDENTIFIER ::= { boundary 26 }

  syncCN4R5bu   OBJECT IDENTIFIER ::= { boundary 27 }
  syncFN4R5bu   OBJECT IDENTIFIER ::= { boundary 28 }
  syncQN4R5bu   OBJECT IDENTIFIER ::= { boundary 29 }
  syncCN4R5du   OBJECT IDENTIFIER ::= { boundary 30 }
  syncFN4R5du   OBJECT IDENTIFIER ::= { boundary 31 }
  syncQN4R5du   OBJECT IDENTIFIER ::= { boundary 32 }
  syncFN5R5du   OBJECT IDENTIFIER ::= { boundary 33 }
  syncBC4R5b    OBJECT IDENTIFIER ::= { boundary 34 }
  syncBF4R5b    OBJECT IDENTIFIER ::= { boundary 35 }
  syncBF3R5b    OBJECT IDENTIFIER ::= { boundary 36 }
  syncBF5R5b    OBJECT IDENTIFIER ::= { boundary 37 }

  -- Added Sync's 4200 products for release 5.600
  syncFN3R5du   OBJECT IDENTIFIER ::= { boundary 38 }
  syncCN3R5du   OBJECT IDENTIFIER ::= { boundary 39 }
  syncCN5R5du   OBJECT IDENTIFIER ::= { boundary 40 }

  -- Sync's 3600 products for release 5.600
  syncBF3R5     OBJECT IDENTIFIER ::= { boundary 41 }
  syncBC3R5     OBJECT IDENTIFIER ::= { boundary 42 }
  syncBF4R5     OBJECT IDENTIFIER ::= { boundary 43 }
  syncBC4R5     OBJECT IDENTIFIER ::= { boundary 44 }
  syncBF5R5     OBJECT IDENTIFIER ::= { boundary 45 }
  syncBC5R5     OBJECT IDENTIFIER ::= { boundary 46 }

  -- Subgroups of the CentralSite Group

  syncCN4R2c    OBJECT IDENTIFIER ::= { centralSite 1 }
  syncFN4R2c    OBJECT IDENTIFIER ::= { centralSite 2 }
  syncQN4R2c    OBJECT IDENTIFIER ::= { centralSite 3 }
  syncCN4R3c    OBJECT IDENTIFIER ::= { centralSite 4 }
  syncFN4R3c    OBJECT IDENTIFIER ::= { centralSite 5 }
  syncQN4R3c    OBJECT IDENTIFIER ::= { centralSite 6 }
  syncCN4R4u    OBJECT IDENTIFIER ::= { centralSite 7 }
  syncFN4R4u    OBJECT IDENTIFIER ::= { centralSite 8 }
  syncQN4R4u    OBJECT IDENTIFIER ::= { centralSite 9 }

  -- Subgroups of oemProducts

  threeCom     OBJECT IDENTIFIER ::= { oemProducts 1 }
  cableTron    OBJECT IDENTIFIER ::= { oemProducts 2 }
  chipcom      OBJECT IDENTIFIER ::= { oemProducts 3 }
  ibm          OBJECT IDENTIFIER ::= { oemProducts 4 }

  -- Subgroups of the threeCom EOM

  linkConverter    OBJECT IDENTIFIER ::= { threeCom 1 }
  linkConverter2   OBJECT IDENTIFIER ::= { threeCom 2 }
      -- 486 based linconverters, Ethernet and Token Ring
      -- 4 port and 2port.
  lc2EN2port       OBJECT IDENTIFIER ::= { threeCom 3 }
  lc2EN4port       OBJECT IDENTIFIER ::= { threeCom 4 }
  lc2TR2port       OBJECT IDENTIFIER ::= { threeCom 5 }
  lc2TR6port       OBJECT IDENTIFIER ::= { threeCom 6 }


  -- Subgroups of the CableTron OEM

  oemSNACXR2C    OBJECT IDENTIFIER ::= { cableTron 1 }
  oemSNACXR2W    OBJECT IDENTIFIER ::= { cableTron 2 }
  oemSNACMR2C    OBJECT IDENTIFIER ::= { cableTron 3 }
  oemSNACMR2W    OBJECT IDENTIFIER ::= { cableTron 4 }
  oemSNACMIM2    OBJECT IDENTIFIER ::= { cableTron 5 }
  oemSNACXR2Q    OBJECT IDENTIFIER ::= { cableTron 6 }
  oemSNACMR2Q    OBJECT IDENTIFIER ::= { cableTron 7 }
  oemSNACXR3C    OBJECT IDENTIFIER ::= { cableTron 8 }
  oemSNACXR3W    OBJECT IDENTIFIER ::= { cableTron 9 }
  oemSNACMR3C    OBJECT IDENTIFIER ::= { cableTron 10 }
  oemSNACMR3W    OBJECT IDENTIFIER ::= { cableTron 11 }
  oemSNACXR3Q    OBJECT IDENTIFIER ::= { cableTron 12 }
  oemSNACMR3Q    OBJECT IDENTIFIER ::= { cableTron 13 }
  oemSNACXR4C    OBJECT IDENTIFIER ::= { cableTron 14 }
  oemSNACXR4W    OBJECT IDENTIFIER ::= { cableTron 15 }
  oemSNACMR4C    OBJECT IDENTIFIER ::= { cableTron 16 }
  oemSNACMR4W    OBJECT IDENTIFIER ::= { cableTron 17 }
  oemSNACXR4Q    OBJECT IDENTIFIER ::= { cableTron 18 }
  oemSNACMR4Q    OBJECT IDENTIFIER ::= { cableTron 19 }

-- Subgroups of the IBM OEM

   oem2490R22F   OBJECT IDENTIFIER ::= { ibm 1 }
   oem2490R22C   OBJECT IDENTIFIER ::= { ibm 2 }
   -- 486 based 2mB DRAM/2mB FLASH
   oem22181FR4   OBJECT IDENTIFIER ::= { ibm 3 }
   oem22181CR4   OBJECT IDENTIFIER ::= { ibm 4 }
   -- 486 based 4mB DRAM/2mB FLASH
   oem22183FR4   OBJECT IDENTIFIER ::= { ibm 5 }
   oem22183CR4   OBJECT IDENTIFIER ::= { ibm 6 }
   -- 486 based 2mB DRAM/2mB FLASH
   oem22181FR5   OBJECT IDENTIFIER ::= { ibm 7 }
   oem22181CR5   OBJECT IDENTIFIER ::= { ibm 8 }
   -- 486 based 4mB DRAM/2mB FLASH
   oem22183FR5   OBJECT IDENTIFIER ::= { ibm 9 }
   oem22183CR5   OBJECT IDENTIFIER ::= { ibm 10 }
   -- 486 based 8mB DRAM/2mB FLASH
   oem22185FR5   OBJECT IDENTIFIER ::= { ibm 11 }

   -- Added IBM's 4200 product for release 5.600
   oem22185CR5   OBJECT IDENTIFIER ::= { ibm 12 }

   -- IBM's 3600 products for release 5.600
   oem22183BF5   OBJECT IDENTIFIER ::= { ibm 13 }
   oem22183BC5   OBJECT IDENTIFIER ::= { ibm 14 }
   oem22184BF5   OBJECT IDENTIFIER ::= { ibm 15 }
   oem22184BC5   OBJECT IDENTIFIER ::= { ibm 16 }
   oem22185BF5   OBJECT IDENTIFIER ::= { ibm 17 }
   oem22185BC5   OBJECT IDENTIFIER ::= { ibm 18 }


  -- The Node group contains both the Frame Node and Conversion Node.

  srNodeGroup    OBJECT IDENTIFIER ::= { syncResearch 3 }

  -- Subgroups of the Node group.

  nodeUnitGroup       OBJECT IDENTIFIER ::= { srNodeGroup 1 }
  nodeNetViewPUGroup  OBJECT IDENTIFIER ::= { srNodeGroup 2 }
  nodeBridgeGroup     OBJECT IDENTIFIER ::= { srNodeGroup 3 }
  nodeLANGroup        OBJECT IDENTIFIER ::= { srNodeGroup 4 }
  nodeLineGroup       OBJECT IDENTIFIER ::= { srNodeGroup 5 }
  nodePUGroup         OBJECT IDENTIFIER ::= { srNodeGroup 6 }
  nodeDeviceGroup     OBJECT IDENTIFIER ::= { srNodeGroup 7 }
  nodeT7Group         OBJECT IDENTIFIER ::= { srNodeGroup 8 }
  nodeFrCirGroup      OBJECT IDENTIFIER ::= { srNodeGroup 9 }
  nodeSlipGroup       OBJECT IDENTIFIER ::= { srNodeGroup 10}
  nodeIpxGroup        OBJECT IDENTIFIER ::= { srNodeGroup 11}
  nodeIpGroup         OBJECT IDENTIFIER ::= { srNodeGroup 12}


  -- Subgroups of the Unit Group

  unitControlGroup    OBJECT IDENTIFIER ::= { nodeUnitGroup 1 }
  unitStatusGroup     OBJECT IDENTIFIER ::= { nodeUnitGroup 2 }
  unitConfigGroup     OBJECT IDENTIFIER ::= { nodeUnitGroup 3 }
  unitStatisticsGroup OBJECT IDENTIFIER ::= { nodeUnitGroup 4 }

  -- Subgroups of the Netview Group

  netViewPUStatusGroup  OBJECT IDENTIFIER ::= { nodeNetViewPUGroup 1 }
  netViewPUConfigGroup  OBJECT IDENTIFIER ::= { nodeNetViewPUGroup 2 }

  -- Subgroups of the Bridge Group

  bridgeConfigGroup  OBJECT IDENTIFIER ::= { nodeBridgeGroup 1 }
  bridgeStatsGroup   OBJECT IDENTIFIER ::= { nodeBridgeGroup 2 }

  -- Subgroups of the IPX Group

  ipxConfigGroup  OBJECT IDENTIFIER ::= { nodeIpxGroup 1 }

  -- Subgroups of the IP Group

  ipConfigGroup  OBJECT IDENTIFIER ::= { nodeIpGroup 1 }

  -- Subgroups of the LAN Group

  lanControlGroup    OBJECT IDENTIFIER ::= { nodeLANGroup 1 }
  lanTokenRingGroup  OBJECT IDENTIFIER ::= { nodeLANGroup 2 }

  -- Subgroups of the Line Group

  lineControlGroup    OBJECT IDENTIFIER ::= { nodeLineGroup 1 }
  linePhysicalGroup   OBJECT IDENTIFIER ::= { nodeLineGroup 2 }
  lineSDLCGroup       OBJECT IDENTIFIER ::= { nodeLineGroup 3 }
  lineBisyncGroup     OBJECT IDENTIFIER ::= { nodeLineGroup 4 }
  lineFrameRelayGroup OBJECT IDENTIFIER ::= { nodeLineGroup 5 }
  lineAsyncGroup      OBJECT IDENTIFIER ::= { nodeLineGroup 6 }
  lineBisyncRjeGroup  OBJECT IDENTIFIER ::= { nodeLineGroup 7 }
  lineDialBackupGroup OBJECT IDENTIFIER ::= { nodeLineGroup 8 }
  lineX25Group        OBJECT IDENTIFIER ::= { nodeLineGroup 9 }
  lineAlcGroup        OBJECT IDENTIFIER ::= { nodeLineGroup 10}

  -- Subgroups of the LinePhysical Group

  isdnControlGroup    OBJECT IDENTIFIER ::= { linePhysicalGroup 2 }
  dsucsuControlGroup  OBJECT IDENTIFIER ::= { linePhysicalGroup 3 }

  -- Other future Line types (e.g. X.25) would be added here.

  -- Note Token Ring Statistics are obtained via the 802.5 standard
  -- MIB as defined in RFC 1231, and Ethernet via 802.3 standard MIB

  -- Subgroups of the PU Group

  puControlGroup      OBJECT IDENTIFIER ::= { nodePUGroup 1 }
  puSDLCGroup         OBJECT IDENTIFIER ::= { nodePUGroup 2 }
  puBisyncGroup       OBJECT IDENTIFIER ::= { nodePUGroup 3 }
  puMappingGroup      OBJECT IDENTIFIER ::= { nodePUGroup 4 }
  puAsyncGroup        OBJECT IDENTIFIER ::= { nodePUGroup 5 }
  puLanGroup          OBJECT IDENTIFIER ::= { nodePUGroup 6 }
  puRemoteGroup       OBJECT IDENTIFIER ::= { nodePUGroup 7 }
  puX25Group          OBJECT IDENTIFIER ::= { nodePUGroup 8 }
  puAlcGroup          OBJECT IDENTIFIER ::= { nodePUGroup 9 }
  puBisyncRjeGroup    OBJECT IDENTIFIER ::= { nodePUGroup 10}

  -- Subgroups of the Device Group

  deviceControlGroup  OBJECT IDENTIFIER ::= { nodeDeviceGroup 1 }
  deviceBSCGroup      OBJECT IDENTIFIER ::= { nodeDeviceGroup 2 }
  deviceALCGroup      OBJECT IDENTIFIER ::= { nodeDeviceGroup 3 }

  -- Subgroups of the T7 Group

  t7ConfigGroup       OBJECT IDENTIFIER ::= { nodeT7Group 1 }
  t7StatsGroup        OBJECT IDENTIFIER ::= { nodeT7Group 2 }

  -- Subgroups of the Slip Group

  slipConfigGroup     OBJECT IDENTIFIER ::= { nodeSlipGroup 1 }
  slipStatsGroup      OBJECT IDENTIFIER ::= { nodeSlipGroup 2 }

  -- The Sync Research Community Name and Trap Group

  srCommTrapGroup     OBJECT IDENTIFIER ::= { syncResearch 2 }

  commCount OBJECT-TYPE
    SYNTAX  INTEGER (0..32)
    ACCESS  read-only
    STATUS  mandatory
    DESCRIPTION
      "The number of possible community name entries
      in the table."
    ::= { srCommTrapGroup 1 }

  commTable OBJECT-TYPE
    SYNTAX  SEQUENCE OF CommEntry
    ACCESS  not-accessible
    STATUS  mandatory
    DESCRIPTION
      "This table houses the information for trivial
      authentication and sending traps."
    ::= { srCommTrapGroup 2 }

  commEntry OBJECT-TYPE
    SYNTAX  CommEntry
    ACCESS  not-accessible
    STATUS  mandatory
    DESCRIPTION
      "Each entry contains a community name and access code
      for SNMP trivial authentication and enable/disable traps
      options, as well as network and physical addressing
      information for traps."
    INDEX  { commIndex }
    ::= { commTable 1 }

  CommEntry ::= SEQUENCE {
    commIndex
      INTEGER,
    commName
      OCTET STRING,
    commTrap
      INTEGER,
    commIPAddr
      IpAddress,
    commMACAddr
      OCTET STRING,
    commAccess
      INTEGER
    }

  commIndex OBJECT-TYPE
    SYNTAX  INTEGER
    ACCESS  read-only
    STATUS  mandatory
    DESCRIPTION
      "A unique value for each community entry. Its value
      ranges between 1 and commCount."
    ::= { commEntry 1 }

  commName OBJECT-TYPE
    SYNTAX  OCTET STRING
    ACCESS  read-write
    STATUS  mandatory
    DESCRIPTION
      "A community name that will be used to access MIB
      objects. Each community name is  associated with
      an access code of either NO-ACCESS, RO,  RW, or SU."
    ::= { commEntry 2 }

  commTrap OBJECT-TYPE
    SYNTAX  INTEGER {
      trapoff(1),
      trapon(2)
      }
    ACCESS  read-write
    STATUS  mandatory
    DESCRIPTION
      "This object is checked to determine if traps should be
      sent to the corresponding network address associated
      with it."
    ::= { commEntry 3 }

  commIPAddr OBJECT-TYPE
    SYNTAX  IpAddress
    ACCESS  read-write
    STATUS  mandatory
    DESCRIPTION
      "The network address of the device that will receive
      traps from the agent. This IP address also qualifies
      who may use this community name to access MIB objects.
      If this community name is use by some one with a
      different IP address, an Authentication Trap will
      be generated. If the IP address is set to 0.0.0.0,
      anyone may use this address, however, traps will
      not be sent since the address is invalid."
    ::= { commEntry 4 }

  commMACAddr OBJECT-TYPE
    SYNTAX  OCTET STRING
    ACCESS  read-only
    STATUS  mandatory
    DESCRIPTION
      "The physical address of the device receiving traps
      from the agent."
    ::= { commEntry 5 }

  commAccess OBJECT-TYPE
    SYNTAX  INTEGER {
      noAccess(1),
      ro(2),
      rw(3),
      su(4)
      }
    ACCESS  read-write
    STATUS  mandatory
    DESCRIPTION
      "Access code assiciated with the community name of the
      same entry. noAccess indicates a community name with
      zero privileges. ro has read-only access to MIB objects.
      rw allows you to read and write MIB objects. SU (super-
      user) gives you privileges to read and write any MIB
      object. The community table itself can only be written
      to with an access of SU as well as the setting of the
      IP Address on a device."
    ::= { commEntry 6 }



  --
  -- The Unit Control Group
  --

  unitRestart  OBJECT-TYPE
    SYNTAX  INTEGER {
      restart-unit(1),
      dummy-restart(2)
      }
    ACCESS  read-write
    STATUS  mandatory
    DESCRIPTION
      "Setting this variable to a value of 1 will
      force the unit to restart. Setting this variable
      to any other value will cause an SNMP error.
      This variable always returns a value of 2."
    ::= { unitControlGroup 1 }

  dumpOnRestart  OBJECT-TYPE
    SYNTAX  INTEGER {
      dump-on-start(1),
      dont-dump(2)
      }
    ACCESS  read-write
    STATUS  mandatory
    DESCRIPTION
      "Setting this variable to a value of 1 will
      force the unit to perform a dump on restart. Setting
      this variable to a value of 2 will force it to not
      to dump on restart."
    ::= { unitControlGroup 2 }

  initiateInstall  OBJECT-TYPE
    SYNTAX  INTEGER {
      start-install(1),
      dummy-install(2)
      }
    ACCESS  read-write
    STATUS  mandatory
    DESCRIPTION
      "Setting this variable to a value of 1 will force
      the unit to initiate an install process. This variable
      always returns a value of 2."
    ::= { unitControlGroup 3 }


  initializeStats  OBJECT-TYPE
    SYNTAX  INTEGER {
      init-stats(1),
      dummy-init-stats(2)
      }
    ACCESS  read-write
    STATUS  mandatory
    DESCRIPTION
      "Setting this variable to a value of 1 will force
      the unit to initialize (clear) SyncResearch proprietary
      statistics kept by the unit.
      This variable always returns a value of 2."
    ::= { unitControlGroup 4 }

  clearDump  OBJECT-TYPE
    SYNTAX  INTEGER {
      clear-dump-file(1),
      dummy-clear(2)
      }
    ACCESS  read-write
    STATUS  mandatory
    DESCRIPTION
      "Setting this variable to a value of 1 will
      force the unit to clear a dump.
      This variable always returns a value of 2."
    ::= { unitControlGroup 5 }

  acknowledgeAllStatuses OBJECT-TYPE
    SYNTAX  INTEGER {
      yes (1),
      no  (2)
      }
    ACCESS  read-write
    STATUS  mandatory
    DESCRIPTION
      "This field is used for consolidating status of the
      unit. When this field is set to yes, the unit will
      mark each of the various statuses in different levels
      as acknowledged. It will then re-consolidate
      without putting these statuses into consideration.
      Subseqent change of these statuses will cause
      the unit to include them in computing the status of the
      unit. Setting the object to no has no effect."
    ::= { unitControlGroup 6 }

  consolidatedUnitStatus  OBJECT-TYPE
    SYNTAX  INTEGER {
      unknown   (1),
      normal    (2),
      informational (3),
      disabled (4),
      marginal (5),
      warning  (6),
      minor    (7),
      major    (8),
      critical (9)
      }
    ACCESS  read-only
    STATUS  mandatory
    DESCRIPTION
      "This object reports the consolidted status of the
      unit.  All acknowledged element statuses and any
      element statuses specified as ignored by the user are
      ignored for unit level status computation."
    ::= { unitControlGroup 7 }

  homeDialBackup  OBJECT-TYPE
    SYNTAX  INTEGER {
      home-dial-backup (1),
      dummy-home (2)
      }
    ACCESS  read-write
    STATUS  mandatory
    DESCRIPTION
      "Setting this variable to a value of 1 will force all
        dial backup lines to dedicated lines.   Setting this
        variable to any other value will case an SNMP error.
        This variable always returns a value of 2."
    ::= { unitControlGroup 8 }

  --
  -- Unit Status Group
  --
  -- This group contains the device status variables. There exists
  -- only one instance of this group per unit.
  --

  unitModel  OBJECT-TYPE
    SYNTAX  INTEGER {
      boundary(1),
      lic(2),
      chipcomPED(3),
      snacMIM(4),
      microMac(5),
      linkConverter (6),
      universal-boundary (7),
      universal-desktop (8),
      linkConverterII (9),
      ibm (10),
      sync3600(11),
      ibm3600(12)
      }
    ACCESS  read-only
    STATUS  mandatory
    DESCRIPTION
      "This variable defines the base hardware model of
       the unit."

    ::= { unitStatusGroup 1 }

  softwareVersion  OBJECT-TYPE
    SYNTAX  DisplayString (SIZE(1..6))
    ACCESS  read-only
    STATUS  mandatory
    DESCRIPTION
      "The current version number of the operating
       software in xx.yyy where xx = major release,
       yyy = revision."
    ::= { unitStatusGroup 2 }


  productType  OBJECT-TYPE
    SYNTAX  DisplayString (SIZE(1..8))
    ACCESS  read-only
    STATUS  mandatory
    DESCRIPTION
      "The product type string returned is set in the
      MS.SYS file and defines the product name."
    ::= { unitStatusGroup 3 }

  maxPortNumber  OBJECT-TYPE
    SYNTAX  INTEGER
    ACCESS  read-only
    STATUS  mandatory
    DESCRIPTION
      "The maximum number of ports this unit can
      support (total number of serial access ports plus
      total number of LAN ports)."
    ::= { unitStatusGroup 4 }

  maxPU    OBJECT-TYPE
    SYNTAX  INTEGER
    ACCESS  read-only
    STATUS  mandatory
    DESCRIPTION
      "The maximum number of PUs this unit can
      support (total number that can be configured)."
    ::= { unitStatusGroup 5 }


  maxSession    OBJECT-TYPE
    SYNTAX  INTEGER
    ACCESS  read-only
    STATUS  mandatory
    DESCRIPTION
      "The maximum number of sessions this unit can
      support (total number that can be configured)."
    ::= { unitStatusGroup 6 }

  maxDevice    OBJECT-TYPE
    SYNTAX  INTEGER
    ACCESS  read-only
    STATUS  mandatory
    DESCRIPTION
      "The maximum number of devices this unit can
      support (total number that can be configured)."
    ::= { unitStatusGroup 7 }

  msBoardType    OBJECT-TYPE
    SYNTAX  INTEGER {
      not-expected(1),
      two-port-RS232(16),
      two-port-RS422(17),
      two-port-V35(18),
      v35-RS232(22),
      rs422-RS232(23),
      two-port-universal(26),
      two-port-iusc-RS232(30)
      }
    ACCESS  read-only
    STATUS  mandatory
    DESCRIPTION
      "Indicates the type of serial I/O ports on
       main board.  It returns 1 if not expected."
    ::= { unitStatusGroup 8 }

  msExtBoardType    OBJECT-TYPE
    SYNTAX  INTEGER {
      not-present(1),
      two-port-RS232(19),
      two-port-RS422(20),
      two-port-V35(21),
      two-port-hspeedRS232(24),
      two-port-hspeedV35(25),
      two-port-universal(27),
      four-port-universal(28),
      six-port-universal(29)
      }
    ACCESS  read-only
    STATUS  mandatory
    DESCRIPTION
      "Indicates the type of serial I/O ports on
       extension board. It returns 1 if not present."
    ::= { unitStatusGroup 9 }

  dumpFileStatus   OBJECT-TYPE
    SYNTAX  INTEGER  {
      none (1),
      dump-available(2)
      }
    ACCESS  read-only
    STATUS  mandatory
    DESCRIPTION
      "Indicates the presence of a dump file."
    ::= { unitStatusGroup 10 }

  dumpFileName OBJECT-TYPE
    SYNTAX  DisplayString (SIZE(1..11))
    ACCESS  read-only
    STATUS  mandatory
    DESCRIPTION
      "The dump file name."
    ::= { unitStatusGroup 11 }

  unitSerialNumber OBJECT-TYPE
    SYNTAX  DisplayString (SIZE(1..9))
    ACCESS  read-only
    STATUS  mandatory
    DESCRIPTION
      "The base unit serial number."
    ::= { unitStatusGroup 12 }

  expansionSerialNumber OBJECT-TYPE
    SYNTAX  DisplayString (SIZE(1..9))
    ACCESS  read-only
    STATUS  mandatory
    DESCRIPTION
      "The expansion board serial number."
    ::= { unitStatusGroup 13 }

  romVersion OBJECT-TYPE
    SYNTAX  DisplayString (SIZE(1..16))
    ACCESS  read-only
    STATUS  mandatory
    DESCRIPTION
      "The ROM version number."
    ::= { unitStatusGroup 14 }

  processorType OBJECT-TYPE
    SYNTAX  INTEGER  {
      i286 (1),
      i386 (2),
      i486SX (3),
      i486DX (4),
      i486DX-2 (5),
      i486DX-4 (6)
      }
    ACCESS  read-only
    STATUS  mandatory
    DESCRIPTION
      "The base unit processor type."
    ::= { unitStatusGroup 15 }

  chassisSlot   OBJECT-TYPE
    SYNTAX  INTEGER (1..99)
    ACCESS  read-only
    STATUS  mandatory
    DESCRIPTION
      "If the unit is a blade in a chassis, then
      this variable indicates the slot number. If
      not applicable, a value of 99 will be returned."
    ::= { unitStatusGroup 16 }

  lastTrapSeqNumber   OBJECT-TYPE
    SYNTAX  INTEGER (0..65535)
    ACCESS  read-only
    STATUS  mandatory
    DESCRIPTION
      "This entry contains the last sequence number of the
      last trap generated by the unit. When this value
      reaches its maximum, it then rolls back to 0."
    ::= { unitStatusGroup 17 }

  lastInstallErrCode      OBJECT-TYPE
    SYNTAX  INTEGER (0..9999)
    ACCESS  read-only
    STATUS  mandatory
    DESCRIPTION
      "This entry contains the status of last install.
      If the last install was successful, 0 is returned,
      9999 indicates installation is in progress,
      otherwise an error code is returned."
    ::= { unitStatusGroup 18 }

  unitPartNumber OBJECT-TYPE
    SYNTAX  DisplayString (SIZE(1..19))
    ACCESS  read-only
    STATUS  mandatory
    DESCRIPTION
      "The base unit part number."
    ::= { unitStatusGroup 19 }

  expansionPartNumber OBJECT-TYPE
    SYNTAX  DisplayString (SIZE(1..19))
    ACCESS  read-only
    STATUS  mandatory
    DESCRIPTION
      "The expansion board part number."
    ::= { unitStatusGroup 20 }

  wan1BoardType    OBJECT-TYPE
    SYNTAX  INTEGER {
      not-present(1),
      dsu-csu(31)
      }
    ACCESS  read-only
    STATUS  mandatory
    DESCRIPTION
      "Indicates the type of serial I/O ports on
       extension board. It returns 1 if not present."
    ::= { unitStatusGroup 21 }

  wan2BoardType    OBJECT-TYPE
    SYNTAX  INTEGER {
      not-present(1),
      dsu-csu(31),
      isdn(32)
      }
    ACCESS  read-only
    STATUS  mandatory
    DESCRIPTION
      "Indicates the type of serial I/O ports on
       extension board. It returns 1 if not present."
    ::= { unitStatusGroup 22 }

  patchId OBJECT-TYPE
    SYNTAX  DisplayString (SIZE(1..4))
    ACCESS  read-only
    STATUS  mandatory
    DESCRIPTION
      "The current patch identifier for the operating
       software.  Either the three character Patch ID
       or 'None'"
    ::= { unitStatusGroup 23 }

  --
  -- The Unit Configuration Group

  -- Contains the current operational configuration of the unit

  unitId    OBJECT-TYPE
    SYNTAX  DisplayString (SIZE(1..8))
    ACCESS  read-only
    STATUS  mandatory
    DESCRIPTION
      "This is the unit id.  It consists of a 1 to 8 octet
       right justified case-sensitive ASCII field which
       uniquely identifies the unit.
       This ID is displayed on the LCD display if available,
       all system dumps, and any ASCII alarms.
       The defalult value for this field is startup."
    ::= { unitConfigGroup 1 }

  nmsSerialSpeed  OBJECT-TYPE
    SYNTAX  INTEGER {
      speed1200(12),
      speed2400(24),
      speed4800(48),
      speed9600(96),
      speed19200(192)
      }
    ACCESS  read-only
    STATUS  mandatory
    DESCRIPTION
      "The async serial port speed for NMS console port.
       The speed is expressed in bits per second (i.e.
       9.6 Kbps is represented as 96 decimal).
       Currently supported speeds are:
        1200
        2400
        4800
        9600
        19200
       Default speed is 9600 bits per second."
    ::= { unitConfigGroup 2 }

  serialPortLogoffTimer   OBJECT-TYPE
    SYNTAX  INTEGER (0..60)
    ACCESS  read-only
    STATUS  mandatory
    DESCRIPTION
      "Units are minutes. Default value is 0, indicating
      that no timer is active."
    ::= { unitConfigGroup 3 }

  callRetryTimer  OBJECT-TYPE
    SYNTAX  INTEGER (2..999)
    ACCESS  read-only
    STATUS  mandatory
    DESCRIPTION
      "The call retry timer (a.k.a Session Retry Timer).
      The number of seconds to wait before trying
      to retry a failed connection attempt.
      Currently supported values are 2 - 999 seconds.
      The default is 30 seconds."
    ::= { unitConfigGroup 4 }

  password  OBJECT-TYPE
    SYNTAX  DisplayString (SIZE(1..8))
    ACCESS  read-write
    STATUS  mandatory
    DESCRIPTION
      "The unit's password.
       This field indicates the system password used to
       log into the unit for operating the NMS interface.

       This field is a one to eight byte case-sensitive
       left justified ASCII data field and may not be
       left blank.

       The default value is 'sri' (for Sync Research Inc.),
       or 'ctron' for Cabletron products."
    ::= { unitConfigGroup 5 }

  configPassword  OBJECT-TYPE
    SYNTAX  DisplayString (SIZE(1..8))
    ACCESS  read-write
    STATUS  mandatory
    DESCRIPTION
      "The configuration password.
       This field indicates the password used to
       enter the configuration subsystem.

       This field is a one to eight byte case-sensitive
       left justified ASCII data field and may not be
       left blank.

       The default value is 'sri' (for Sync Research Inc.),
       or 'ctron' for Cabletron products."
    ::= { unitConfigGroup 6 }

  dateTimeField  OBJECT-TYPE
    SYNTAX  OCTET STRING (SIZE(6))
    ACCESS  read-write
    STATUS  mandatory
    DESCRIPTION
      "The date and time.
      This field is stored as 6 bytes of BCD Data in the
      following order:
         Month:      0x01 - 0x12
         Day:        0x01 - 0x31
         Year:       0x00 - 0x99
         Hour:       0x00 - 0x23
         Minute:     0x00 - 0x59
         Second:     0x00 - 0x59"
    ::= { unitConfigGroup 7 }

  configId    OBJECT-TYPE
    SYNTAX  DisplayString (SIZE(1..8))
    ACCESS  read-only
    STATUS  mandatory
    DESCRIPTION
      "The configuration identifer.
      This field is the configuration ID assigned
      when a new configuration is activated.
      first time.  It is assigned by the unit or a
      Sync Research management product (SyncMan)
      automatically and is not user assignable."
    ::= { unitConfigGroup 8 }

  internalMacAddress   OBJECT-TYPE
    SYNTAX  PhysAddress
    ACCESS  read-only
    STATUS  mandatory
    DESCRIPTION
      "Embedded conversion node MAC address. Applicable
      to Frame Node only."
    ::= { unitConfigGroup 9 }

  internalRingNumber   OBJECT-TYPE
    SYNTAX  INTEGER (1..4095)
    ACCESS  read-only
    STATUS  mandatory
    DESCRIPTION
      "Embedded conversion node ring number. This should
      be unique within the network. Applicable
      to Frame Node only."
    ::= { unitConfigGroup 10 }

  internalBridgeNumber   OBJECT-TYPE
    SYNTAX  INTEGER (1..15)
    ACCESS  read-only
    STATUS  mandatory
    DESCRIPTION
      "Embedded conversion node bridge number. This
      parameter is currently not used. Applicable
      to Frame Node only."
    ::= { unitConfigGroup 11 }

  internalMacAddress2   OBJECT-TYPE
    SYNTAX  PhysAddress
    ACCESS  read-only
    STATUS  mandatory
    DESCRIPTION
      "Optional second embedded conversion node MAC
      address. Applicable to Frame Node only."
    ::= { unitConfigGroup 12 }

  internalRingNumber2   OBJECT-TYPE
    SYNTAX  INTEGER (1..4095)
    ACCESS  read-only
    STATUS  mandatory
    DESCRIPTION
      "Optional second embedded conversion node
      ring number. This should be unique within the
      network. Applicable to Frame Node only."
    ::= { unitConfigGroup 13 }

  associatedPortNumber2   OBJECT-TYPE
    SYNTAX  INTEGER
    ACCESS  read-only
    STATUS  mandatory
    DESCRIPTION
      "Assigns the physical port number corresponding
      to the virtual port that the second embedded
      conversion node is associated with.
      Applicable to Frame Node only."
    ::= { unitConfigGroup 14 }

  associatedDLCI2         OBJECT-TYPE
    SYNTAX  INTEGER (0..1023)
    ACCESS  read-only
    STATUS  mandatory
    DESCRIPTION
      "Assigns the Frame Relay PVC number corresponding
      to the virtual port that the second embedded
      conversion node is associated with.
      Applicable to Frame Node only."
    ::= { unitConfigGroup 15 }

  internalMacAddress3   OBJECT-TYPE
    SYNTAX  PhysAddress
    ACCESS  read-only
    STATUS  mandatory
    DESCRIPTION
      "Optional third embedded conversion node
      MAC address. Applicable to Frame Node only."
    ::= { unitConfigGroup 16 }

  internalRingNumber3   OBJECT-TYPE
    SYNTAX  INTEGER (1..4095)
    ACCESS  read-only
    STATUS  mandatory
    DESCRIPTION
      "Optional third embedded conversion node ring
      number. This should be unique within the
      network. Applicable to Frame Node only."
    ::= { unitConfigGroup 17 }

  associatedPortNumber3   OBJECT-TYPE
    SYNTAX  INTEGER
    ACCESS  read-only
    STATUS  mandatory
    DESCRIPTION
      "Assigns the physical port number corresponding
      to the virtual port that the third embedded
      conversion node is associated with.
      Applicable to Frame Node only."
    ::= { unitConfigGroup 18 }

  associatedDLCI3         OBJECT-TYPE
    SYNTAX  INTEGER (0..1023)
    ACCESS  read-only
    STATUS  mandatory
    DESCRIPTION
      "Assigns the Frame Relay PVC number corresponding
      to the virtual port that the third embedded
      conversion node is associated with.
      Applicable to Frame Node only."
    ::= { unitConfigGroup 19 }

  internalMacAddress4   OBJECT-TYPE
    SYNTAX  PhysAddress
    ACCESS  read-only
    STATUS  mandatory
    DESCRIPTION
      "Optional forth embedded conversion node
      MAC address. Applicable to Frame Node only."
    ::= { unitConfigGroup 20 }

  internalRingNumber4   OBJECT-TYPE
    SYNTAX  INTEGER (1..4095)
    ACCESS  read-only
    STATUS  mandatory
    DESCRIPTION
      "Optional forth embedded conversion node
      ring number. This should be unique within
      the network. Applicable to Frame Node only."
    ::= { unitConfigGroup 21 }

  associatedPortNumber4   OBJECT-TYPE
    SYNTAX  INTEGER
    ACCESS  read-only
    STATUS  mandatory
    DESCRIPTION
      "Assigns the physical port number corresponding
      to the virtual port that the forth embedded
      conversion node is associated with.
      Applicable to Frame Node only."
    ::= { unitConfigGroup 22 }

  associatedDLCI4         OBJECT-TYPE
    SYNTAX  INTEGER (0..1023)
    ACCESS  read-only
    STATUS  mandatory
    DESCRIPTION
      "Assigns the Frame Relay PVC number corresponding
      to the virtual port that the forth embedded
      conversion node is associated with.
      Applicable to Frame Node only."
    ::= { unitConfigGroup 23 }

  ipInactivityTimer       OBJECT-TYPE
    SYNTAX  INTEGER (1..3600)
    ACCESS  read-only
    STATUS  mandatory
    DESCRIPTION
      "This timer is used for IP/SNMP over X25 support.
      It is the inactivity timer for an IP connection.
      If there is no activity for an IP session for the
      time this field specifies, IP will clear the
      session.
      The timer is expressed in seconds and is defaulted
      to 90."
    ::= { unitConfigGroup 24 }

  excessBurstGovernor   OBJECT-TYPE
    SYNTAX  INTEGER {
      yes(1),
      no(2)
      }
    ACCESS  read-only
    STATUS  mandatory
    DESCRIPTION
      "This parameter configuration determines whether
      the FrameNode should limit the throughput on a per
      PVC basis to the configured Excess Burst Size (in
      the excess burst measure time period Tc).  The range
      of this parameter is YES or NO. Default value
      is NO"
    ::= { unitConfigGroup 25 }

  measurementPeriod   OBJECT-TYPE
    SYNTAX  INTEGER (1..5)
    ACCESS  read-only
    STATUS  mandatory
    DESCRIPTION
      "This parameter specifies the time period for
      calculating Excess Burst for Frame Relay ports.
      The range of this parameter is 1 second to 5
      seconds.  Default is 1 second."
    ::= { unitConfigGroup 26 }

  markDEBit   OBJECT-TYPE
    SYNTAX  INTEGER {
      yes(1),
      no(2)
      }
    ACCESS  read-only
    STATUS  mandatory
    DESCRIPTION
      "This parameter specifies whether the FrameNode
      marks frames with the DE bit.  The range of this
      parameter is YES or NO.  Default is YES.  If the
      parameter is set to YES, the FrameNode marks the
      frames with the DE bit (for a non-urgent priority
      traffic) if a port's used bandwidth value is
      greater than the configured bandwidth."
    ::= { unitConfigGroup 27 }


  --
  -- The Unit Statistics Group
  --


  numberSamples  OBJECT-TYPE
    SYNTAX  Counter
    ACCESS  read-only
    STATUS  mandatory
    DESCRIPTION
      "The number of internal system level samples
       performed.  Samples are taken every 10th of a
       second."
    ::= { unitStatisticsGroup 1 }

  systemBufferFreeCounts  OBJECT-TYPE
    SYNTAX  INTEGER
    ACCESS  read-only
    STATUS  mandatory
    DESCRIPTION
      "The average number of system buffers free in
       the system during the system sample period.
       The number of available buffers varies by
       system type and configuration.  To determine
       the maximum number of buffers for a given
       configuration, view a sample when there is no
       activity in the unit.

       A heavily loaded unit will display a small number
       of available buffers and low Processor Idle counts."
    ::= { unitStatisticsGroup 2 }

  cpuIdleSumCounts OBJECT-TYPE
    SYNTAX  Counter
    ACCESS  read-only
    STATUS  mandatory
    DESCRIPTION
      "The main processor average idle sum count.
       This is the average number of times the idle counter
       was incremented over the sampling period divided
       by 1000.  This is an absolute value of performance
       as does not vary by performance.

       A heavily loaded unit will display a small number
       of available buffers and low Processor Idle counts."
    ::= { unitStatisticsGroup 3 }


  --
  -- NetView PU Status Group
  --
  -- This group contains status variables. There exists
  -- only one instance of this group per unit.
  --


  netviewConnectionStatus  OBJECT-TYPE
    SYNTAX  INTEGER  {
      connected(1),
      not-connected(2)
      }
    ACCESS  read-only
    STATUS  mandatory
    DESCRIPTION
      "The status of the Primary Netview Connection."
    ::= { netViewPUStatusGroup 1 }

  netviewLastClearCode    OBJECT-TYPE
    SYNTAX  OCTET STRING (SIZE(2))
    ACCESS  read-only
    STATUS  mandatory
    DESCRIPTION
      "A two octet field indicating the Last Clearing
      Cause and Diagnostic Field of the last failed primary
      NetView connection attempt (a.k.a. call attempt) or
      Netview active connection (a.k.a. session).

      For LLC type 2 connections the first octet (cause)
      is always 0.  The second octet (diagnostic)
      indicates the reason for the last connection failure.
      The second octet is set to 0 when a sucessful
      call has been placed, or if no call has ever been
      placed (e.g. PU never came up).
      If the second octet is non-zero then it indicates
      the reason for the connection attempt failure.
      See current product documentation for list of possible
      values."
    ::= { netViewPUStatusGroup 2 }

  netviewAltConnectionStatus  OBJECT-TYPE
    SYNTAX  INTEGER  {
      connected(1),
      not-connected(2)
      }
    ACCESS  read-only
    STATUS  mandatory
    DESCRIPTION
      "The status of the alternate Netview Connection"
    ::= { netViewPUStatusGroup 3 }

  netviewAltLastClearCode    OBJECT-TYPE
    SYNTAX  OCTET STRING (SIZE(2))
    ACCESS  read-only
    STATUS  mandatory
    DESCRIPTION
      "A two octet field indicating the Last Clearing
      Cause and Diagnostic Field of the last failed alternate
      NetView connection attempt (a.k.a. call attempt) or
      Netview active connection (a.k.a. session).

      For LLC type 2 connections the first octet (cause)
      is always 0.  The second octet (diagnostic)
      indicates the reason for the last connection failure.
      The second octet is set to 0 when a sucessful
      call has been placed, or if no call has ever been
      placed (e.g. PU never came up).
      If the second octet is non-zero then it indicates
      the reason for the connection attempt failure.
      See current product documentation for list of possible
      values."
    ::= { netViewPUStatusGroup 4 }

  netviewConnectionAttemptCount   OBJECT-TYPE
    SYNTAX  INTEGER
    ACCESS  read-only
    STATUS  mandatory
    DESCRIPTION
      "The number of connection attempts performed on the
      Primary NetView PU. This count is set to zero at
      startup, and after every loss of an estabished
      session."
    ::= { netViewPUStatusGroup 5 }

  netviewAltConnectionAttemptCount   OBJECT-TYPE
    SYNTAX  INTEGER
    ACCESS  read-only
    STATUS  mandatory
    DESCRIPTION
      "The number of connection attempts performed on the
      Alternate NetView PU. This count is set to zero at
      startup, and after every loss of an estabished
      session."
    ::= { netViewPUStatusGroup 6 }

  netviewStatusIgnored   OBJECT-TYPE
    SYNTAX  INTEGER {
      yes (1),
      no  (2)
      }
    ACCESS  read-write
    STATUS  mandatory
    DESCRIPTION
      "This field is used for consolidating status of the
      unit. The status of this netview pu is not put into
      consideration when consolidating status of the
      unit if this field is set to yes."
    ::= { netViewPUStatusGroup 7 }

  netviewStatusAcknowledged       OBJECT-TYPE
    SYNTAX  INTEGER {
      yes (1),
      no  (2)
      }
    ACCESS  read-write
    STATUS  mandatory
    DESCRIPTION
      "This field is used for consolidating status of the
      unit. When this field is set to yes, the unit will
      re-consolidate its status without putting the status
      of this netview PU into consideration. Subseqent
      status change of the this netview PU will cause the
      unit to include it in computing the status of the
      unit. Setting the value to no has no effect."
    ::= { netViewPUStatusGroup 8 }

  netviewAltStatusIgnored   OBJECT-TYPE
    SYNTAX  INTEGER {
      yes (1),
      no  (2)
      }
    ACCESS  read-write
    STATUS  mandatory
    DESCRIPTION
      "This field is used for consolidating status of the
      unit. The status of this netview pu is not put into
      consideration when consolidating status of the
      unit if this field is set to yes."
    ::= { netViewPUStatusGroup 9 }

  netviewAltStatusAcknowledged       OBJECT-TYPE
    SYNTAX  INTEGER {
      yes (1),
      no  (2)
      }
    ACCESS  read-write
    STATUS  mandatory
    DESCRIPTION
      "This field is used for consolidating status of the
      unit. When this field is set to yes, the unit will
      re-consolidate its status without putting the status
      of this netview pu into consideration. Subseqent
      status change of the this netview pu will cause the
      unit to include it in computing the status of the
      unit. Setting the value to no has no effect."
    ::= { netViewPUStatusGroup 10 }

  --
  -- The NetView PU Configuration Group

  -- Contains the current operational configuration
  --

  netviewPUXID  OBJECT-TYPE
    SYNTAX  OCTET STRING (SIZE(4))
    ACCESS  read-only
    STATUS  mandatory
    DESCRIPTION
      "Primary NetView PU XID.
       This field indicates the XID data to be
       sent to the host for establishing Netview Session.

       This field is a maximum four byte hexadecimal
       data field.

       This field should be set to all zeroes if no
       Netview session is to be established.

       The default value is all zeroes."
    ::= { netViewPUConfigGroup 1 }

  alternateNetviewPUXID   OBJECT-TYPE
    SYNTAX  OCTET STRING (SIZE(4))
    ACCESS  read-only
    STATUS  mandatory
    DESCRIPTION
      "Alternate NetView PU XID.
       This field indicates the XID data to be
       sent to the host for establishing Netview Session.

       This field is a maximum four byte hexadecimal
       data field.

       This field should be set to all zeroes if no
       Netview session is to be established.

       The default value is all zeroes."
    ::= { netViewPUConfigGroup 2 }

  netviewConnectID OBJECT-TYPE
    SYNTAX  OCTET STRING (SIZE(2))
    ACCESS  read-only
    STATUS  mandatory
    DESCRIPTION
      "The primary NetView PU connection ID.

       The default value is 0."
    ::= { netViewPUConfigGroup 3 }

  alternateNetviewConnectID OBJECT-TYPE
    SYNTAX  OCTET STRING (SIZE(2))
    ACCESS  read-only
    STATUS  mandatory
    DESCRIPTION
      "The alternate NetView PU connection ID.

       The default value is 0."
    ::= { netViewPUConfigGroup 4 }

  netviewSpecialConnect OBJECT-TYPE
    SYNTAX  INTEGER {
      answer (1),
      originate (2)
      }
    ACCESS  read-only
    STATUS  mandatory
    DESCRIPTION
      "The primary NetView PU connection type.

       The default value is originate."
    ::= { netViewPUConfigGroup 5 }

  alternateNetviewSpecialConnect OBJECT-TYPE
    SYNTAX  INTEGER {
      answer (1),
      originate (2)
      }
    ACCESS  read-only
    STATUS  mandatory
    DESCRIPTION
      "The alternate NetView PU connection type.

       The default value is originate."
    ::= { netViewPUConfigGroup 6 }

  --
  -- The Bridge Configuration Group

  -- Contains the current operational configuration
  --

  brEnableBridging        OBJECT-TYPE
    SYNTAX  INTEGER {
      yes(1),
      no(2)
      }
    ACCESS  read-only
    STATUS  mandatory
    DESCRIPTION
      "This flag indicates if bridging is to be performed
      on this unit.  Applicable to Frame Nodes only.

     The default value for this field is 'No'"
    ::= { bridgeConfigGroup 1 }

  bridgePriority   OBJECT-TYPE
    SYNTAX  INTEGER (0..65535)
    ACCESS  read-only
    STATUS  mandatory
    DESCRIPTION
      "Sometimes referred to as the ROOT id. Determines the
     priority component of the Bridge identifier used in
     determining the Root Bridge for a spanning tree network."
    ::= { bridgeConfigGroup 2 }

  brMaxAge   OBJECT-TYPE
    SYNTAX  INTEGER (6..40)
    ACCESS  read-only
    STATUS  mandatory
    DESCRIPTION
      "The time at which a configuration message is descarded.
     Units are in seconds. Default value is 10 seconds"
    ::= { bridgeConfigGroup 3 }

  brHelloTimer   OBJECT-TYPE
    SYNTAX  INTEGER (1..10)
    ACCESS  read-only
    STATUS  mandatory
    DESCRIPTION
      "The time interval between issuing configuration
     messages. Units are seconds. Default value is 2 seconds"
    ::= { bridgeConfigGroup 4 }

  brFilterIPX   OBJECT-TYPE
    SYNTAX  INTEGER {
      yes(1),
      no(2)
      }
    ACCESS  read-only
    STATUS  mandatory
    DESCRIPTION
      "If set to yes, all IPX frames are filtered (if
      bridge is enabled). Default is no."
    ::= { bridgeConfigGroup 5 }

  brFilterIP   OBJECT-TYPE
    SYNTAX  INTEGER {
      yes(1),
      no(2)
      }
    ACCESS  read-only
    STATUS  mandatory
    DESCRIPTION
      "If set to yes, all IP frames are filtered (if bridging
      is enabled). Default is no."
    ::= { bridgeConfigGroup 6 }

  brFilterNetBIOS  OBJECT-TYPE
    SYNTAX  INTEGER {
      yes(1),
      no(2)
      }
    ACCESS  read-only
    STATUS  mandatory
    DESCRIPTION
      "If set to yes, all NetBIOS frames are filtered
      (if bridging is enabled). Default is no."
    ::= { bridgeConfigGroup 7 }

  brFilterLLC2   OBJECT-TYPE
    SYNTAX  INTEGER {
      yes(1),
      no(2)
      }
    ACCESS  read-only
    STATUS  mandatory
    DESCRIPTION
      "If set to yes, all LAN attached SNA LLC2 frames are
      filtered (if bridging is enabled). Default is no."
    ::= { bridgeConfigGroup 8 }

  brFilterSMAN   OBJECT-TYPE
    SYNTAX  INTEGER {
      yes(1),
      no(2)
      }
    ACCESS  read-only
    STATUS  mandatory
    DESCRIPTION
      "If set to yes, all SyncManager LLC2 frames are
      filtered (if bridging is enabled). Default is no."
    ::= { bridgeConfigGroup 9 }

  brForwardOther   OBJECT-TYPE
    SYNTAX  INTEGER {
      yes(1),
      no(2)
      }
    ACCESS  read-only
    STATUS  mandatory
    DESCRIPTION
      "If set to yes, all other frames are forwarded (if
      bridging is enabled). Default is No."
    ::= { bridgeConfigGroup 10 }

  brIPXtargetPort  OBJECT-TYPE
    SYNTAX  INTEGER
    ACCESS  read-only
    STATUS  mandatory
    DESCRIPTION
      "If IPX filtering is set to no, then this parameter
      defines a specific FR port to deliver IPX frames to.
      Used in conjunction with brIPXtargetDLCI.

      The valid range is 0 to 5.  A value of 0 indicates that
      the IPX target port/DLCI is not configured.

      This field has the default value of 0."
    ::= { bridgeConfigGroup 11 }

  brIPXtargetDLCI  OBJECT-TYPE
    SYNTAX  INTEGER (0..1023)
    ACCESS  read-only
    STATUS  mandatory
    DESCRIPTION
      "If IPX filtering is set to no, then this parameter
      defines a specific FR DLCI to deliver IPX frames to.
      Used in conjunction with brIPXtargetPort.

      If the value of brIPXtargetport is 0, then the value of
      brIPXtargetDLCI is not significant."
    ::= { bridgeConfigGroup 12 }

  brIPtargetPort  OBJECT-TYPE
    SYNTAX  INTEGER
    ACCESS  read-only
    STATUS  mandatory
    DESCRIPTION
      "If IP filtering is set to no, then this parameter
      defines a specific FR port to deliver IP frames to.
      Used in conjunction with brIPtargetDLCI.

      The valid range is 0 to 5.  A value of 0 indicates that
      the IP target port/DLCI is not configured.

      This field has the default value of 0."
    ::= { bridgeConfigGroup 13 }

  brIPtargetDLCI  OBJECT-TYPE
    SYNTAX  INTEGER
    ACCESS  read-only
    STATUS  mandatory
    DESCRIPTION
      "If IP filtering is set to no, then this parameter
      defines a specific FR DLCI to deliver IP frames to.
      Used in conjunction with brIPtargetPort.

      If the value of brIPtargetport is 0, then the value of
      brIPtargetDLCI is not significant."
    ::= { bridgeConfigGroup 14 }


  brNetBIOStargetPort  OBJECT-TYPE
    SYNTAX  INTEGER
    ACCESS  read-only
    STATUS  mandatory
    DESCRIPTION

      "If NetBIOS filtering is set to no, then this parameter
      defines a specific FR port to deliver NetBIOS frames
      to. Used in conjunction with brNetBIOStargetDLCI.

      The valid range is 0 to 5.  A value of 0 indicates that
      the NetBIOS target port/DLCI is not configured.

      This field has the default value of 0."
    ::= { bridgeConfigGroup 15 }


  brNetBIOStargetDLCI  OBJECT-TYPE
    SYNTAX  INTEGER
    ACCESS  read-only
    STATUS  mandatory
    DESCRIPTION
      "If NetBIOS filtering is set to no, then this parameter
      defines a specific FR DLCI to deliver NetBIOS frames
      to. Used in conjunction with brNetBIOStargetPort.

      If the value of brNetBIOStargetport is 0, then the
      value of brNetBIOStargetDLCI is not significant."

    ::= { bridgeConfigGroup 16 }


  brLLC2targetPort  OBJECT-TYPE
    SYNTAX  INTEGER
    ACCESS  read-only
    STATUS  mandatory
    DESCRIPTION
      "If SNA LLC2 filtering is set to no, then this parameter
      defines a specific FR port to deliver LLC2 frames to.
      Used in conjunction with brLLC2targetDLCI.

      The valid range is 0 to 5.  A value of 0 indicates that
      the brLLC2targetport/brLLC2targetDLCI is not configured.

      This field has the default value of 0."
    ::= { bridgeConfigGroup 17 }


  brLLC2targetDLCI  OBJECT-TYPE
    SYNTAX  INTEGER
    ACCESS  read-only
    STATUS  mandatory
    DESCRIPTION
      "If SNA LLC2 filtering is set to no, then this parameter
      defines a specific FR DLCI to deliver LLC2 frames to.
      Used in conjunction with brLLC2targetPort.

      If the value of brLLC2targetport is 0, then the value
      of brLLC2targetDLCI is not significant."
    ::= { bridgeConfigGroup 18 }


  brOthertargetPort  OBJECT-TYPE
    SYNTAX  INTEGER
    ACCESS  read-only
    STATUS  mandatory
    DESCRIPTION
      "If Other forwarding is set to yes, then this parameter
      defines a specific FR port to deliver Other frames to.
      Used in conjunction with brOthertargetDLCI.

      The valid range is 0 to 5.  The value 0 indicates that
      the brOthertargetport/brOthertargetDLCI is not
      configured.

      This field has the default value of 0."
    ::= { bridgeConfigGroup 19 }


  brOthertargetDLCI  OBJECT-TYPE
    SYNTAX  INTEGER
    ACCESS  read-only
    STATUS  mandatory
    DESCRIPTION
      "If Other forwarding is set to yes, then this parameter
      defines a specific FR DLCI to deliver Other frames to.
      Used in conjunction with brOthertargetPort.

      If the value of brOthertargetport is 0, then the value
      of brOthertargetDLCI is not significant."
    ::= { bridgeConfigGroup 20 }

  brSerialPriority  OBJECT-TYPE
    SYNTAX  INTEGER {
      urgent (1),
      high (2),
      medium (3),
      low (4)
      }
    ACCESS  read-only
    STATUS  mandatory
    DESCRIPTION
      "This parameter defines the transmit priority for
      Frame Relay of serial attached port traffic."
    ::= { bridgeConfigGroup 21 }


  brTerminatedLLC2Priority  OBJECT-TYPE
    SYNTAX  INTEGER {
      urgent (1),
      high (2),
      medium (3),
      low (4)
      }
    ACCESS  read-only
    STATUS  mandatory
    DESCRIPTION
      "This parameter defines the transmit priority for
      Frame Relay of terminated LLC2 traffic."
    ::= { bridgeConfigGroup 22 }


  brLLC2Priority  OBJECT-TYPE
    SYNTAX  INTEGER {
      urgent (1),
      high (2),
      medium (3),
      low (4)
      }
    ACCESS  read-only
    STATUS  mandatory
    DESCRIPTION
      "This parameter defines the transmit priority for
      Frame Relay of SNA LLC2 traffic."
    ::= { bridgeConfigGroup 23 }


  brIPXPriority  OBJECT-TYPE
    SYNTAX  INTEGER {
      urgent (1),
      high (2),
      medium (3),
      low (4)
      }
    ACCESS  read-only
    STATUS  mandatory
    DESCRIPTION
      "This parameter defines the transmit priority for
      Frame Relay of IPX traffic."
    ::= { bridgeConfigGroup 24 }


  brIPPriority  OBJECT-TYPE
    SYNTAX  INTEGER {
      urgent (1),
      high (2),
      medium (3),
      low (4)
      }
    ACCESS  read-only
    STATUS  mandatory
    DESCRIPTION
      "This parameter defines the transmit priority for
      Frame Relay of IP traffic."
    ::= { bridgeConfigGroup 25 }


  brNetBIOSPriority  OBJECT-TYPE
    SYNTAX  INTEGER {
      urgent (1),
      high (2),
      medium (3),
      low (4)
      }
    ACCESS  read-only
    STATUS  mandatory
    DESCRIPTION
      "This parameter defines the transmit priority for
      Frame Relay of NetBIOS traffic."
    ::= { bridgeConfigGroup 26 }


  brOtherPriority  OBJECT-TYPE
    SYNTAX  INTEGER {
      urgent (1),
      high (2),
      medium (3),
      low (4)
      }
    ACCESS  read-only
    STATUS  mandatory
    DESCRIPTION
      "This parameter defines the transmit priority for
      Frame Relay of other traffic."
    ::= { bridgeConfigGroup 27 }

  brHighPriorityBandwidth  OBJECT-TYPE
    SYNTAX  INTEGER (0..100)
    ACCESS  read-only
    STATUS  mandatory
    DESCRIPTION
      "This parameter defines the high priority bandwidth.
      The sum of high, medium, and low priority bandwidth
      cannot exceed 100.

      Default value is 40."
    ::= { bridgeConfigGroup 28 }


  brMediumPriorityBandwidth  OBJECT-TYPE
    SYNTAX  INTEGER (0..100)
    ACCESS  read-only
    STATUS  mandatory
    DESCRIPTION
      "This parameter defines the medium priority bandwidth.
      The sum of high, medium, and low priority bandwidth
      cannot exceed 100.

      Default value is 30."
    ::= { bridgeConfigGroup 29 }

  brLowPriorityBandwidth  OBJECT-TYPE
    SYNTAX  INTEGER (0..100)
    ACCESS  read-only
    STATUS  mandatory
    DESCRIPTION
      "This parameter defines the low priority bandwidth.
      The sum of high, medium, and low priority bandwidth
      cannot exceed 100.

      Default value is 20."
    ::= { bridgeConfigGroup 30 }

  brDelayTimer      OBJECT-TYPE
    SYNTAX  INTEGER (1..4)
    ACCESS  read-only
    STATUS  mandatory
    DESCRIPTION
      "This field, expressed in seconds, specifies the maximum
       number of seconds a bridge frame can live in the unit.
       If a bridge frame stays in the unit longer than this
       value, the frame will be tossed.

       The default value for this field is 1"
    ::= { bridgeConfigGroup 31 }

brEnableIPXBridging        OBJECT-TYPE
    SYNTAX  INTEGER {
      yes(1),
      no(2)
      }
    ACCESS  read-only
    STATUS  mandatory
    DESCRIPTION
      "This flag indicates if IPX bridging is to be performed
      on this unit.  Applicable to Frame Nodes only.

     The default value for this field is 'Yes'"
    ::= { bridgeConfigGroup 32 }

  brEnableIPBridging        OBJECT-TYPE
    SYNTAX  INTEGER {
      yes(1),
      no(2)
      }
    ACCESS  read-only
    STATUS  mandatory
    DESCRIPTION
      "This flag indicates if IP bridging is to be performed
      on this unit.  Applicable to Frame Nodes only.

     The default value for this field is 'Yes'"
    ::= { bridgeConfigGroup 33 }

  brEnableNetBiosBridging        OBJECT-TYPE
    SYNTAX  INTEGER {
      yes(1),
      no(2)
      }
    ACCESS  read-only
    STATUS  mandatory
    DESCRIPTION
      "This flag indicates if NetBios bridging is to be performed
      on this unit.  Applicable to Frame Nodes only.

     The default value for this field is 'Yes'"
    ::= { bridgeConfigGroup 34 }

  brEnableSNABridging        OBJECT-TYPE
    SYNTAX  INTEGER {
      yes(1),
      no(2)
      }
    ACCESS  read-only
    STATUS  mandatory
    DESCRIPTION
      "This flag indicates if SNA bridging is to be performed
      on this unit.  Applicable to Frame Nodes only.

     The default value for this field is 'Yes'"
    ::= { bridgeConfigGroup 35 }

  brEnableSyncManBridging        OBJECT-TYPE
    SYNTAX  INTEGER {
      yes(1),
      no(2)
      }
    ACCESS  read-only
    STATUS  mandatory
    DESCRIPTION
      "This flag indicates if Sync/Man bridging is to be performed
      on this unit.  Applicable to Frame Nodes only.

     The default value for this field is 'Yes'"
    ::= { bridgeConfigGroup 36 }

  brEnableOtherBridging        OBJECT-TYPE
    SYNTAX  INTEGER {
      yes(1),
      no(2)
      }
    ACCESS  read-only
    STATUS  mandatory
    DESCRIPTION
      "This flag indicates if any other traffic bridging is to be performed
      on this unit.  Applicable to Frame Nodes only.

     The default value for this field is 'No'"
    ::= { bridgeConfigGroup 37 }




  --
  -- Bridge stats group
  --

  ipxStatsTable OBJECT-TYPE
    SYNTAX SEQUENCE OF IpxStatsEntry
    ACCESS  not-accessible
    STATUS  mandatory
    DESCRIPTION
      "A table for reporting statistics for bridging."
    ::= { bridgeStatsGroup 1 }

  ipxStatsEntry OBJECT-TYPE
    SYNTAX  IpxStatsEntry
    ACCESS  not-accessible
    STATUS  mandatory

    DESCRIPTION
      "An entry consisting of IPX bridging statistics for each
      bridge port."
    INDEX { ipxStatsIndex }
    ::= { ipxStatsTable 1 }

  IpxStatsEntry ::=
    SEQUENCE {
      ipxStatsIndex
        INTEGER,
      ipxRipRcvdFwdInterval
        Counter,
      ipxRipRcvdFiltInterval
        Counter,
      ipxSapRcvdFwdInterval
        Counter,
      ipxSapRcvdFiltInterval
        Counter
    }


  ipxStatsIndex  OBJECT-TYPE
    SYNTAX  INTEGER
    ACCESS  read-only
    STATUS  mandatory
    DESCRIPTION
      "The number that uniquely identifies this IPX bridge port."
    ::= { ipxStatsEntry 1 }

  ipxRipRcvdFwdInterval  OBJECT-TYPE
    SYNTAX  Counter
    ACCESS  read-only
    STATUS  mandatory
    DESCRIPTION
      "Identifies the number of IPX RIP packets received on this port
      during the RIP forwarding interval.  These packets were accepted
      by the port."
    ::= { ipxStatsEntry 2 }

  ipxRipRcvdFiltInterval  OBJECT-TYPE
    SYNTAX  Counter
    ACCESS  read-only
    STATUS  mandatory
    DESCRIPTION
      "Identifies the number of IPX RIP packets received on this port
      during the RIP filtering interval.  These packets were tossed
      by the port."
    ::= { ipxStatsEntry 3 }

  ipxSapRcvdFwdInterval  OBJECT-TYPE
    SYNTAX  Counter
    ACCESS  read-only
    STATUS  mandatory
    DESCRIPTION
      "Identifies the number of IPX SAP packets received on this port
      during the SAP forwarding interval.  These packets were accepted
      by the port."
    ::= { ipxStatsEntry 4 }

  ipxSapRcvdFiltInterval  OBJECT-TYPE
    SYNTAX  Counter
    ACCESS  read-only
    STATUS  mandatory
    DESCRIPTION
      "Identifies the number of IPX SAP packets received on this port
      during the SAP filtering interval.  These packets were tossed
      by the port."
    ::= { ipxStatsEntry 5 }


  --
  -- The IPX Configuration Group

  -- Contains the current operational configuration
  --

  ipxEnableRouting        OBJECT-TYPE
    SYNTAX  INTEGER {
      yes(1),
      no(2)
      }
    ACCESS  read-only
    STATUS  mandatory
    DESCRIPTION
      "This parameter determines whether or not IPX
      Routing is enabled.  Thr range of this parameter
      is yes or no.  If set to yes, the parameter
      'Filter IPX' should be set to yes.

     The default value for this field is 'No'"
    ::= { ipxConfigGroup 1 }

  ipxRoutedTxPriority   OBJECT-TYPE
    SYNTAX  INTEGER {
      urgent (1),
      high (2),
      medium (3),
      low (4)
      }
    ACCESS  read-only
    STATUS  mandatory
    DESCRIPTION
      "This parameter governs the transmission priority of
     the routed IPX frames for Frame Relay port(s).  The
     range is URGENT, HIGH, MEDIUM AND LOW.

     The default is set to 'High'."
    ::= { ipxConfigGroup 2 }

  ipxEnableRipBroadcast        OBJECT-TYPE
    SYNTAX  INTEGER {
      yes(1),
      no(2)
      }
    ACCESS  read-only
    STATUS  mandatory
    DESCRIPTION
      "This parameter governs whether the framenode
      should send RIP packets or not.  The range of
      this parameter is YES or NO. If IPX routing
      is disabled, this parameter is ignored.

     The default value for this field is 'Yes'"
    ::= { ipxConfigGroup 3 }

  ipxEnableSapBroadcast        OBJECT-TYPE
    SYNTAX  INTEGER {
      yes(1),
      no(2)
      }
    ACCESS  read-only
    STATUS  mandatory
    DESCRIPTION
      "This parameter governs whether the framenode
      should send SAP packets.  The range of
      this parameter is YES or NO. If IPX routing
      is disabled, this parameter is ignored.

     The default value for this field is 'Yes'"
    ::= { ipxConfigGroup 4 }

  ipxEnableNetBIOS  OBJECT-TYPE
    SYNTAX  INTEGER {
      yes(1),
      no(2)
      }
    ACCESS  read-only
    STATUS  mandatory
    DESCRIPTION
      "This parameter governs whether the frame Node
      should process NetBIOS packets or not. The
      range of this parameter is Yes or No. If IPX
      Routing is disabled, this parameter is ignored.

      Default is Yes."
    ::= { ipxConfigGroup 5 }

  ipxGlobalNodeId  OBJECT-TYPE
    SYNTAX  OCTET STRING (SIZE (1))
    ACCESS  read-only
    STATUS  mandatory
    DESCRIPTION
      " By default FrameNode always implements IPX WAN
       over Frame Relay. The 'timer request' packet
       is transmitted by the FrameNode over Frame Relay.
       This packet includes a field call WAN Node
       (referred to as WNode ID). This parameter defines
       the Wnode ID field. This field is 4 hexadecimal
       bytes (8 characters) long.

       This field is used in determining the MASTER and
       SLAV relationship between two end points.
       If IPX routing is enabled, this field needs to be
       configured for proper operation of IPX routing over
       Frame Relay. This value should be unique in the network.

      Default is undefined."
    ::= { ipxConfigGroup 6 }

  --
  -- The IP Configuration Group

  -- Contains the current operational configuration
  --

  priIPHelperAddress OBJECT-TYPE
    SYNTAX  IpAddress
    ACCESS  read-only
    STATUS  mandatory
    DESCRIPTION
      "This is the Primary IP Helper Address of this unit."
    ::= { ipConfigGroup 1 }

  secIPHelperAddress OBJECT-TYPE
    SYNTAX  IpAddress
    ACCESS  read-only
    STATUS  mandatory
    DESCRIPTION
      "This is the Secondary IP Helper Address of this unit."
    ::= { ipConfigGroup 2 }

  internalIPAddr OBJECT-TYPE
    SYNTAX  IpAddress
    ACCESS  read-only
    STATUS  mandatory
    DESCRIPTION
      "The range of this parameter and the default
      value is same as other IP Address in the unit."
    ::= { ipConfigGroup 3 }

  internalIPNetmask OBJECT-TYPE
    SYNTAX  IpAddress
    ACCESS  read-only
    STATUS  mandatory
    DESCRIPTION
      "This is the Internal IP network mask."
    ::= { ipConfigGroup 4 }

  enableIpRouting OBJECT-TYPE
    SYNTAX  INTEGER {
      yes(1),
      no(2)
      }
    ACCESS  read-only
    STATUS  mandatory
    DESCRIPTION
      "This is the Internal IP network mask."
    ::= { ipConfigGroup 5 }

  enableIpBridging OBJECT-TYPE
    SYNTAX  INTEGER {
      yes(1),
      no(2)
      }
    ACCESS  read-only
    STATUS  mandatory
    DESCRIPTION
      "This is the Internal IP network mask."
    ::= { ipConfigGroup 6 }

  enableRipBroadcast OBJECT-TYPE
    SYNTAX  INTEGER {
      yes(1),
      no(2)
      }
    ACCESS  read-only
    STATUS  mandatory
    DESCRIPTION
      "This is the Internal IP network mask."
    ::= { ipConfigGroup 7 }

  --
  -- The LAN control
  --

  lanControlTable OBJECT-TYPE
    SYNTAX SEQUENCE OF LanControlEntry
    ACCESS  not-accessible
    STATUS  mandatory
    DESCRIPTION
      "A table for controlling LAN ports and obtaining
      information."
    ::= { lanControlGroup 1 }

  lanControlEntry OBJECT-TYPE
    SYNTAX  LanControlEntry
    ACCESS  not-accessible
    STATUS  mandatory

    DESCRIPTION
      "An entry consisting of port information for a
      particular LAN port."
    INDEX { lanControlIndex }
    ::= { lanControlTable 1 }

  LanControlEntry ::=
    SEQUENCE {
      lanControlIndex
        INTEGER,
      lanControlType
        INTEGER,
      lanStatus
        INTEGER,
      lanControlFailureCode
        OCTET STRING,
      lanControlNAUName
        DisplayString,
      lanStatusIgnored
          INTEGER,
      lanStatusAcknowledged
          INTEGER
    }


  lanControlIndex  OBJECT-TYPE
    SYNTAX  INTEGER
    ACCESS  read-only
    STATUS  mandatory
    DESCRIPTION
      "The number that uniquely identifies
      this LAN port.
      Currently only one LAN port per unit is supported."
    ::= { lanControlEntry 1 }


  lanControlType  OBJECT-TYPE
    SYNTAX  INTEGER {
      token-ring-type(21),
      ethernet-type(17)
      }
    ACCESS  read-only
    STATUS  mandatory
    DESCRIPTION
      "The LAN type.

      Token-Ring ports run the IEEE 802.5 protocol.
      Ethernet-type run the IEEE 802.3 and Ethernet
      Version 2.

      Other LAN protocols may be added in
      the future."
    ::= { lanControlEntry 2 }

  lanStatus    OBJECT-TYPE
    SYNTAX  INTEGER {
      enable(1),
      disable(2),
      failed(3),
      restart(4)
      }
    ACCESS  read-write
    STATUS  mandatory
    DESCRIPTION
      "The status of the port.
      To change status of a port an enable, enable all
      or disable may be set.

      Valid Return status are enable(d), disable(d),
      or failed.

      Commands:
      An enable command will attempt to bring up the LAN.

      An enable all command will perform the same function
      as enable, since there are no sub elements on a LAN.

      A disable command will disable the LAN.

      Status:
      Enable(d) indicates the LAN is enabled and running.
      Disable(d) indicates the LAN has been disabled.
      Failed indicates the LAN is enabled and not
      Running."
    ::= { lanControlEntry 3 }

  lanControlFailureCode   OBJECT-TYPE
    SYNTAX  OCTET STRING (SIZE (2))
    ACCESS  read-only
    STATUS  mandatory
    DESCRIPTION
      "This entry contains the failure codes if the
      associated LAN interface is in the failed state."
    ::= { lanControlEntry 4 }


  lanControlNAUName   OBJECT-TYPE
    SYNTAX  DisplayString (SIZE(1..8))
    ACCESS  read-only
    STATUS  mandatory
    DESCRIPTION
      "The NAU name of this port.
      The default value for this field is all blank
      (filled with ASCII space 0x20 characters)."
    ::= { lanControlEntry 5 }

  lanStatusIgnored   OBJECT-TYPE
    SYNTAX  INTEGER {
      yes (1),
      no  (2)
      }
    ACCESS  read-write
    STATUS  mandatory
    DESCRIPTION
      "This field is used for consolidating status of the
      unit. The status of this LAN is not put into
      consideration when consolidating status of the
      unit if this field is set to yes."
    ::= { lanControlEntry 6 }

  lanStatusAcknowledged   OBJECT-TYPE
    SYNTAX  INTEGER {
      yes (1),
      no  (2)
      }
    ACCESS  read-write
    STATUS  mandatory
    DESCRIPTION
      "This field is used for consolidating status of the
      unit. When this field is set to yes, the unit will
      re-consolidate its status without putting the status
      of this LAN into consideration. Subseqent status
      change of the LAN will cause the unit to include it
      in computing the status of the unit. Setting this
      value to no has no effect."
    ::= { lanControlEntry 7 }

  --
  -- The LAN Configuration Group
  --

  lanPortTable  OBJECT-TYPE
    SYNTAX  SEQUENCE OF LanPortEntry
    ACCESS  not-accessible
    STATUS  mandatory
    DESCRIPTION
      "A table of LAN information."
    ::= { lanTokenRingGroup 1 }

  lanPortEntry  OBJECT-TYPE
    SYNTAX  LanPortEntry
    ACCESS  not-accessible
    STATUS  mandatory
    DESCRIPTION
      "An entry consisting of port information for a
      particular LAN port."
    INDEX { lanPortIndex }
    ::= { lanPortTable 1 }

  LanPortEntry ::=
    SEQUENCE {
      lanPortIndex
        INTEGER,
      lanPortType
        INTEGER,
      lanMACAddress
        PhysAddress,
      lanPROMMACAddress
        PhysAddress,
      lanSpeed
        INTEGER,
      lanT1Timer
        INTEGER,
      lanT2Timer
        INTEGER,
      lanTiTimer
        INTEGER,
      lanRxWindowSize
        INTEGER,
      lanTxWindowSize
        INTEGER,
      lanMaxRetries
        INTEGER,
      lanRingNumber
        INTEGER,
      lanBridgeNumber
        INTEGER,
      lanEthernetFrameFormat
        INTEGER,
      lanSendLocalTest
        INTEGER,
      lanBroadcastType
        INTEGER,
      lanIPAddress
        IpAddress,
      lanNetworkMask
        IpAddress,
      lanDefaultGateway
        IpAddress,
      lanNAUName
        DisplayString,
      lanInterfaceType
        INTEGER,
      lanIPEthernetFrameType
        INTEGER,
      lanInitState
        INTEGER,
      lanSecondDefaultGateway
        IpAddress,
      lanRIPUpdtTimer
        INTEGER,
      lanRIPAge
        INTEGER,
      lanSAPUpdtTimer
        INTEGER,
      lanSAPAge
        INTEGER,
      lanRSM
        INTEGER
    }


  lanPortIndex  OBJECT-TYPE
    SYNTAX  INTEGER
    ACCESS  read-only
    STATUS  mandatory
    DESCRIPTION
      "The port number that uniquely identifies
      this port.
      Currently only one LANtoken ring port per unit is
      supported."
    ::= { lanPortEntry 1 }


  lanPortType  OBJECT-TYPE
    SYNTAX  INTEGER {
      token-ring-type(21),
      ethernet-type(17)
      }
    ACCESS  read-only
    STATUS  mandatory
    DESCRIPTION
      "The LAN port type."
    ::= { lanPortEntry 2 }

  lanMACAddress  OBJECT-TYPE
    SYNTAX  PhysAddress
    ACCESS  read-only
    STATUS  mandatory
    DESCRIPTION
      "The user configured LANtoken ring MAC address.
      If the address is set to 0 then the burned-in Address
      is used.  This field contains a user configured
      address if any.  If a user configured address
      is desired, then it must be configured as
      a valid individual, user defined - MAC address.
      The address must be configured in the native
      format convention used by the LAN port.

      For token Ring LAN ports the address follows
      User configured addresses must follow IEEE 802.5
      IEEE 802.5 rules (most significant bit transmitted first)
      and must be between 400000000000 and 7FFFFFFFFFFF
      hexadecimal inclusive.

      For Ethernet LAN ports the format is must
      follow IEEE 802.3 rules.where the two least
      significant bits of the first octet must be
      zero.  This means the first octet must be
      in the set of numbers 0x00, 0x04, 0x08, ...
      0xFC.....

      The Default Value for this field is all zeroes."
    ::= { lanPortEntry 3 }

  lanPROMMACAddress OBJECT-TYPE
    SYNTAX  PhysAddress
    ACCESS  read-only
    STATUS  mandatory
    DESCRIPTION
      "The burned in MAC address.

      This is the MAC address assigned by the factory
      when the unit is shipped.  If the User configured
      address is set to 0, then this will be the address
      used by the adapter for the source address field
      for all frames sent by the LAN adapter.

      The format ordering of bits is as defined in
      IEEE 802.5.  This ordering is where the Most
      Significant Bit is transmitted first.  This is
      different from other protocols (e.g. 802.3) where
      the least significant bit is transmitted first.
      The representation of the MAC address is
      in the format native for the LAN port.

      Boundary platform Token-Ring LAN ports start with the
      first six digits (three octects) equal  to
      0002F6 which indicates a Sync Research Token Ring
      MAC address.

      Boundary platform Ethernet LAN ports start with
      the first six digits (three octects) equal to
       to 00406F which indicates a Sync Research
      Ethernet MAC address.

      This field is not changable via any commands
      and will always contain the manufactured
      MAC address for the LAN port."
    ::= { lanPortEntry 4 }

  lanSpeed    OBJECT-TYPE
    SYNTAX  INTEGER {
      speed-4Mbs(4),
      speed-10Mbs(10),
      speed-16Mbs(16)
      }
    ACCESS  read-only
    STATUS  mandatory
    DESCRIPTION
      "The LAN port speed in Megabits/second."
    ::= { lanPortEntry 5 }

  lanT1Timer  OBJECT-TYPE
    SYNTAX  INTEGER (1..25)
    ACCESS  read-only
    STATUS  mandatory
    DESCRIPTION
      "The default LLC T1 timer value in seconds.
      T1 should be greater than T2 and less than Ti.
      Currently supported values are 1 to 25 seconds.
      The default value for this field is 3 seconds."
    ::= { lanPortEntry 6 }

  lanT2Timer  OBJECT-TYPE
    SYNTAX  INTEGER (0..50)
    ACCESS  read-only
    STATUS  mandatory
    DESCRIPTION
      "The default LLC T2 timer value in tenths of seconds.
      If configured for 0 then the T2 timer is disabled
      and an RR frame will be sent for every I frame
      received.
      Current supported values are 0 and 2-50.
      T2 should be less than T1.
      The default value for this field is 0 (disabled)."
    ::= { lanPortEntry 7 }

  lanTiTimer  OBJECT-TYPE
    SYNTAX  INTEGER (2..50)
    ACCESS  read-only
    STATUS  mandatory
    DESCRIPTION
      "The default LLC Ti (inactivity) timer value
      in seconds.
      Ti should be greater than T1.
      Currently supported values are 2 to 50 seconds.
      The default value for this field is 30 seconds."
    ::= { lanPortEntry 8 }

  lanRxWindowSize OBJECT-TYPE
    SYNTAX  INTEGER (1..15)
    ACCESS  read-only
    STATUS  mandatory
    DESCRIPTION
      "The default LLC receive window (N3) size.
      Note that this is not the same receive window as
      defined in IEEE 802.2 LLC.  This is N3 which is the
      number of I frames received before an RR frame is
      sent (defined as N3 in IEEE 802.2 LLC).
      Current allowable values are 1-15.
      The default value for this field is 7."
    ::= { lanPortEntry 9 }

  lanTxWindowSize OBJECT-TYPE
    SYNTAX  INTEGER (1..15)
    ACCESS  read-only
    STATUS  mandatory
    DESCRIPTION
      "The defalut LLC transmit window size.
      Current allowable values are 1-15.
      The default value for this field is 7."
    ::= { lanPortEntry 10 }

  lanMaxRetries  OBJECT-TYPE
    SYNTAX  INTEGER (1..99)
    ACCESS  read-only
    STATUS  mandatory
    DESCRIPTION
      "The default LLC maximum number of retries (N2 value).
      Current allowable values are 1-99.
      The default value for this field is 3."
    ::= { lanPortEntry 11 }

  lanRingNumber  OBJECT-TYPE
    SYNTAX  INTEGER (0..4095)
    ACCESS  read-only
    STATUS  mandatory
    DESCRIPTION
      "802.5 bridging parameter.
      This variable returns a value of 0, if it is not
      defined. This value is configured in  hex from 0
      to FFF.
      This value is not applicable to Ethernet."
    ::= { lanPortEntry 12 }

  lanBridgeNumber  OBJECT-TYPE
    SYNTAX  INTEGER (1..15)
    ACCESS  read-only
    STATUS  mandatory
    DESCRIPTION
      "802.5 bridging parameter.
      The default value for this field is 1.
      This value is not applicable to Ethernet."
    ::= { lanPortEntry 13 }

  lanEthernetFrameFormat
    OBJECT-TYPE
    SYNTAX  INTEGER {
      not-applicable(1),
      e802-3-type(2),
      ethernet-type-2(3)
      }
    ACCESS  read-only
    STATUS  mandatory
    DESCRIPTION
      "The Ethernet frame format used on this LAN.
      The default value for this field is 802.3.
      Not used if Token Ring, and 1 is returned."
    ::= { lanPortEntry 14 }

  lanSendLocalTest  OBJECT-TYPE
    SYNTAX  INTEGER {
      not-applicable(1),
      yes(2),
      no(3)
      }
    ACCESS  read-only
    STATUS  mandatory
    DESCRIPTION
      "This port's send local test option.

      Identifies whether a test frame should be sent on the
      local ring to discover a destination MAC address.

      If all destinations for the unit are located on a
      remote ring, setting this field to No allows the unit
      to bypass discovery of a destination MAC address on
      the local ring.  If this field is set to 'No' then
      the broadcastType field must be set to all routes or
      single route broadcast.

      If the any destination is on a local ring or unknown,
      this parameter should be set to 'Yes'.

      The default value for this field is 'Yes'.

      Not used if Ethernet, and 0 is returned."
    ::= { lanPortEntry 15 }

  lanBroadcastType  OBJECT-TYPE
    SYNTAX  INTEGER {
      not-applicable(1),
      none-bc(2),
      all-bc(3),
      single-bc(4)
      }
    ACCESS  read-only
    STATUS  mandatory
    DESCRIPTION
      "This port's broadcast type. Not used if Ethernet.

      Types are:  none, all-routes, and single-route.
      Identifies the form of a broadcast test frame
      sent to discover the route to a destination MAC
      address.

      If all destinations are located on the local ring,
      this field may be set to 'None' to prevent a
      broadcast search for a destination MAC address.  If
      set to 'None', then the sendLocalTest field must be
      set to 'Yes'.

      If set as 'All-routes', the unit will send an
      All-routes broadcast TEST command frame and expect a
      non-broadcast TEST response frame in return.

      If set to Single-route, the unit will send a
      Single-route broadcast TEST command frame and expect a
      all-routes TEST response frame in return.

      The default for this field is all routes broadcast.

      Not used if Ethernet, and 0 is returned."
    ::= { lanPortEntry 16 }

  lanIPAddress OBJECT-TYPE
    SYNTAX  IpAddress
    ACCESS  read-only
    STATUS  mandatory
    DESCRIPTION
      "This is the IP Address of this interface."
    ::= { lanPortEntry 17 }

  lanNetworkMask OBJECT-TYPE
    SYNTAX  IpAddress
    ACCESS  read-only
    STATUS  mandatory
    DESCRIPTION
      "This is the network mask to be used on this
      interface."
    ::= { lanPortEntry 18 }

  lanDefaultGateway OBJECT-TYPE
    SYNTAX  IpAddress
    ACCESS  read-only
    STATUS  mandatory
    DESCRIPTION
      "Default gateway address to be used when sending
      responses on this interface."
    ::= { lanPortEntry 19 }

  lanNAUName   OBJECT-TYPE
    SYNTAX  DisplayString (SIZE(1..8))
    ACCESS  read-only
    STATUS  mandatory
    DESCRIPTION
      "The NAU name of this port.
      The default value for this field is all blank
      (filled with ASCII space 0x20 characters)."
    ::= { lanPortEntry 20 }

  lanInterfaceType  OBJECT-TYPE
    SYNTAX  INTEGER {
      not-applicable(1),
      aui(2),
      bnc(3),
      utp(4),
      stp(5)
      }
    ACCESS  read-only
    STATUS  mandatory
    DESCRIPTION
      "This port's physical interface type. Only used if
      Ethernet.  The default for this field is utp.
      Not used if Token Ring, and 1 is returned."
    ::= { lanPortEntry 21 }

  lanIPEthernetFrameType     OBJECT-TYPE
    SYNTAX  INTEGER {
      not-applicable(1),
      e802-3-type(2),
      ethernet-type-2(3)
      }
    ACCESS  read-only
    STATUS  mandatory
    DESCRIPTION
      "The IP Ethernet frame format used on this LAN for IP
      frames. The default value for this field is 802.3.
      Not used if Token Ring, and 1 is returned."
    ::= { lanPortEntry 22 }

  lanInitState  OBJECT-TYPE
    SYNTAX  INTEGER {
      in-service(1),
      out-of-service(2)
      }
    ACCESS  read-only
    STATUS  mandatory
    DESCRIPTION
      "The initial state of the LAN port.

      If configured for 'in-service', then the LAN port will
      be brougt up automattically when the unit is powered
      up.

      If configured for 'out-of-service', the the LAN port
      must be manually enabled by operator intervention (i.e.
      enable command must be sent).

      The default value is 'enabled'."
    ::= { lanPortEntry 23 }

  lanSecondDefaultGateway OBJECT-TYPE
    SYNTAX  IpAddress
    ACCESS  read-only
    STATUS  mandatory
    DESCRIPTION
      "Second Default gateway address to be used when sending
      responses on this interface."
    ::= { lanPortEntry 24 }

  lanRIPUpdtTimer   OBJECT-TYPE
    SYNTAX  INTEGER (10..180)
    ACCESS  read-only
    STATUS  mandatory
    DESCRIPTION
      "Defines frequency at which the RIP packets are sent
     over this interface.  The range of this parameter is
     from 10 seconds to 180 seconds. A value of 0 implies
     no RIP is sent over this interface.

     Default value is 60 seconds"
    ::= { lanPortEntry 25 }

  lanRIPAge   OBJECT-TYPE
    SYNTAX  INTEGER (40..540)
    ACCESS  read-only
    STATUS  mandatory
    DESCRIPTION
      "Defines frequency at which the learned RIP entries are
     removed if not corresponding RIP update is received.  The
     range of this parameter is from 40 seconds to 540 seconds.

     Default value is 180 seconds"
    ::= { lanPortEntry 26 }

  lanSAPUpdtTimer   OBJECT-TYPE
    SYNTAX  INTEGER (0..180)
    ACCESS  read-only
    STATUS  mandatory
    DESCRIPTION
      "Defines frequency at which the SAP packets are sent
     over this interface.  The range of this parameter is
     from 10 seconds to 180 seconds.  A value of 0 implies
     that no SAP broadcasts are sent over this interface.

     Default value is 60 seconds"
    ::= { lanPortEntry 27 }

  lanSAPAge   OBJECT-TYPE
    SYNTAX  INTEGER (40..720)
    ACCESS  read-only
    STATUS  mandatory
    DESCRIPTION
      "Defines frequency at which the learned SAP entries are
     removed if not corresponding SAP update is received.  The
     range of this parameter is from 40 seconds to 720 seconds.

     Default value is 180 seconds"
    ::= { lanPortEntry 28 }

  lanRSM   OBJECT-TYPE
    SYNTAX  INTEGER {
      yes (1),
      no  (2)
      }
    ACCESS  read-only
    STATUS  mandatory
    DESCRIPTION
      "The Routing Summary Information parameter indicates whether
       the routing summary information should be generated in the
       RIP on that interface. If RSM is set to NO, RIP will
       broadcast subnet information as it is defined in the
       routing table.

     Default value is 'NO'"
    ::= { lanPortEntry 29 }

  --
  -- The Line Control Group
  --

  lineControlTable OBJECT-TYPE
    SYNTAX SEQUENCE OF LineControlEntry
    ACCESS  not-accessible
    STATUS  mandatory
    DESCRIPTION
      "A table for controlling lines and obtaining
       information."
    ::= { lineControlGroup 1 }

  lineControlEntry OBJECT-TYPE
    SYNTAX  LineControlEntry
    ACCESS  not-accessible
    STATUS  mandatory
    DESCRIPTION
      "An entry consisting of port information for a
       particular port."
    INDEX { lineControlIndex }
    ::= { lineControlTable 1 }

  LineControlEntry ::=
    SEQUENCE {
      lineControlIndex
        INTEGER,
      lineControlType
        INTEGER,
      lineStatus
        INTEGER,
      lineControlFailureCode
        OCTET STRING,
      lineControlNAUName
        DisplayString,
      lineStatusIgnored
        INTEGER,
      lineStatusAcknowledged
        INTEGER,
      loopbackTest
        INTEGER
    }


  lineControlIndex  OBJECT-TYPE
    SYNTAX  INTEGER
    ACCESS  read-only
    STATUS  mandatory
    DESCRIPTION
      "The port number that uniquely identifies
      this port."
    ::= { lineControlEntry 1 }

  lineControlType  OBJECT-TYPE
    SYNTAX  INTEGER {
      hbsc-type(1),
      tbsc-type(2),
      x25dte-type(7),
      x25dce-type(8),
      hasc-type(9),
      tasc-type(10),
      hsdlc-type(11),
      tsdlc-type(12),
      frameRelay-type(19),
      dial-backup-type(20),
      secondaryRJE-type(13),
      primaryRJE-type(14)
     }
    ACCESS  read-only
    STATUS  mandatory
    DESCRIPTION
      "The port type.

      TSDLC (Terminal SDLC) ports emulate a Host
      and poll the downstream PUs (e.g. 3274 or 3174
      SDLC/SNA controllers).

      HSDLC ports (Host SDLC) ports emulate a line with
      Terminal Controllers (PUs) and respond to polls
      from the Host or upstream PU.

      TBSC (Terminal Bisync) ports emulate a Host
      and poll the downstream CUs (e.g. 3274 or ATM
      Bisync controllers).

      HBSC ports (Host Bisync) ports emulate a line with
      Terminal Controllers (CUs) and respond to polls
      from the Host or upstream CU.

      Frame Relay ports support Frame Relay PVC.

      X25 type is for either X.25 packet level DCE or DTE."

    ::= { lineControlEntry 2 }

  lineStatus  OBJECT-TYPE
    SYNTAX  INTEGER {
      enable(1),
      disable(2),
      failed(3),
      restart(4),
      enable-all(5),
      not-in-use(6)
      }
    ACCESS  read-write
    STATUS  mandatory
    DESCRIPTION
      "The status of the port.
      To change status of a port an enable, enable all
      or disable may be set.


      Valid Return status are enable(d), disable(d),
      or failed.

      When calculating consolidated status for the unit,
      if the line status set to not-in-use then this port
      is not included.

      Commands:
      An enable command will attempt to bring up the line.
      An enable all command will attempt to bring up
      the line and any lower layer entities (e.g. PUs).
      A disable command will disable the line.

      Status:
      Enable(d) indicates the line is enabled and running.
      Disable(d) indicates the line has been disabled.
      Failed indicates the line is enabled and not
      Running."
    ::= { lineControlEntry 3 }

  lineControlFailureCode   OBJECT-TYPE
    SYNTAX  OCTET STRING (SIZE (2))
    ACCESS  read-only
    STATUS  mandatory
    DESCRIPTION
      "This entry contains the failure codes if the
      associated port interface is in the failed state."
    ::= { lineControlEntry 4 }

  lineControlNAUName   OBJECT-TYPE
    SYNTAX  DisplayString (SIZE(1..8))
    ACCESS  read-only
    STATUS  mandatory
    DESCRIPTION
      "The NAU name of this port.
      The default value for this field is all blank
      (filled with ASCII space 0x20 characters)."
    ::= { lineControlEntry 5 }

  lineStatusIgnored   OBJECT-TYPE
    SYNTAX  INTEGER {
      yes (1),
      no  (2)
      }
    ACCESS  read-write
    STATUS  mandatory
    DESCRIPTION
      "This field is used for consolidating status of the
      unit. The status of this line is not put into
      consideration when consolidating status of the
      unit if this field is set to yes."
    ::= { lineControlEntry 6 }

  lineStatusAcknowledged   OBJECT-TYPE
    SYNTAX  INTEGER {
      yes (1),
      no  (2)
      }
    ACCESS  read-write
    STATUS  mandatory
    DESCRIPTION
      "This field is used for consolidating status of the
      unit. When this field is set to yes, the unit will
      re-consolidate its status without putting the status
      of this line into consideration. Subseqent status
      change of the line will cause the unit to include it
      in computing the status of the unit. Setting this
      value to no has no effect."
    ::= { lineControlEntry 7 }

  loopbackTest   OBJECT-TYPE
    SYNTAX  INTEGER {
      local (1),
      network-or-full (2),
      remote (3),
      stop-test(4),
      passive (5)
      }
    ACCESS  read-write
    STATUS  mandatory
    DESCRIPTION
      "Loopback Test can be supported on both DSU/CSU and
      ISDN.  Loopback can be local, Network, or Remote.
      Local loopback means outgoing serial data is looped
      back toward DTE device.  Network loopback triggers
      the local node to loopback any incoming serial data
      back to the network.  Remote loopback triggers the far
      end node to loopback any serial data received from the
      network.
      A local loopback test is stopped by entering a Ctrl-C."
    ::= { lineControlEntry 8 }

  --
  -- The Line Physical Control Group
  --
  -- This is a separate group as not all 'lines' have an RS-232
  -- or other WAN physical interface (e.g. V.35, RS-449 etc.)
  -- This group is for reporting EIA status for the STM command.
  --

  linePhysicalTable OBJECT-TYPE
    SYNTAX  SEQUENCE OF LinePhysicalEntry
    ACCESS  not-accessible
    STATUS  mandatory
    DESCRIPTION
      "A table for obtaining physical signal status
      information."
    ::= { linePhysicalGroup 1 }

  linePhysicalEntry OBJECT-TYPE
    SYNTAX  LinePhysicalEntry
    ACCESS  not-accessible
    STATUS  mandatory
    DESCRIPTION
      "An entry consisting of port information for a
      particular port."
    INDEX { linePhysicalIndex }
    ::= { linePhysicalTable 1 }

  LinePhysicalEntry ::=
    SEQUENCE {
      linePhysicalIndex
        INTEGER,
      linePhysicalType
        INTEGER,
      lineEIAStatus
        INTEGER,
      lineQualityFrameCount
        Counter,
      lineQualityCRCErrors
        Counter,
      lineQualityAborts
        Counter,
      lineInterfaceType
        INTEGER,
      lineCableType
        INTEGER,
      lineSwitchedConnection
        INTEGER
    }


  linePhysicalIndex  OBJECT-TYPE
    SYNTAX  INTEGER
    ACCESS  read-only
    STATUS  mandatory
    DESCRIPTION
      "The port number that uniquely identifies
      this port."
    ::= { linePhysicalEntry 1 }


  linePhysicalType OBJECT-TYPE
    SYNTAX  INTEGER {
      hbsc-type(1),
      tbsc-type(2),
      x25dte-type(7),
      x25dce-type(8),
      tasc-type(9),
      hasc-type(10),
      frameRelay-type(19),
      hsdlc-type(11),
      tsdlc-type(12),
      dial-backup-type(20),
      secondaryRJE-type(13),
      primaryRJE-type(14)
 }
    ACCESS  read-only
    STATUS  mandatory
    DESCRIPTION
      "The port type.

      TSDLC (Terminal SDLC) ports emulate a Host
      and poll the downstream PUs (e.g. 3274 or 3174
      SDLC/SNA controllers).

      HSDLC ports (Host SDLC) ports emulate a line with
      Terminal Controllers (PUs) and respond to polls
      from the Host or upstream PU.

      TBSC (Terminal Bisync) ports emulate a Host
      and poll the downstream CUs (e.g. 3274 or ATM
      Bisync controllers).

      HBSC ports (Host Bisync) ports emulate a line with
      Terminal Controllers (CUs) and respond to polls
      from the Host or upstream CU.

      Frame Relay ports support Frame Relay PVC."

    ::= { linePhysicalEntry 2 }

  lineEIAStatus  OBJECT-TYPE
    SYNTAX  INTEGER (0..65535)
    ACCESS  read-only
    STATUS  mandatory
    DESCRIPTION
      "A port's current control signal status.

      All SDLC ports have the ability to read
      the current status of RS-232 or equivalent
      control signals.

      The value returned is a 16 bit value where each
      bit signifies a signal status where 1 means the
      signal is active and 0 means the signal is inactive.

      The value returned is a snapshot taken when the
      command actually is sent to the driver software and
      wherever possible actually goes out to the driver
      or receiver control chips to get the value.

      Currently defined bit values are as follows*:
       128 : Data Terminal Ready  0x0080 RS-232 pin 20
        64 : Data Set Ready       0x0040 RS-232 pin 6
        32 : Clear to Send        0x0020 RS-232 pin 5
        16 : Clear to Send Ext.   0x0010 RS-232 pin 11**
         8 : Data Carrier Detect  0x0008 RS-232 pin 8
         4 : Busy Out             0x0004 RS-232 pin 25
         2 : Request to send      0x0002 RS-232 pin 4
         1 : Ring Indicator       0x0001 RS-232 pin 22

      Note*: Bit values higher than 128 are reserved for
      future use.

      Note**: Clear to Send External is extended (non-
       standard) pin and reserved for future use
       by Sync Research."
    ::= { linePhysicalEntry 3 }

  lineQualityFrameCount  OBJECT-TYPE
    SYNTAX  Counter
    ACCESS  read-only
    STATUS  mandatory
    DESCRIPTION
      "This entry contains the number of frames received.
      For every 255 incoming frames, a trap is generated by
      the unit if lineQualityCRCErrors or lineQualityAborts
      exceeds 5.  When this value reaches 255, it
      then rolls back to 0.  Applicable to SDLC only."
    ::= { linePhysicalEntry 4}

  lineQualityCRCErrors  OBJECT-TYPE
    SYNTAX  Counter
    ACCESS  read-only
    STATUS  mandatory
    DESCRIPTION
      "This entry contains the number of frames with CRC
      errors.  For every 255 incoming frames, a trap is
      generated by the unit if lineQualityCRCErrors or
      lineQualityAborts exceeds 5.  Applicable to SDLC only."
    ::= { linePhysicalEntry 5 }


  lineQualityAborts  OBJECT-TYPE
    SYNTAX  Counter
    ACCESS  read-only
    STATUS  mandatory
    DESCRIPTION
      "This entry contains the number of aborts received.
       For every 255 incoming frames, a trap is generated
       by the unit if lineQualityCRCErrors or
       lineQualityAborts exceeds 5.
       Applicable to SDLC only."
    ::= { linePhysicalEntry 6 }

  lineInterfaceType  OBJECT-TYPE
    SYNTAX  INTEGER {
      line-RS232(1),
      line-V35(2),
      line-RS530(3),
      line-universal(4),
      dsu-csu(5),
      isdn(6)
      }
    ACCESS  read-only
    STATUS  mandatory
    DESCRIPTION
      "Report hardware Interface type of the line. For
      older systems, this interface is fixed per port.

      For universal ports, the Interface type if set via
      the cable."
    ::= { linePhysicalEntry 7 }

  lineCableType  OBJECT-TYPE
    SYNTAX  INTEGER {
      not-applicable(1),
      indeterminate-cable(2),
      no-cable-attached(3),
      rs232-DTE-cable(4),
      rs232-DCE-cable(5),
      v35-DTE-cable(6),
      v35-DCE-cable(7),
      x21-DTE-cable(8),
      x21-DCE-cable(9),
      rs530-DTE-cable(10),
      rs530-DCE-cable(11)
      }
    ACCESS  read-only
    STATUS  mandatory
    DESCRIPTION
      "Returns not-applicable if the h/w does not support universal port
      configuration.  Identifies the cable type connected to the port."
    ::= { linePhysicalEntry 8 }

  lineSwitchedConnection  OBJECT-TYPE
    SYNTAX  INTEGER {
      not-applicable(1),
      dedicated(2),
      switched(3)
      }
    ACCESS  read-only
    STATUS  mandatory
    DESCRIPTION
      "Identifies whether the line is connected over a
      switched backup facility or a dedicated facility to
      a frame relay network.
      This parameter is applicable to frame relay port only.
      For any other ports it returns not-applicable.

      If the object frameRelaySwitchedBackup is set to none
      it returns not-applicable.  Otherwise returns appropriate
      value."
    ::= { linePhysicalEntry 9 }



  --
  -- The ISDN Config Control Group
  --
  -- This is a separate group for the ISDN internal device.
  --
  -- This is the configuration for this device

  isdndeviceConfigTable  OBJECT-TYPE
      SYNTAX  SEQUENCE OF IsdndeviceConfigEntry
      ACCESS  not-accessible
      STATUS  mandatory
      DESCRIPTION
        "A list of device entries."
      ::= { isdnControlGroup 1 }

  isdndeviceConfigEntry  OBJECT-TYPE
      SYNTAX  IsdndeviceConfigEntry
      ACCESS  not-accessible
      STATUS  mandatory
      DESCRIPTION
        "This entry contains information about
        a given device. The entry is indexed by the
        port number, CU index, and device."
      INDEX  { isdnLineIndex }
      ::= { isdndeviceConfigTable 1 }

  IsdndeviceConfigEntry ::=
    SEQUENCE {
      isdnLineIndex
        INTEGER,
      serviceType
        INTEGER,
      isdnSpeed
        INTEGER,
      connectionTimeOut
        INTEGER,
      nosConnectAttempts
        INTEGER,
      farEndNumberType
        INTEGER,
      farEndNumberPlan
        INTEGER,
      farEndNumber
        INTEGER,
      localNumberType
        INTEGER,
      localNumberPlan
        INTEGER,
      localNumber
        INTEGER,
      spid
        OCTET STRING
      }


  isdnLineIndex   OBJECT-TYPE
    SYNTAX  INTEGER
    ACCESS  read-only
    STATUS  mandatory
    DESCRIPTION
      "The port number for which the ISDN line is configured
       (line level)."
    ::= { isdndeviceConfigEntry 1 }

  serviceType  OBJECT-TYPE
    SYNTAX  INTEGER
    ACCESS  read-only
    STATUS  mandatory
    DESCRIPTION
      "Defines the service type of the ISDN WAN port."
    ::= { isdndeviceConfigEntry 2 }

  isdnSpeed  OBJECT-TYPE
    SYNTAX  INTEGER {
      speed56000(560),
      speed64000(640)
      }
    ACCESS  read-only
    STATUS  mandatory
    DESCRIPTION
      "The ports speed in 100 bits per second.
      The default value is 56000 bits per second."
    ::= { isdndeviceConfigEntry 3 }

  connectionTimeOut    OBJECT-TYPE
    SYNTAX  INTEGER
    ACCESS  read-only
    STATUS  mandatory
    DESCRIPTION
      "Defines the time to wait after sensing disruption
      before declaring failure.
      The range is 0 to 255 seconds.
      The default value is 12 seconds."
    ::= { isdndeviceConfigEntry 4 }

  nosConnectAttempts   OBJECT-TYPE
    SYNTAX  INTEGER
    ACCESS  read-only
    STATUS  mandatory
    DESCRIPTION
      "Defines the number or re-dial attempts before fail
      to connect.
      The range is 0 to 255.
      The default value is 1."
    ::= { isdndeviceConfigEntry 5 }

  farEndNumberType    OBJECT-TYPE
    SYNTAX  INTEGER
    ACCESS  read-only
    STATUS  mandatory
    DESCRIPTION
      "One byte field that defines the called number
      type."
    ::= { isdndeviceConfigEntry 6 }

  farEndNumberPlan    OBJECT-TYPE
    SYNTAX  INTEGER
    ACCESS  read-only
    STATUS  mandatory
    DESCRIPTION
      "One byte field that defines the called number
      Plan."
    ::= { isdndeviceConfigEntry 7 }

  farEndNumber    OBJECT-TYPE
    SYNTAX  INTEGER
    ACCESS  read-only
    STATUS  mandatory
    DESCRIPTION
      "One byte field that defines the called number."
    ::= { isdndeviceConfigEntry 8 }

  localNumberType    OBJECT-TYPE
    SYNTAX  INTEGER
    ACCESS  read-only
    STATUS  mandatory
    DESCRIPTION
      "One byte field that defines the local number
      type."
    ::= { isdndeviceConfigEntry 9 }

  localNumberPlan    OBJECT-TYPE
    SYNTAX  INTEGER
    ACCESS  read-only
    STATUS  mandatory
    DESCRIPTION
      "One byte field that defines the local number
      Plan."
    ::= { isdndeviceConfigEntry 10 }

  localNumber    OBJECT-TYPE
    SYNTAX  INTEGER
    ACCESS  read-only
    STATUS  mandatory
    DESCRIPTION
      "One byte field that defines the local number."
    ::= { isdndeviceConfigEntry 11 }

  spid    OBJECT-TYPE
    SYNTAX  OCTET STRING (SIZE(20))
    ACCESS  read-only
    STATUS  mandatory
    DESCRIPTION
      "SPID is a zero-terminated ASCII string with
       a minium length of 0 and a maximum length of 20. "
    ::= { isdndeviceConfigEntry 12 }

  --
  -- The ISDN Statitics Group
  --

  isdndeviceStatsTable  OBJECT-TYPE
      SYNTAX  SEQUENCE OF IsdndeviceStatsEntry
      ACCESS  not-accessible
      STATUS  mandatory
      DESCRIPTION
        "A list of device entries."
      ::= { isdnControlGroup 2 }

  isdndeviceStatsEntry  OBJECT-TYPE
      SYNTAX  IsdndeviceStatsEntry
      ACCESS  not-accessible
      STATUS  mandatory
      DESCRIPTION
        "This entry contains information about
        a given device. The entry is indexed by the
        port number, CU index, and device."
      INDEX  { isdnIndex }
      ::= { isdndeviceStatsTable 1 }

  IsdndeviceStatsEntry ::=
    SEQUENCE {
      isdnIndex
        INTEGER,
      channelID
        INTEGER,
      kbytesTransmitted
        Counter,
      kbytesReceived
        Counter,
      packetsTransmitted
        Counter,
      packetsReceived
        Counter,
      isdnloopbackbytesTransmitted
        Counter,
      isdnloopbackbytesReceived
        Counter,
      isdnCRCErrors
        Counter
      }


  isdnIndex   OBJECT-TYPE
    SYNTAX  INTEGER
    ACCESS  read-only
    STATUS  mandatory
    DESCRIPTION
      "The port number for which the ISDN line is configured
       (line level)."
    ::= { isdndeviceStatsEntry 1 }

  channelID   OBJECT-TYPE
    SYNTAX  INTEGER
    ACCESS  read-only
    STATUS  mandatory
    DESCRIPTION
      "The port number for which the ISDN line is configured
       (line level)."
    ::= { isdndeviceStatsEntry 2 }

  kbytesTransmitted  OBJECT-TYPE
    SYNTAX  Counter
    ACCESS  read-only
    STATUS  mandatory
    DESCRIPTION
      "This entry contains the number of bytes
       transmited."
    ::= { isdndeviceStatsEntry 3 }

  kbytesReceived    OBJECT-TYPE
    SYNTAX  Counter
    ACCESS  read-only
    STATUS  mandatory
    DESCRIPTION
      "This entry contains the number of bytes
       received."
    ::= { isdndeviceStatsEntry 4 }

  packetsTransmitted  OBJECT-TYPE
    SYNTAX  Counter
    ACCESS  read-only
    STATUS  mandatory
    DESCRIPTION
      "This entry contains the number of packets
       transmited."
    ::= { isdndeviceStatsEntry 5 }

  packetsReceived  OBJECT-TYPE
    SYNTAX  Counter
    ACCESS  read-only
    STATUS  mandatory
    DESCRIPTION
      "This entry contains the number of packets
       received."
    ::= { isdndeviceStatsEntry 6 }

  isdnloopbackbytesTransmitted  OBJECT-TYPE
    SYNTAX  Counter
    ACCESS  read-only
    STATUS  mandatory
    DESCRIPTION
      "This entry contains the number of bytes
       transmited."
    ::= { isdndeviceStatsEntry 7 }

  isdnloopbackbytesReceived  OBJECT-TYPE
    SYNTAX  Counter
    ACCESS  read-only
    STATUS  mandatory
    DESCRIPTION
      "This entry contains the number of bytes
       received."
    ::= { isdndeviceStatsEntry 8 }

  isdnCRCErrors  OBJECT-TYPE
    SYNTAX  Counter
    ACCESS  read-only
    STATUS  mandatory
    DESCRIPTION
      "This entry contains the number of frames with CRC
      errors."
    ::= { isdndeviceStatsEntry 9 }

  --
  -- The DsuCSU Control Group
  --
  -- This is a separate group for the DSU/CSU internal device.
  --
  -- This is the configuration for this device
  --

  dsucsudeviceConfigTable  OBJECT-TYPE
      SYNTAX  SEQUENCE OF DsucsudeviceConfigEntry
      ACCESS  not-accessible
      STATUS  mandatory
      DESCRIPTION
        "A list of device entries."
      ::= { dsucsuControlGroup 1 }

  dsucsudeviceConfigEntry  OBJECT-TYPE
      SYNTAX  DsucsudeviceConfigEntry
      ACCESS  not-accessible
      STATUS  mandatory
      DESCRIPTION
        "This entry contains information about
        a given device. The entry is indexed by the
        port number, CU index, and device."
      INDEX  { dsucsuLineNumber }
      ::= { dsucsudeviceConfigTable 1 }

  DsucsudeviceConfigEntry ::=
    SEQUENCE {
      dsucsuLineNumber
        INTEGER,
      dsucsuType
        INTEGER,
      dsucsuClocking
        INTEGER,
      dsucsuSpeed
        INTEGER
      }


  dsucsuLineNumber   OBJECT-TYPE
    SYNTAX  INTEGER
    ACCESS  read-only
    STATUS  mandatory
    DESCRIPTION
      "The port number for which the DsuCsu line is configured
       (line level)."
    ::= { dsucsudeviceConfigEntry 1 }

  dsucsuType  OBJECT-TYPE
    SYNTAX  INTEGER {
      dsu-csu-dds(1),
      dsu-csu-async-dial(2)
      }
    ACCESS  read-only
    STATUS  mandatory
    DESCRIPTION
      "Defines the service type of the DSU/CSU port."
    ::= { dsucsudeviceConfigEntry 2 }

  dsucsuClocking  OBJECT-TYPE
    SYNTAX  INTEGER {
      external(1),
      internal(2)
      }
    ACCESS  read-only
    STATUS  mandatory
    DESCRIPTION
      "Clocking source for this port.
      Setting 'internal' will cause the
      port to emulate a physical DCE, and setting
      external will cause the port to emulate a
      physical DTE.
      The default value for this field is 'external'."
    ::= { dsucsudeviceConfigEntry 3 }

  dsucsuSpeed  OBJECT-TYPE
    SYNTAX  INTEGER {
      speed56000(560),
      speed64000(640)
      }
    ACCESS  read-only
    STATUS  mandatory
    DESCRIPTION
      "The ports speed in 100 bits per second.
      The default value is 56000 bits per second."
    ::= { dsucsudeviceConfigEntry 4 }

  --
  -- The DsuCSU Stats Group
  --
  --

  dsucsudeviceStatsTable  OBJECT-TYPE
      SYNTAX  SEQUENCE OF DsucsudeviceStatsEntry
      ACCESS  not-accessible
      STATUS  mandatory
      DESCRIPTION
        "A list of device entries."
      ::= { dsucsuControlGroup 2 }

  dsucsudeviceStatsEntry  OBJECT-TYPE
      SYNTAX  DsucsudeviceStatsEntry
      ACCESS  not-accessible
      STATUS  mandatory
      DESCRIPTION
        "This entry contains information about
        a given device. The entry is indexed by the
        port number, CU index, and device."
      INDEX  { dsucsuLine }
      ::= { dsucsudeviceStatsTable 1 }

  DsucsudeviceStatsEntry ::=
    SEQUENCE {
      dsucsuLine
        INTEGER,
      dsucsuloopbackbytesTransmitted
        Counter,
      dsucsuloopbackbytesReceived
        Counter
      }


  dsucsuLine   OBJECT-TYPE
    SYNTAX  INTEGER
    ACCESS  read-only
    STATUS  mandatory
    DESCRIPTION
      "The port number for which the DsuCsu line is configured
       (line level)."
    ::= { dsucsudeviceStatsEntry 1 }

  dsucsuloopbackbytesTransmitted  OBJECT-TYPE
    SYNTAX  Counter
    ACCESS  read-only
    STATUS  mandatory
    DESCRIPTION
      "This entry contains the number of bytes
       transmited."
    ::= { dsucsudeviceStatsEntry 2 }

  dsucsuloopbackbytesReceived  OBJECT-TYPE
    SYNTAX  Counter
    ACCESS  read-only
    STATUS  mandatory
    DESCRIPTION
      "This entry contains the number of bytes
       received."
    ::= { dsucsudeviceStatsEntry 3 }


  --
  -- The SDLC Port Level Configuration Group
  --

  --
  -- The SDLC Configuration Table:
  --

  sdlcConfigTable  OBJECT-TYPE
    SYNTAX SEQUENCE OF SdlcConfigEntry
    ACCESS  not-accessible
    STATUS  mandatory
    DESCRIPTION
      "A table of SDLC information."
    ::= { lineSDLCGroup 1 }

  sdlcConfigEntry  OBJECT-TYPE
    SYNTAX  SdlcConfigEntry
    ACCESS  not-accessible
    STATUS  mandatory
    DESCRIPTION
      "An entry consisting of port information for a
       particular SDLC port."
    INDEX { sdlcConfigPortIndex }
    ::= { sdlcConfigTable 1 }

  SdlcConfigEntry ::=
    SEQUENCE {
      sdlcConfigPortIndex
        INTEGER,
      sdlcConfigType
        INTEGER,
      sdlcInitState
        INTEGER,
      sdlcCarrier
        INTEGER,
      sdlcClocking
        INTEGER,
      sdlcSpeed
        INTEGER,
      sdlcPause
        INTEGER,
      sdlcNRZI
        INTEGER,
      sdlcT1Timer
        INTEGER,
      sdlcSlowPollTimer
        INTEGER,
      sdlcMaxRetries
        INTEGER,
      sdlcNAUName
        DisplayString,
      sdlcMultiFlagInsertion
        INTEGER,
      sdlcCTS
        INTEGER,
      sdlcDCD
        INTEGER,
      sdlcDSR
        INTEGER,
      sdlcDTR
        INTEGER,
      sdlcRTS
        INTEGER,
      sdlcReturnClock
        INTEGER
    }


  sdlcConfigPortIndex  OBJECT-TYPE
    SYNTAX  INTEGER
    ACCESS  read-only
    STATUS  mandatory
    DESCRIPTION
      "The port number that uniquely identifies
       this port.
       Current supported SDLC numbers are 1-4."
    ::= { sdlcConfigEntry 1 }


  sdlcConfigType  OBJECT-TYPE
    SYNTAX  INTEGER {
      hsdlc-type(11),
      tsdlc-type(12)
      }
    ACCESS  read-only
    STATUS  mandatory
    DESCRIPTION
      "The port type.

      TSDLC (Terminal SDLC) ports emulate a Host
      and poll the downstream PUs (e.g. 3274 or 3174
      SDLC/SNA controllers).

      HSDLC ports (Host SDLC) ports emulate a line with
      Terminal Controllers (PUs) and respond to polls
      from the Host or upstream PU.

      Note that all ports must currently be defined as
      the same time for a given unit (i.e. no mixing of
      HSDLC and TSDLC ports is allowed)."
    ::= { sdlcConfigEntry 2 }

  sdlcInitState  OBJECT-TYPE
    SYNTAX  INTEGER {
      in-service(1),
      out-of-service(2)
      }
    ACCESS  read-only
    STATUS  mandatory
    DESCRIPTION
      "The initial state of the SDLC port.

      If configured for 'in-service', then the SDLC port will
      be brougt up automattically when the unit is powered
      up.

      If configured for 'out-of-service', the the SDLC port must
      be manually enabled by operator intervention (i.e.
      enable command must be sent).

      The default value is 'enabled'."
    ::= { sdlcConfigEntry 3 }

  sdlcCarrier  OBJECT-TYPE
    SYNTAX  INTEGER {
      constant(1),
      switched(2)
      }
    ACCESS  read-only
    STATUS  mandatory
    DESCRIPTION
      "This field indicates whether Carrier (a.k.a. CD or
      DCD, RS-232 pin 8) is constant or switched for
      DCE devices (internally clocked), or Request To
      Send (a.k.a. RTS, RS-232 pin 4) is constant or
      switched.

      This parameter also affects SDLC flag generation.
      If configured for constant then the line will
      transmit flags in an idle (no data being sent) state.
      If configured for switched then the line will
      transmit all one bits (mark state).

      The default value for this parameter is 'constant'."
    ::= { sdlcConfigEntry 4 }

  sdlcClocking  OBJECT-TYPE
    SYNTAX  INTEGER {
      external(1),
      internal(2),
      x21-external(3),
      x21-internal(4)
      }
    ACCESS  read-only
    STATUS  mandatory
    DESCRIPTION
      "Clocking source for this port.
      Setting 'internal' will cause the
      port to emulate a physical DCE, and setting
      external will cause the port to emulate a
      physical DTE.
      X21 External and Internal are used (with the
      proper external adapter) to support X.21 Leased
      Line operation for RS-422/RS-530 (25 pin balanced)
      interfaces.  X21 operation is not supported for
      boards that operate RS-232 or V.35.
      The default value for this field is 'external'."
    ::= { sdlcConfigEntry 5 }

  sdlcSpeed  OBJECT-TYPE
    SYNTAX  INTEGER {
      speed1200(12),
      speed2000(20),
      speed2400(24),
      speed3600(36),
      speed4800(48),
      speed7200(72),
      speed9600(96),
      speed14400(144),
      speed19200(192),
      speed28800(288),
      speed48000(480),
      speed56000(560),
      speed64000(640),
      speed128000(1280)
      }
    ACCESS  read-only
    STATUS  mandatory
    DESCRIPTION
      "The ports speed in 100 bits per second.
      The default value is 9600 bits per second.
      Speeds higher than 19200 are not supported on
      RS-232 ports units (must be V.35 or RS-422)."
    ::= { sdlcConfigEntry 6 }

  sdlcPause  OBJECT-TYPE
    SYNTAX  INTEGER
    ACCESS  read-only
    STATUS  mandatory
    DESCRIPTION
      "This parameter defines the amount of time
      between polls in 1/100 second (10 millisecond)
      intervals.  If set to zero then the port will
      poll the PUs as fast as possible.  The minimum
      value for this parameter is 5 and the timer
      has a resolution of 25 milliseconds.
      The default value is 20 (.20 seconds).
      This field is not applicable to Host port.  It
      returns a dummy value."
    ::= { sdlcConfigEntry 7 }

  sdlcNRZI  OBJECT-TYPE
    SYNTAX  INTEGER {
      yes(1),
      no(2)
      }
    ACCESS  read-only
    STATUS  mandatory
    DESCRIPTION
      "This parameter indicates whether the port is
      configured for NRZI (yes) or NRZ (no) bit
      encoding.
      The default value is 'No' (NRZ encoding selected)."
    ::= { sdlcConfigEntry 8 }

  sdlcT1Timer  OBJECT-TYPE
    SYNTAX  INTEGER
    ACCESS  read-only
    STATUS  mandatory
    DESCRIPTION
      "The SDLC T1 timer value in 20ths of a second.
      The default value is 20 (1 second).

      This field is not applicable to Host ports.  It
      returns a dummy value."
    ::= { sdlcConfigEntry 9 }

  sdlcSlowPollTimer OBJECT-TYPE
    SYNTAX  INTEGER
    ACCESS  read-only
    STATUS  mandatory
    DESCRIPTION
      "The slow poll timer value in 20ths of a second.
      The slow poll timer is the amount of time to wait
      to contact (send SNRM) failed PUs.
      The default value for this field is 600 (30 seconds).
      This field is not applicable to Host ports.  It
      returns a dummy value."
    ::= { sdlcConfigEntry 10 }

  sdlcMaxRetries  OBJECT-TYPE
    SYNTAX  INTEGER (1..99)
    ACCESS  read-only
    STATUS  mandatory
    DESCRIPTION
      "The maximum number of retries (N2 value) before
      failing a PU.
      The default value for this field is 3.
      This field is not applicable to Host ports.  It
      returns a dummy value."

    ::= { sdlcConfigEntry 11 }

  sdlcNAUName   OBJECT-TYPE
    SYNTAX  DisplayString (SIZE(1..8))
    ACCESS  read-only
    STATUS  mandatory
    DESCRIPTION
      "The NAU name of this port.
      The default value for this field is all blank
      (filled with ASCII space 0x20 characters)."
    ::= { sdlcConfigEntry 12 }

   sdlcMultiFlagInsertion   OBJECT-TYPE
    SYNTAX  INTEGER {
      yes(1),
      no(2)
      }
    ACCESS  read-only
    STATUS  mandatory
    DESCRIPTION
      "This parameter indicates whether the port is
      configured to send multiple interframe flags.
      The default value is 'No' (single flags)."
    ::= { sdlcConfigEntry 13 }

  sdlcCTS  OBJECT-TYPE
    SYNTAX  INTEGER {
      yes(1),
      no(2)
      }
    ACCESS  read-only
    STATUS  mandatory
    DESCRIPTION
      "Defines whether CTS is an input signal used to
      determine the port status. This parameter is applicable
      if clocking is set to external.  For internal clocking
      the parameter is ignored and DCD is asserted when port
      is enabled. The range is yes and no.

      The default value is 'No'."
    ::= { sdlcConfigEntry 14 }

   sdlcDCD  OBJECT-TYPE
    SYNTAX  INTEGER {
      yes(1),
      no(2)
      }
    ACCESS  read-only
    STATUS  mandatory
    DESCRIPTION
      "Defines whether DCD is required as input signal
      or ignored. This parameter is applicable if the
      clocking is set to external.  For internal clocking
      the parameter is ignored and DCD is asserted when port
      is enabled. The range is yes and no.

      The default value is 'yes'."
    ::= { sdlcConfigEntry 15 }

  sdlcDSR  OBJECT-TYPE
    SYNTAX  INTEGER {
      yes(1),
      no(2)
      }
    ACCESS  read-only
    STATUS  mandatory
    DESCRIPTION
      "Defines whether DSR is required as input signal
      or ignored. This parameter is applicable if the
      clocking is set to external.  For internal clocking
      the parameter is ignored and DSR is asserted when port
      is enabled. The range is yes and no.

      The default value is 'yes'."
    ::= { sdlcConfigEntry 16 }

  sdlcDTR  OBJECT-TYPE
    SYNTAX  INTEGER {
      yes(1),
      no(2)
      }
    ACCESS  read-only
    STATUS  mandatory
    DESCRIPTION
      "Defines whether DTR is required as input signal
      or ignored. This parameter is applicable if the
      clocking is set to internal.  For external clocking
      the parameter is ignored and DTR is asserted when port
      is enabled. The range is yes and no.

      The default value is 'yes'."
    ::= { sdlcConfigEntry 17 }

  sdlcRTS  OBJECT-TYPE
    SYNTAX  INTEGER {
      yes(1),
      no(2)
      }
    ACCESS  read-only
    STATUS  mandatory
    DESCRIPTION
      "Defines whether RTS is an input signal to determine
      the port status. This parameter is applicable if the
      clocking is set to internal.  For external clocking
      the parameter is ignored and RTS is asserted when port
      is enabled. The range is yes and no.

      The default value is 'No'."
    ::= { sdlcConfigEntry 18 }

  sdlcReturnClock  OBJECT-TYPE
    SYNTAX  INTEGER {
      yes(1),
      no(2),
      default(3)
      }
    ACCESS  read-only
    STATUS  mandatory
    DESCRIPTION
      "Defines whether Return Clock (SCTE) is available as
      input signal or ignored. This parameter is applicable
      if the clocking is set to internal. For external clocking
      the parameter is ignored. The range is yes and no.

      The default value is 'yes'."
    ::= { sdlcConfigEntry 19 }


  --
  -- The SDLC Port Statistics Table:
  --

  sdlcStatsTable  OBJECT-TYPE
    SYNTAX SEQUENCE OF SdlcStatsEntry
    ACCESS  not-accessible
    STATUS  mandatory
    DESCRIPTION
      "A table of SDLC information."
    ::= { lineSDLCGroup 2 }

  sdlcStatsEntry  OBJECT-TYPE
    SYNTAX  SdlcStatsEntry
    ACCESS  not-accessible
    STATUS  mandatory
    DESCRIPTION
      "An entry consisting of port information for a
      particular SDLC port."
    INDEX { sdlcStatsPortIndex }
    ::= { sdlcStatsTable 1 }

  SdlcStatsEntry ::=
    SEQUENCE {
      sdlcStatsPortIndex
        INTEGER,
      sdlcPortType
        INTEGER,
      sdlcInOctets
        Counter,
      sdlcOutOctets
        Counter,
      sdlcInFrames
        Counter,
      sdlcOutFrames
        Counter,
      sdlcOverruns
        Counter,
      sdlcCRCErrors
        Counter,
      sdlcRecvAborts
        Counter,
      sdlcpollrsptimeouts
        Counter,
      sdlciframetrans
        Counter
    }


  sdlcStatsPortIndex OBJECT-TYPE
    SYNTAX  INTEGER
    ACCESS  read-only
    STATUS  mandatory
    DESCRIPTION
      "The port number that uniquely identifies
      this SDLC port.
      Current supported numbers on are 1-4."
    ::= { sdlcStatsEntry 1 }


  sdlcPortType  OBJECT-TYPE
    SYNTAX  INTEGER {
      hsdlc-type(11),
      tsdlc-type(12)
      }
    ACCESS  read-only
    STATUS  mandatory
    DESCRIPTION
      "The port type.
      TSDLC (Terminal SDLC) ports emulate a Host
      and poll the downstream PUs (e.g. 3274 or 3174
      SDLC/SNA controllers).
      HSDLC ports (Host SDLC) ports emulate a line with
      Terminal Controllers (PUs) and respond to polls
      from the Host or upstream PU."
    ::= { sdlcStatsEntry 2 }

  sdlcInOctets OBJECT-TYPE
    SYNTAX  Counter
    ACCESS  read-only
    STATUS  mandatory
    DESCRIPTION
      "The number of bytes received."
    ::= { sdlcStatsEntry 3 }

  sdlcOutOctets OBJECT-TYPE
    SYNTAX  Counter
    ACCESS  read-only
    STATUS  mandatory
    DESCRIPTION
      "The number of bytes sent."
    ::= { sdlcStatsEntry 4 }

  sdlcInFrames OBJECT-TYPE
    SYNTAX  Counter
    ACCESS  read-only
    STATUS  mandatory
    DESCRIPTION
      "The number of I-frames received."
    ::= { sdlcStatsEntry 5 }

  sdlcOutFrames OBJECT-TYPE
    SYNTAX  Counter
    ACCESS  read-only
    STATUS  mandatory
    DESCRIPTION
      "The number of I-frames sent."
    ::= { sdlcStatsEntry 6 }

  sdlcOverruns  OBJECT-TYPE
    SYNTAX  Counter
    ACCESS  read-only
    STATUS  mandatory
    DESCRIPTION
      "The number of overruns."
    ::= { sdlcStatsEntry 7 }

  sdlcCRCErrors  OBJECT-TYPE
    SYNTAX  Counter
    ACCESS  read-only
    STATUS  mandatory
    DESCRIPTION
      "The number of CRC errors."
    ::= { sdlcStatsEntry 8 }


  sdlcRecvAborts  OBJECT-TYPE
    SYNTAX  Counter
    ACCESS  read-only
    STATUS  mandatory
    DESCRIPTION
      "The number of aborts received."
    ::= { sdlcStatsEntry 9 }

  sdlcpollrsptimeouts  OBJECT-TYPE
    SYNTAX  Counter
    ACCESS  read-only
    STATUS  mandatory
    DESCRIPTION
      "The number of poll response timeouts."
    ::= { sdlcStatsEntry 10 }


  sdlciframetrans OBJECT-TYPE
    SYNTAX  Counter
    ACCESS  read-only
    STATUS  mandatory
    DESCRIPTION
      "The number of i-frame re-transmissions."
    ::= { sdlcStatsEntry 11 }

  --
  -- The Bisync Port Level Group
  --
  --
  -- The Bisync Configuration Table:
  --

  bisyncConfigTable  OBJECT-TYPE
    SYNTAX SEQUENCE OF BisyncConfigEntry
    ACCESS  not-accessible
    STATUS  mandatory
    DESCRIPTION
      "A table of Bisync port information."
    ::= { lineBisyncGroup 1 }

  bisyncConfigEntry  OBJECT-TYPE
    SYNTAX  BisyncConfigEntry
    ACCESS  not-accessible
    STATUS  mandatory
    DESCRIPTION
      "An entry consisting of port information for a
       particular Bisync port."
    INDEX { bisyncConfigPortIndex }
    ::= { bisyncConfigTable 1 }

  BisyncConfigEntry ::=
    SEQUENCE {
      bisyncConfigPortIndex
        INTEGER,
      bisyncConfigType
        INTEGER,
      bisyncNAUName
        DisplayString,
      bisyncInitState
        INTEGER,
      bisyncCarrier
        INTEGER,
      bisyncClocking
        INTEGER,
      bisyncSpeed
        INTEGER,
      bisyncPause
        INTEGER,
      bisyncReplyTimer
        INTEGER,
      bisyncRetries
        INTEGER,
      bisyncSlowpollTimer
        INTEGER,
      bisyncSessTerm
        INTEGER,
      bisyncIBS
        INTEGER,
      bisyncCTS
        INTEGER,
      bisyncDCD
        INTEGER,
      bisyncDSR
        INTEGER,
      bisyncDTR
        INTEGER,
      bisyncRTS
        INTEGER,
      bisyncReturnClock
        INTEGER
    }

  bisyncConfigPortIndex  OBJECT-TYPE
    SYNTAX  INTEGER
    ACCESS  read-only
    STATUS  mandatory
    DESCRIPTION
      "The port number that uniquely identifies
      this port.
      Current supported Bisync numbers are 1-4."
    ::= { bisyncConfigEntry 1 }


  bisyncConfigType  OBJECT-TYPE
    SYNTAX  INTEGER {
      hbsc-type(1),
      tbsc-type(2)
      }
    ACCESS  read-only
    STATUS  mandatory
    DESCRIPTION
      "The port type.

      TBSC (Terminal Bisync) ports emulate a Host
      and polls the downstream controllers).

      HBSC ports (Host Bisync) ports emulate a line with
      Terminal Controllers (CUs) and respond to polls
      from the Host."

    ::= { bisyncConfigEntry 2 }

  bisyncNAUName   OBJECT-TYPE
    SYNTAX  DisplayString (SIZE(1..8))
    ACCESS  read-only
    STATUS  mandatory
    DESCRIPTION
      "The NAU name of this port.
      The default value for this field is all blank
      (filled with ASCII space 0x20 characters)."
    ::= { bisyncConfigEntry 3 }

  bisyncInitState  OBJECT-TYPE
    SYNTAX  INTEGER {
      in-service(1),
      out-of-service(2)
      }
    ACCESS  read-only
    STATUS  mandatory
    DESCRIPTION
      "The initial state of the Bisync port.

      If configured for 'in-service', then the Bisync port will
      be brougt up automattically when the unit is powered
      up.

      If configured for 'out-of-service', then the Bisync port must
      be manually enabled by operator intervention (i.e.
      enable command must be sent).

      The default value is 'enabled'."
    ::= { bisyncConfigEntry 4 }

  bisyncCarrier  OBJECT-TYPE
    SYNTAX  INTEGER {
      constant(1),
      switched(2)
      }
    ACCESS  read-only
    STATUS  mandatory
    DESCRIPTION
      "This field indicates whether Carrier (a.k.a. CD or
      DCD, RS-232 pin 8) is constant or switched for
      DCE devices (internally clocked), or Request To
      Send (a.k.a. RTS, RS-232 pin 4) is constant or
      switched.

      The default value for this parameter is 'constant'."
    ::= { bisyncConfigEntry 5 }

  bisyncClocking  OBJECT-TYPE
    SYNTAX  INTEGER {
      external(1),
      internal(2),
      x21-external(3),
      x21-internal(4)
      }
    ACCESS  read-only
    STATUS  mandatory
    DESCRIPTION
      "Clocking source for this port.
      Setting 'internal' will cause the
      port to emulate a physical DCE, and setting
      external will cause the port to emulate a
      physical DTE.
      X21 External and Internal are used (with the
      proper external adapter) to support X.21 Leased
      Line operation for RS-422/RS-530 (25 pin balanced)
      interfaces.  X21 operation is not supported for
      boards that operate RS-232 or V.35.
      The default value for this field is 'external'."
    ::= { bisyncConfigEntry 6 }

  bisyncSpeed  OBJECT-TYPE
    SYNTAX  INTEGER {
      speed1200(12),
      speed2000(20),
      speed2400(24),
      speed3600(36),
      speed4800(48),
      speed7200(72),
      speed9600(96),
      speed14400(144),
      speed19200(192),
      speed28800(288),
      speed48000(480),
      speed56000(560),
      speed64000(640)
      }
    ACCESS  read-only
    STATUS  mandatory
    DESCRIPTION
      "The ports speed in bits per second.
      The default value is 9600 bits per second.
      Speeds higher than 64000 are not supported."
    ::= { bisyncConfigEntry 7 }

  bisyncPause OBJECT-TYPE
    SYNTAX  INTEGER
    ACCESS  read-only
    STATUS  mandatory
    DESCRIPTION
      "This parameter defines the amount of time
      between polls in 1/100 second (10 millisecond)
      intervals.  If set to zero then the port will
      poll the CUs as fast as possible.  The minimum
      value for this parameter is 5 and the timer
      has a resolution of 25 milliseconds.
      The default value is 20 (.20 seconds).
      This field is not applicable to a Host port. It
      returns a dummy value."
    ::= { bisyncConfigEntry 8 }

  bisyncReplyTimer  OBJECT-TYPE
    SYNTAX  INTEGER (1..99)

    ACCESS  read-only
    STATUS  mandatory
    DESCRIPTION
      "The time to wait for a response in seconds.
      The default value for this field is 3 seconds."

    ::= { bisyncConfigEntry 9 }

  bisyncRetries  OBJECT-TYPE
    SYNTAX  INTEGER (1..99)
    ACCESS  read-only
    STATUS  mandatory
    DESCRIPTION
      "The maximum number of retries (N2 value) before
      failing a CU.
      The default value for this field is 5."

    ::= { bisyncConfigEntry 10 }

  bisyncSlowpollTimer  OBJECT-TYPE
    SYNTAX  INTEGER (1..99)
    ACCESS  read-only
    STATUS  mandatory
    DESCRIPTION
      "The time to wait in seconds before attempting a
      slowpoll.

      The default value for this field is 30 seconds."

    ::= { bisyncConfigEntry 11 }

  bisyncSessTerm   OBJECT-TYPE
    SYNTAX  INTEGER {
      none (1),
      interventionReq (2),
      unformattedLogoff (3)
      }
    ACCESS  read-only
    STATUS  mandatory
    DESCRIPTION
      "The type of session termination used. Only
      applies to Host BSC ports."
    ::= { bisyncConfigEntry 12 }

  bisyncIBS  OBJECT-TYPE
    SYNTAX  INTEGER {
      yes(1),
      no(2)
      }
    ACCESS  read-only
    STATUS  mandatory
    DESCRIPTION
      "Some of non IBM 3270 BSC controllers can not handle
      ESC character but IBM 3270 BSC implementation requires
      ESC character.  A new configuration parameter for
      Terminal BSC line as described below

      The default value is Yes."
    ::= { bisyncConfigEntry 13 }

  bisyncCTS  OBJECT-TYPE
    SYNTAX  INTEGER {
      yes(1),
      no(2)
      }
    ACCESS  read-only
    STATUS  mandatory
    DESCRIPTION
      "Defines whether CTS is an input signal used to
      determine the port status. This parameter is applicable
      if clocking is set to external.  For internal clocking
      the parameter is ignored and DCD is asserted when port
      is enabled. The range is yes and no.

      The default value is 'No'."
    ::= { bisyncConfigEntry 14 }

   bisyncDCD  OBJECT-TYPE
    SYNTAX  INTEGER {
      yes(1),
      no(2)
      }
    ACCESS  read-only
    STATUS  mandatory
    DESCRIPTION
      "Defines whether DCD is required as input signal
      or ignored. This parameter is applicable if the
      clocking is set to external.  For internal clocking
      the parameter is ignored and DCD is asserted when port
      is enabled. The range is yes and no.

      The default value is 'yes'."
    ::= { bisyncConfigEntry 15 }

  bisyncDSR  OBJECT-TYPE
    SYNTAX  INTEGER {
      yes(1),
      no(2)
      }
    ACCESS  read-only
    STATUS  mandatory
    DESCRIPTION
      "Defines whether DSR is required as input signal
      or ignored. This parameter is applicable if the
      clocking is set to external.  For internal clocking
      the parameter is ignored and DSR is asserted when port
      is enabled. The range is yes and no.

      The default value is 'yes'."
    ::= { bisyncConfigEntry 16 }

  bisyncDTR  OBJECT-TYPE
    SYNTAX  INTEGER {
      yes(1),
      no(2)
      }
    ACCESS  read-only
    STATUS  mandatory
    DESCRIPTION
      "Defines whether DTR is required as input signal
      or ignored. This parameter is applicable if the
      clocking is set to internal.  For external clocking
      the parameter is ignored and DTR is asserted when port
      is enabled. The range is yes and no.

      The default value is 'yes'."
    ::= { bisyncConfigEntry 17 }

  bisyncRTS  OBJECT-TYPE
    SYNTAX  INTEGER {
      yes(1),
      no(2)
      }
    ACCESS  read-only
    STATUS  mandatory
    DESCRIPTION
      "Defines whether RTS is an input signal to determine
      the port status. This parameter is applicable if the
      clocking is set to internal.  For external clocking
      the parameter is ignored and RTS is asserted when port
      is enabled. The range is yes and no.

      The default value is 'No'."
    ::= { bisyncConfigEntry 18 }

  bisyncReturnClock  OBJECT-TYPE
    SYNTAX  INTEGER {
      yes(1),
      no(2),
      default(3)
      }
    ACCESS  read-only
    STATUS  mandatory
    DESCRIPTION
      "Defines whether Return Clock (SCTE) is available as
      input signal or ignored. This parameter is applicable
      if the clocking is set to internal. For external clocking
      the parameter is ignored. The range is yes and no.

      The default value is 'yes'."
    ::= { bisyncConfigEntry 19 }

  --
  -- The Bisync Port Statistics Table:
  --

  bisyncStatsTable   OBJECT-TYPE
    SYNTAX SEQUENCE OF BisyncStatsEntry
    ACCESS  not-accessible
    STATUS  mandatory
    DESCRIPTION
      "A table of Bisync information."
    ::= { lineBisyncGroup 2 }

  bisyncStatsEntry   OBJECT-TYPE
    SYNTAX  BisyncStatsEntry
    ACCESS  not-accessible
    STATUS  mandatory
    DESCRIPTION
      "An entry consisting of port information for a
       particular Bisync port."
    INDEX { bisyncStatsPortIndex }
    ::= { bisyncStatsTable 1 }

  BisyncStatsEntry ::=
    SEQUENCE {
      bisyncStatsPortIndex
        INTEGER,
      bisyncPortType
        INTEGER,
      bisyncInOctets
        Counter,
      bisyncOutOctets
        Counter,
      bisyncOverruns
        Counter,
      bisyncCRCErrors
        Counter,
      bisyncRcvTimeout
        Counter,
      bisyncXmtTimeout
        Counter
    }


  bisyncStatsPortIndex OBJECT-TYPE
    SYNTAX  INTEGER
    ACCESS  read-only
    STATUS  mandatory
    DESCRIPTION
      "The port number that uniquely identifies
      this Bisync port.
      Current supported numbers are 1-4."
    ::= { bisyncStatsEntry 1 }


  bisyncPortType  OBJECT-TYPE
    SYNTAX  INTEGER {
      hbsc-type(1),
      tbsc-type(2)
      }
    ACCESS  read-only
    STATUS  mandatory
    DESCRIPTION
      "The port type.
      TBSC (Terminal Bisync) ports emulate a Host
      and poll the downstream controllers).
      HBSC ports (Host Bisync) ports emulate a line with
      Terminal Controllers (PUs) and respond to polls
      from the Host or upstream PU."
    ::= { bisyncStatsEntry 2 }

  bisyncInOctets OBJECT-TYPE
    SYNTAX  Counter
    ACCESS  read-only
    STATUS  mandatory
    DESCRIPTION
      "The number of bytes received."
    ::= { bisyncStatsEntry 3 }

  bisyncOutOctets OBJECT-TYPE
    SYNTAX  Counter
    ACCESS  read-only
    STATUS  mandatory
    DESCRIPTION
      "The number of bytes sent."
    ::= { bisyncStatsEntry 4 }

  bisyncOverruns  OBJECT-TYPE
    SYNTAX  Counter
    ACCESS  read-only
    STATUS  mandatory
    DESCRIPTION
      "The number of receiver overruns."
    ::= { bisyncStatsEntry 5 }

  bisyncCRCErrors  OBJECT-TYPE
    SYNTAX  Counter
    ACCESS  read-only
    STATUS  mandatory
    DESCRIPTION
      "The number of receive frame CRC errors."
    ::= { bisyncStatsEntry 6 }

  bisyncRcvTimeout OBJECT-TYPE
    SYNTAX  Counter
    ACCESS  read-only
    STATUS  mandatory
    DESCRIPTION
      "The number of receive timeout."
    ::= { bisyncStatsEntry 7 }

  bisyncXmtTimeout OBJECT-TYPE
    SYNTAX  Counter
    ACCESS  read-only
    STATUS  mandatory
    DESCRIPTION
      "The number of transmit timeout."
    ::= { bisyncStatsEntry 8 }

  --
  -- The Frame Relay Port Level Group
  --
  --
  -- The Frame Relay Configuration Table:
  --

  frameRelayConfigTable  OBJECT-TYPE
    SYNTAX SEQUENCE OF FrameRelayConfigEntry
    ACCESS  not-accessible
    STATUS  mandatory
    DESCRIPTION
      "A table of Sync product Frame Relay information."
    ::= { lineFrameRelayGroup 1 }

  frameRelayConfigEntry  OBJECT-TYPE
    SYNTAX  FrameRelayConfigEntry
    ACCESS  not-accessible
    STATUS  mandatory
    DESCRIPTION
      "An entry consisting of port information for a
      particular Sync product Frame Relay port."
    INDEX { frameRelayConfigPortIndex }
    ::= { frameRelayConfigTable 1 }

  FrameRelayConfigEntry ::=
    SEQUENCE {
      frameRelayConfigPortIndex
        INTEGER,
      frameRelayPortType
        INTEGER,
      frameRelayInitState
        INTEGER,
      frameRelayClocking
        INTEGER,
      frameRelaySpeed
        INTEGER,
      frameRelayLocalManagementProtocol
        INTEGER,
      frameRelayLinkPollingTimer
        INTEGER,
      frameRelayFullStatusPollingCount
        INTEGER,
      frameRelayT1Timer
        INTEGER,
      frameRelayT2Timer
        INTEGER,
      frameRelayTiTimer
        INTEGER,
      frameRelayRxWindowSize
        INTEGER,
      frameRelayTxWindowSize
        INTEGER,
      frameRelayMaxRetries
        INTEGER,
      frameRelayNAUName
        DisplayString,
      frameRelayVirtualMACAddress
        PhysAddress,
      frameRelayVirtualRingNumber
        INTEGER,
      frameRelayVirtualBridgeNumber
        INTEGER,
      frameRelayIPAddress
        IpAddress,
      frameRelayNetworkMask
        IpAddress,
      frameRelayDefaultGatewayAddress
        IpAddress,
      frameRelaySessSwitchThreshold
        INTEGER,
      frameRelaySwitchedBackup
        INTEGER,
      frameRelaySwitchedLineWaitTimer
        INTEGER,
      frameRelayDedLineWaitTimer
        INTEGER,
      frameRelayCommittedBurst
        INTEGER,
      frameRelayExcessBurst
        INTEGER,
      frameRelayBridgingProtocol
        INTEGER,
      frameRelayProxyARP
        INTEGER,
      frameRelaySecondDefaultGatewayAddress
        IpAddress,
      frameRelayAlternateIPAddress
        IpAddress,
      frameRelayAlternateNetmask
        IpAddress,
      frameRelayLLC2FrameFormat
        INTEGER,
      frameRelayMultiflagSeparation
        INTEGER,
      frameRelayRestrictTerminateSessUsage
        INTEGER,
      frameRelayRIPUpdtTimer
        INTEGER,
      frameRelayRIPAge
        INTEGER,
      frameRelaySAPUpdtTimer
        INTEGER,
      frameRelaySAPAge
        INTEGER,
      frameRelayRSM
        INTEGER,
      frameRelayARP
        INTEGER,
      frameRelayCTS
        INTEGER,
      frameRelayDCD
        INTEGER,
      frameRelayDSR
        INTEGER,
      frameRelayDTR
        INTEGER,
      frameRelayRTS
        INTEGER,
      frameRelayReturnClock
        INTEGER
    }

  frameRelayConfigPortIndex  OBJECT-TYPE
    SYNTAX  INTEGER
    ACCESS  read-only
    STATUS  mandatory
    DESCRIPTION
      "The port number that uniquely identifies
      this port."
    ::= { frameRelayConfigEntry 1 }

  frameRelayPortType  OBJECT-TYPE
    SYNTAX  INTEGER {
      frame-relay-type(19),
      frame-relay-dialbackup-type(20)
      }
    ACCESS  read-only
    STATUS  mandatory
    DESCRIPTION
      "The Frame Relay port type."
    ::= { frameRelayConfigEntry 2 }

  frameRelayInitState  OBJECT-TYPE
    SYNTAX  INTEGER {
      in-service(1),
      out-of-service(2)
      }
    ACCESS  read-only
    STATUS  mandatory
    DESCRIPTION
      "The initial state of the Frame Relay port.

      If configured for 'in-service', then the Frame Relay port will
      be brougt up automatically when the unit is powered
      up.

      If configured for 'out-of-service', then the Frame Relay port must
      be manually enabled by operator intervention (i.e.
      enable command must be sent).

      The default value is 'enabled'."
    ::= { frameRelayConfigEntry 3 }

  frameRelayClocking  OBJECT-TYPE
    SYNTAX  INTEGER {
      external(1),
      internal(2),
      x21-external(3),
      x21-internal(4)
      }
    ACCESS  read-only
    STATUS  mandatory
    DESCRIPTION
      "Clocking source for this port.
      Setting 'internal' will cause the
      port to emulate a physical DCE, and setting
      external will cause the port to emulate a
      physical DTE.
      X21 External and Internal are used (with the
      proper external adapter) to support X.21 Leased
      Line operation for RS-422/RS-530 (25 pin balanced)
      interfaces.  X21 operation is not supported for
      boards that operate RS-232 or V.35.
      The default value for this field is 'external'."
    ::= { frameRelayConfigEntry 4 }

  frameRelaySpeed  OBJECT-TYPE
    SYNTAX  INTEGER {
      speed1200(12),
      speed2000(20),
      speed2400(24),
      speed3600(36),
      speed4800(48),
      speed7200(72),
      speed9600(96),
      speed14400(144),
      speed19200(192),
      speed28800(288),
      speed48000(480),
      speed56000(560),
      speed64000(640),
      speed128000(1280),
      speed256000(2560),
      speed512000(5120),
      speed102400(10240),
      speed154400(15440),
      speed204800(20480)
      }
    ACCESS  read-only
    STATUS  mandatory
    DESCRIPTION
      "The ports speed in bits per second.
       The default value is 9600 bits per second.
       Speeds higher than 19200 are not supported on
       RS-232 port Sync products (must be V.35 or RS-422)."
    ::= { frameRelayConfigEntry 5 }

  frameRelayLocalManagementProtocol OBJECT-TYPE
    SYNTAX  INTEGER {
      annexD(1),
      lmi(2),
      annexA(3)
      }
    ACCESS  read-only
    STATUS  mandatory
    DESCRIPTION
      "The ports management protocol type.
      Annex D = ANSI T1.617 Annex D
      LMI = Frame Relay Manufacturers LMI
      The default value is Annex D."
    ::= { frameRelayConfigEntry 6 }

  frameRelayLinkPollingTimer OBJECT-TYPE
    SYNTAX  INTEGER (5..30)
    ACCESS  read-only
    STATUS  mandatory
    DESCRIPTION
      "Measured in seconds, intervals of 5
      T391 - Annex D
      nT1  - LMI
      The default value for this field is 5 seconds."
    ::= { frameRelayConfigEntry 7 }

  frameRelayFullStatusPollingCount OBJECT-TYPE
    SYNTAX  INTEGER (1..255)
    ACCESS  read-only
    STATUS  mandatory
    DESCRIPTION
      "The number of polls that a full status poll is
      issued.
      N391 - Annex D
      nT1  - LMI
      The default value for this field is 6."
    ::= { frameRelayConfigEntry 8 }

  frameRelayT1Timer  OBJECT-TYPE
    SYNTAX  INTEGER (1..25)
    ACCESS  read-only
    STATUS  mandatory
    DESCRIPTION
      "The default LLC T1 timer value in seconds.
      T1 should be greater than T2 and less than Ti.
      Currently supported values are 1 to 25 seconds.
      The default value for this field is 3 seconds."
    ::= { frameRelayConfigEntry 9 }

  frameRelayT2Timer  OBJECT-TYPE
    SYNTAX  INTEGER (0..50)
    ACCESS  read-only
    STATUS  mandatory
    DESCRIPTION
      "The default LLC T2 timer value in tenths of seconds.
      If configured for 0 then the T2 timer is disabled
      and an RR frame will be sent for every I frame
      received.
      Current supported values are 0 and 2-50.
      T2 should be less than T1.
      The default value for this field is 0 (disabled)."
    ::= { frameRelayConfigEntry 10 }

  frameRelayTiTimer  OBJECT-TYPE
    SYNTAX  INTEGER (2..50)
    ACCESS  read-only
    STATUS  mandatory
    DESCRIPTION
      "The default LLC Ti (inactivity) timer value
      in seconds.
      Ti should be greater than T1.
      Currently supported values are 2 to 50 seconds.
      The default value for this field is 30 seconds."
    ::= { frameRelayConfigEntry 11 }

  frameRelayRxWindowSize OBJECT-TYPE
    SYNTAX  INTEGER (1..15)
    ACCESS  read-only
    STATUS  mandatory
    DESCRIPTION
      "The default LLC receive window (N3) size.
      Note that this is not the same receive window as
      defined in IEEE 802.2 LLC.  This is N3 which is the
      number of I frames received before an RR frame is
      sent (defined as N3 in IEEE 802.2 LLC).
      Current allowable values are 1-7.
      The default value for this field is 7."
    ::= { frameRelayConfigEntry 12 }

  frameRelayTxWindowSize OBJECT-TYPE
    SYNTAX  INTEGER (1..15)
    ACCESS  read-only
    STATUS  mandatory
    DESCRIPTION
      "The defalut LLC transmit window size.
      Current allowable values are 1-7.
      The default value for this field is 7."
    ::= { frameRelayConfigEntry 13 }

  frameRelayMaxRetries  OBJECT-TYPE
    SYNTAX  INTEGER (1..20)
    ACCESS  read-only
    STATUS  mandatory
    DESCRIPTION
      "The default LLC maximum number of retries (N2 value).
      The default value for this field is 15."
    ::= { frameRelayConfigEntry 14 }

  frameRelayNAUName   OBJECT-TYPE
    SYNTAX  DisplayString (SIZE(1..8))
    ACCESS  read-only
    STATUS  mandatory
    DESCRIPTION
      "The NAU name of this port.
      The default value for this field is all blank
      (filled with ASCII space 0x20 characters)."
    ::= { frameRelayConfigEntry 15 }

  frameRelayVirtualMACAddress OBJECT-TYPE
    SYNTAX  PhysAddress
    ACCESS  read-only
    STATUS  mandatory
    DESCRIPTION
      "The F/R WAN is treated as a token ring. This address is
      used for communication with other bridges in the
      network."
    ::= { frameRelayConfigEntry 16 }

  frameRelayVirtualRingNumber OBJECT-TYPE
    SYNTAX  INTEGER (1..4095)
    ACCESS  read-only
    STATUS  mandatory
    DESCRIPTION
      "The F/R WAN is treated as a token ring. This is the ring
      number for the F/R network to which the port is attached.
      It must be a unique ring number in the network. This value
      is configured in hex from 0 to FFF.
      The default value for this field is 1."
    ::= { frameRelayConfigEntry 17 }

  frameRelayVirtualBridgeNumber OBJECT-TYPE
    SYNTAX  INTEGER (1..15)
    ACCESS  read-only
    STATUS  mandatory
    DESCRIPTION
      "The F/R WAN is treated as a token ring. This variable only
      has significance if more than 1 F/R port is configured.
      The default value for this field is 1."
    ::= { frameRelayConfigEntry 18 }

  frameRelayIPAddress OBJECT-TYPE
    SYNTAX  IpAddress
    ACCESS  read-only
    STATUS  mandatory
    DESCRIPTION
      "This is the IP Address of this interface."
    ::= { frameRelayConfigEntry 19 }

  frameRelayNetworkMask OBJECT-TYPE
    SYNTAX  IpAddress
    ACCESS  read-only
    STATUS  mandatory
    DESCRIPTION
      "This is the network mask to be used on this
      interface."
    ::= { frameRelayConfigEntry 20 }

  frameRelayDefaultGatewayAddress OBJECT-TYPE
    SYNTAX  IpAddress

    ACCESS  read-only
    STATUS  mandatory
    DESCRIPTION
      "Default gateway address to be used when sending
      responses on this interface."
    ::= { frameRelayConfigEntry 21 }

  frameRelaySessSwitchThreshold  OBJECT-TYPE
    SYNTAX  INTEGER (0..15)
    ACCESS  read-only
    STATUS  mandatory
    DESCRIPTION
      "Describes the session switch threshold for a session
      to switch between eVR and pVR.  The value represents
      the LLC time-out occurrence for any session on this
      port.  If one session has the configured number of
      time-outs, all sessions using that PVC are switched
      between eVR and pVR.  Sessions that do not have a pVR
      are terminated."
    ::= { frameRelayConfigEntry 22 }


  frameRelaySwitchedBackup  OBJECT-TYPE
    SYNTAX  INTEGER {
      none (1),
      racal-dtr-initiated(2)
      }
    ACCESS  read-only
    STATUS  mandatory
    DESCRIPTION
      "Defines the switched backup protocol used for dial
      backup.  The range of this parameter is NONE or RACAL
      DTR-initiated.  The default value is NONE."
    ::= { frameRelayConfigEntry 23 }

  frameRelaySwitchedLineWaitTimer  OBJECT-TYPE
    SYNTAX  INTEGER (1..60)
    ACCESS  read-only
    STATUS  mandatory
    DESCRIPTION
      "This parameter defines the maximum amount of time
      the FrameNode waits for the DAP to establish a dial
      connection before switching back to the dedicated line.
      This parameter is required because the DAP does not
      notify the FrameNode as to whether the dial backup
      connection was successful or not.  This parameter, in
      concert with a high level protocol, helps determine
      whether or not the connection was successful.
      This parameter is expressed in minutes.  The range of
      this parameter is from 1 minute to 60 minutes.  The
      default value is  5 minutes."
    ::= { frameRelayConfigEntry 24 }

  frameRelayDedLineWaitTimer  OBJECT-TYPE
    SYNTAX  INTEGER (10..120)
    ACCESS  read-only
    STATUS  mandatory
    DESCRIPTION
      "The FCC regulation for Autodialers requires that an
      Autodialer waits between successive dial operations.
      This parameter satisfies the FCC requirements.  It
      controls the maximum time the FrameNode waits before
      initiating another dial restoral operation if the previous
      operation fails.   The timer starts when DTR is
      lowered. DTR is raised again upon expiration of the
      timer.  This parameter is expressed in minutes.  Its range
      is from 10 minutes to 120 minutes with a one minute
      resolution.  The default value it 10 minutes."
    ::= { frameRelayConfigEntry 25 }

  frameRelayCommittedBurst OBJECT-TYPE
    SYNTAX   INTEGER
    ACCESS   read-write
    STATUS   mandatory
    DESCRIPTION
       "This parameter specifies the maximum number of bits, during time
        interval Tc, the network agrees to accept under normal conditions.
        This parameter must match the configured value for the network.
        The value of this parameter can not be greater that the line speed.

        The range of the parameter is 1Kbits to 2048Kbits.  The default value
        equals the line speed.   However, this value depends on the
        Measurement Period Tc and the line speed.

        The value is expressed in Kbits."

    ::= { frameRelayConfigEntry 26 }

  frameRelayExcessBurst OBJECT-TYPE
    SYNTAX   INTEGER
    ACCESS   read-write
    STATUS   mandatory
    DESCRIPTION
       "This is the maximum number of uncommitted bits, during time
       interval Tc, the network accepts above the committed burst size Bc.
       When the Excess burst Governor is configured to YES, the FrameNode
       tries to limit the throughput to the Bc + Be bits in the Time Period Tc.
       The default value of this parameter is 0.  The range is from 0K to
       2048K.  However, the value depends on the Measurement Period Tc and
       the speed of the line.

       The value is expressed in Kbits."

    ::= { frameRelayConfigEntry 27 }

  frameRelayBridgingProtocol OBJECT-TYPE
    SYNTAX   INTEGER {
        srb(1),
        tbr(2),
        both(3)
        }
    ACCESS   read-write
    STATUS   mandatory
    DESCRIPTION
       "This parameter specifies the bridging protocol to be used over
       Frame Relay link.  This parameter has no effect if bridging
       is not turned on.  The range of this parameter is SRB (source
       route bridging), TBR(transparent bridging) or BOTH.

       The value is BOTH."

    ::= { frameRelayConfigEntry 28 }

  frameRelayProxyARP OBJECT-TYPE
    SYNTAX   INTEGER {
      enable(1),
      disable(2)
        }
    ACCESS   read-write
    STATUS   mandatory
    DESCRIPTION
       "This parameter defines whether PROXY ARP is enabled for F/R
       attached devices or not.  Range of this parameter is ENABLED
       or DISABLED.

       The value is 'DISABLED'."

    ::= { frameRelayConfigEntry 29 }

  frameRelaySecondDefaultGatewayAddress OBJECT-TYPE
    SYNTAX  IpAddress
    ACCESS  read-only
    STATUS  mandatory
    DESCRIPTION
      "Second Default gateway address to be used when sending
      responses on this interface."
    ::= { frameRelayConfigEntry 30 }

  frameRelayAlternateIPAddress  OBJECT-TYPE
    SYNTAX  IpAddress
    ACCESS  read-only
    STATUS  mandatory
    DESCRIPTION
      "This is the Alternate IP Address for single
      port dial up connection."
    ::= { frameRelayConfigEntry 31 }

  frameRelayAlternateNetmask OBJECT-TYPE
    SYNTAX  IpAddress
    ACCESS  read-only
    STATUS  mandatory
    DESCRIPTION
      "This is the Alternate network mask for IP
      for single port dial up connecton."
    ::= { frameRelayConfigEntry 32 }

  frameRelayLLC2FrameFormat OBJECT-TYPE
    SYNTAX   INTEGER {
        tokenRing(1),
        ethernetVersiontwo(2),
        iEEEeightotwothree(3),
        all(4)
        }
    ACCESS   read-write
    STATUS   mandatory
    DESCRIPTION
       "This parameter specifies the LLC2 frame format to be used
       over Frame Relay link.  The range of this parameter is Token
       Ring, Ethernet Version 2, IEEE 802.3 or  ALL.

       The value is ALL."

    ::= { frameRelayConfigEntry 33 }

  frameRelayMultiflagSeparation OBJECT-TYPE
    SYNTAX   INTEGER {
      yes(1),
      no(2)
        }
    ACCESS   read-write
    STATUS   mandatory
    DESCRIPTION
       "This parameter specifies whether the unit will insert more
       than one flag between frames.  The range of this parameter is
       yes and no.

       The value is 'no'."

    ::= { frameRelayConfigEntry 34 }

  frameRelayRestrictTerminateSessUsage OBJECT-TYPE
    SYNTAX   INTEGER {
      no(1),
      spanningTree(2)
        }
    ACCESS   read-write
    STATUS   mandatory
    DESCRIPTION
       "This parameter specifies whether terminated sessions are to
       follow spanning tree states or not over Frame Relay Link.
       The range of this parameter is No and SpanningTree.

       The value is 'no'."

    ::= { frameRelayConfigEntry 35 }

  frameRelayRIPUpdtTimer   OBJECT-TYPE
    SYNTAX  INTEGER (10..180)
    ACCESS  read-only
    STATUS  mandatory
    DESCRIPTION
      "Defines frequency at which the RIP packets are sent
     over this interface.  The range of this parameter is
     from 10 seconds to 180 seconds. A value of 0 implies
     no RIP is sent over this interface.

     Default value is 60 seconds"
    ::= { frameRelayConfigEntry 36 }

  frameRelayRIPAge   OBJECT-TYPE
    SYNTAX  INTEGER (40..540)
    ACCESS  read-only
    STATUS  mandatory
    DESCRIPTION
      "Defines frequency at which the learned RIP entries are
     removed if not corresponding RIP update is received.  The
     range of this parameter is from 40 seconds to 540 seconds.

     Default value is 180 seconds"
    ::= { frameRelayConfigEntry 37 }

  frameRelaySAPUpdtTimer   OBJECT-TYPE
    SYNTAX  INTEGER (0..180)
    ACCESS  read-only
    STATUS  mandatory
    DESCRIPTION
      "Defines frequency at which the SAP packets are sent
     over this interface.  The range of this parameter is
     from 10 seconds to 180 seconds.  A value of 0 implies
     that no SAP broadcasts are sent over this interface.

     Default value is 60 seconds"
    ::= { frameRelayConfigEntry 38 }

  frameRelaySAPAge   OBJECT-TYPE
    SYNTAX  INTEGER (40..720)
    ACCESS  read-only
    STATUS  mandatory
    DESCRIPTION
      "Defines frequency at which the learned SAP entries are
     removed if not corresponding SAP update is received.  The
     range of this parameter is from 40 seconds to 720 seconds.

     Default value is 180 seconds"
    ::= { frameRelayConfigEntry 39 }

  frameRelayRSM   OBJECT-TYPE
    SYNTAX  INTEGER {
      yes (1),
      no  (2)
      }
    ACCESS  read-only
    STATUS  mandatory
    DESCRIPTION
      "The Routing Summary Information parameter indicates whether
       the routing summary information should be generated in the
       RIP on that interface. If RSM is set to NO, RIP will
       broadcast subnet information as it is defined in the
       routing table.

     Default value is 'NO'"
    ::= { frameRelayConfigEntry 40 }

  frameRelayARP   OBJECT-TYPE
    SYNTAX  INTEGER {
        auto(1),
        inverseArp(2),
        routedArp(3),
        tokenRing(4),
        ethernetVersiontwo(5),
        iEEEeightotwothree(6),
        none(7)
      }
    ACCESS  read-only
    STATUS  mandatory
    DESCRIPTION
      "The ARP parameter indicates what format of ARP should be
       generated.

     Default value is 'Auto'"
    ::= { frameRelayConfigEntry 41 }

  frameRelayCTS  OBJECT-TYPE
    SYNTAX  INTEGER {
      yes(1),
      no(2)
      }
    ACCESS  read-only
    STATUS  mandatory
    DESCRIPTION
      "Defines whether CTS is an input signal used to
      determine the port status. This parameter is applicable
      if clocking is set to external.  For internal clocking
      the parameter is ignored and DCD is asserted when port
      is enabled. The range is yes and no.

      The default value is 'No'."
    ::= { frameRelayConfigEntry 42 }

  frameRelayDCD  OBJECT-TYPE
    SYNTAX  INTEGER {
      yes(1),
      no(2)
      }
    ACCESS  read-only
    STATUS  mandatory
    DESCRIPTION
      "Defines whether DCD is required as input signal
      or ignored. This parameter is applicable if the
      clocking is set to external.  For internal clocking
      the parameter is ignored and DCD is asserted when port
      is enabled. The range is yes and no.

      The default value is 'yes'."
    ::= { frameRelayConfigEntry 43 }

  frameRelayDSR  OBJECT-TYPE
    SYNTAX  INTEGER {
      yes(1),
      no(2)
      }
    ACCESS  read-only
    STATUS  mandatory
    DESCRIPTION
      "Defines whether DSR is required as input signal
      or ignored. This parameter is applicable if the
      clocking is set to external.  For internal clocking
      the parameter is ignored and DSR is asserted when port
      is enabled. The range is yes and no.

      The default value is 'yes'."
    ::= { frameRelayConfigEntry 44 }

  frameRelayDTR  OBJECT-TYPE
    SYNTAX  INTEGER {
      yes(1),
      no(2)
      }
    ACCESS  read-only
    STATUS  mandatory
    DESCRIPTION
      "Defines whether DTR is required as input signal
      or ignored. This parameter is applicable if the
      clocking is set to internal.  For external clocking
      the parameter is ignored and DTR is asserted when port
      is enabled. The range is yes and no.

      The default value is 'yes'."
    ::= { frameRelayConfigEntry 45 }

  frameRelayRTS  OBJECT-TYPE
    SYNTAX  INTEGER {
      yes(1),
      no(2)
      }
    ACCESS  read-only
    STATUS  mandatory
    DESCRIPTION
      "Defines whether RTS is an input signal to determine
      the port status. This parameter is applicable if the
      clocking is set to internal.  For external clocking
      the parameter is ignored and RTS is asserted when port
      is enabled. The range is yes and no.

      The default value is 'No'."
    ::= { frameRelayConfigEntry 46 }

  frameRelayReturnClock  OBJECT-TYPE
    SYNTAX  INTEGER {
      yes(1),
      no(2),
      default(3)
      }
    ACCESS  read-only
    STATUS  mandatory
    DESCRIPTION
      "Defines whether Return Clock (SCTE) is available as
      input signal or ignored. This parameter is applicable
      if the clocking is set to internal. For external clocking
      the parameter is ignored. The range is yes and no.

      The default value is 'yes'."
    ::= { frameRelayConfigEntry 47 }

  --
  -- The Frame Relay Port Statistics Table:
  --

  frameRelayStatsTable  OBJECT-TYPE
    SYNTAX SEQUENCE OF FrameRelayStatsEntry
    ACCESS  not-accessible
    STATUS  mandatory
    DESCRIPTION
      "A table of Frame Relay information."
    ::= { lineFrameRelayGroup 2 }

  frameRelayStatsEntry  OBJECT-TYPE
    SYNTAX  FrameRelayStatsEntry
    ACCESS  not-accessible
    STATUS  mandatory
    DESCRIPTION
      "An entry consisting of port information for a
       particular Frame Relay port."
    INDEX { frameRelayStatsPortIndex }
    ::= { frameRelayStatsTable 1 }

  FrameRelayStatsEntry ::=
    SEQUENCE {
      frameRelayStatsPortIndex
        INTEGER,
      frameRelayInOctets
        Counter,
      frameRelayOutOctets
        Counter,
      frameRelaySampleDuration
        INTEGER,
      frameRelayOverruns
        Counter,
      frameRelayCRCErrors
        Counter,
      frameRelayRecvAborts
        Counter,
      frameRelayTxDe
        Counter,
      frameRelayRxDe
        Counter,
      frameRelaySwitchedAttempts
        Counter,
      frameRelaySwitchedAttemptsSuccessful
        Counter

    }

  frameRelayStatsPortIndex OBJECT-TYPE
    SYNTAX  INTEGER
    ACCESS  read-only
    STATUS  mandatory
    DESCRIPTION
      "The port number that uniquely identifies
      this Frame Relay port."
    ::= { frameRelayStatsEntry 1 }

  frameRelayInOctets OBJECT-TYPE
    SYNTAX  Counter
    ACCESS  read-only
    STATUS  mandatory
    DESCRIPTION
      "The number of bytes received inclusive
      of all valid bytes in the frame relay
      frame except for the CRC field (frame
      relay header included)."
    ::= { frameRelayStatsEntry 2 }

  frameRelayOutOctets OBJECT-TYPE
    SYNTAX  Counter
    ACCESS  read-only
    STATUS  mandatory
    DESCRIPTION
      "The number of bytes transmitted inclusive
      of all bytes in the frame relay
      frame except for the CRC field (frame
      relay header included)."
    ::= { frameRelayStatsEntry 3 }

  frameRelaySampleDuration OBJECT-TYPE
    SYNTAX  INTEGER
    ACCESS  read-only
    STATUS  mandatory
    DESCRIPTION
      "The sample duration in seconds for
      Frame Relay Statistics for this port."
    ::= { frameRelayStatsEntry 4 }

  frameRelayOverruns  OBJECT-TYPE
    SYNTAX  Counter
    ACCESS  read-only
    STATUS  mandatory
    DESCRIPTION
      "The number of receiver overruns."
    ::= { frameRelayStatsEntry 5 }

  frameRelayCRCErrors  OBJECT-TYPE
    SYNTAX  Counter
    ACCESS  read-only
    STATUS  mandatory
    DESCRIPTION
      "The number of received CRC errors."
    ::= { frameRelayStatsEntry 6 }

  frameRelayRecvAborts  OBJECT-TYPE
    SYNTAX  Counter
    ACCESS  read-only
    STATUS  mandatory
    DESCRIPTION
      "The number of received frame aborts
      received."
    ::= { frameRelayStatsEntry 7 }


  frameRelayTxDe  OBJECT-TYPE
    SYNTAX  Counter
    ACCESS  read-only
    STATUS  mandatory
    DESCRIPTION
      "Total number of frames sent with the DE bit."
    ::= { frameRelayStatsEntry 8 }

  frameRelayRxDe  OBJECT-TYPE
    SYNTAX  Counter
    ACCESS  read-only
    STATUS  mandatory
    DESCRIPTION
      "Total number of frames received with the DE bit."
    ::= { frameRelayStatsEntry 9 }

  frameRelaySwitchedAttempts  OBJECT-TYPE
    SYNTAX  Counter
    ACCESS  read-only
    STATUS  mandatory
    DESCRIPTION
      "The total number of times a switched backup is
      attempted."
    ::= { frameRelayStatsEntry 10 }

  frameRelaySwitchedAttemptsSuccessful  OBJECT-TYPE
    SYNTAX  Counter
    ACCESS  read-only
    STATUS  mandatory
    DESCRIPTION
      "The total number of times switched backup attempts
      were successful."
    ::= { frameRelayStatsEntry 11 }


  --
  --   Sync Circuit Table Extension
  --
  --

    frExtCircuitTable OBJECT-TYPE
      SYNTAX   SEQUENCE OF FrExtCircuitEntry
      ACCESS   not-accessible
      STATUS   mandatory
      DESCRIPTION
         "A table containing information about specific Data
         Link Connection Identifiers and corresponding virtual
         circuits."
      ::= { nodeFrCirGroup 1 }

    frExtCircuitEntry OBJECT-TYPE
      SYNTAX   FrExtCircuitEntry
      ACCESS   not-accessible
      STATUS   mandatory
      DESCRIPTION
         "The information regarding a single  Data  Link
         Connection Identifier."
      INDEX { frExtCircuitIfIndex, frExtCircuitDlci }
      ::= { frExtCircuitTable 1 }

    FrExtCircuitEntry ::=
      SEQUENCE {
        frExtCircuitIfIndex
            INTEGER,
        frExtCircuitDlci
            INTEGER,
        frExtCircuitStatusIgnored
            INTEGER,
        frExtCircuitStatusAcknowledged
            INTEGER,
        frExtCircuitPartnerId
            DisplayString,
        frExtCircuitTxDe
            Counter,
        frExtCircuitRxDe
            Counter,
        frExtCircuitMinBits
            Gauge,
        frExtCircuitMaxBits
            Gauge,
        frExtCircuitQOctets
            Counter

    }

    frExtCircuitIfIndex OBJECT-TYPE
      SYNTAX   INTEGER
      ACCESS   read-only
      STATUS   mandatory
      DESCRIPTION
        "The ifIndex Value of the ifEntry this  virtual
        circuit is layered onto."
      ::= { frExtCircuitEntry 1 }

    frExtCircuitDlci OBJECT-TYPE
      SYNTAX   INTEGER
      ACCESS   read-only
      STATUS   mandatory
      DESCRIPTION
        "The Data Link Connection Identifier  for  this
        virtual circuit."
      REFERENCE
        "Draft American National  Standard  T1.618-1991,
        Section 3.3.6"
      ::= { frExtCircuitEntry 2 }

    frExtCircuitStatusIgnored OBJECT-TYPE
      SYNTAX   INTEGER {
        yes (1),
        no  (2)
        }
      ACCESS   read-write
      STATUS   mandatory
      DESCRIPTION
        "This field is used for consolidating status of the
        unit. The status of this circuit is not put into
        consideration when consolidating status of the
        unit if this field is set to yes."
      ::= { frExtCircuitEntry 3 }

    frExtCircuitStatusAcknowledged OBJECT-TYPE
      SYNTAX   INTEGER {
        yes (1),
        no (2)
        }
      ACCESS   read-write
      STATUS   mandatory
      DESCRIPTION
        "This field is used for consolidating status of the
        unit. When this field is set to acknowledge, unit will
        re-consolidate its status without putting the status
        of this circuit into consideration. Subseqent status
        change of the circuit will cause the unit to include it
        in computing the status of the unit. Setting this
        value to no has no effect."
      ::= { frExtCircuitEntry 4 }

    frExtCircuitPartnerId  OBJECT-TYPE
      SYNTAX  DisplayString (SIZE(1..8))
      ACCESS  read-only
      STATUS  mandatory
      DESCRIPTION
        "This is the unit id of the FrameNode at the other
        end of the Frame relay PVC. It consists of a 1 to 8 octets
        right justified case-sensitive ASCII field which
        uniquely identifies the unit.
        If the unit at the other end of the Frame Relay PVC is
        not a Sync Research FrameNode, or and OEM equipment
        NON-FN is returned for this object."
      ::= { frExtCircuitEntry 5 }


    frExtCircuitTxDe  OBJECT-TYPE
      SYNTAX  Counter
      ACCESS  read-only
      STATUS  mandatory
      DESCRIPTION
        "Total number of frames sent with DE bit for this PVC."
      ::= { frExtCircuitEntry 6 }


    frExtCircuitRxDe  OBJECT-TYPE
      SYNTAX  Counter
      ACCESS  read-only
      STATUS  mandatory
      DESCRIPTION
        "Total number of frames received with the DE bit for
        this PVC."
      ::= { frExtCircuitEntry 7 }

    frExtCircuitMinBits  OBJECT-TYPE
      SYNTAX  Gauge
      ACCESS  read-only
      STATUS  mandatory
      DESCRIPTION
        "Minimum number of bits transmitted in Time Period
        Tc for this PVC."
      ::= { frExtCircuitEntry 8 }

    frExtCircuitMaxBits  OBJECT-TYPE
      SYNTAX  Gauge
      ACCESS  read-only
      STATUS  mandatory
      DESCRIPTION
        "Maximum number of bits transmitted in Time Period
        Tc for this PVC."
      ::= { frExtCircuitEntry 9 }

    frExtCircuitQOctets  OBJECT-TYPE
      SYNTAX  Counter
      ACCESS  read-only
      STATUS  mandatory
      DESCRIPTION
        "Number of octets queued for transmission because
        the maximum burst rate was achieved in Tc.  These
        are the number of octets that had transmission delay
        until next excess burst cycle Tc."
      ::= { frExtCircuitEntry 10 }


  --
  -- The Async Port Level Group
  --
  --
  -- The Async Configuration Table:
  --

  asyncConfigTable OBJECT-TYPE
    SYNTAX SEQUENCE OF AsyncConfigEntry
    ACCESS  not-accessible
    STATUS  mandatory
    DESCRIPTION
      "A table of Async port information."
    ::= { lineAsyncGroup 1 }

  asyncConfigEntry OBJECT-TYPE
    SYNTAX  AsyncConfigEntry
    ACCESS  not-accessible
    STATUS  mandatory
    DESCRIPTION
      "An entry consisting of port information for a
       particular async port."
    INDEX { asyncConfigPortIndex }
    ::= { asyncConfigTable 1 }

  AsyncConfigEntry ::=
    SEQUENCE {
      asyncConfigPortIndex
        INTEGER,
      asyncConfigType
        INTEGER,
      asyncNAUName
        DisplayString,
      asyncInitState
        INTEGER,
      asyncCarrier
        INTEGER,
      asyncSpeed
        INTEGER,
      asyncPhysicalType
        INTEGER,
      asyncStopBits
        INTEGER,
      asyncParity
        INTEGER,
      asyncDataBits
        INTEGER,
      asyncIdleTimer
        INTEGER,
      asyncTxFrameGap
        INTEGER,
      asyncRxForwardingCount
        INTEGER,
      asyncEiaSignalForwarding
        INTEGER,
      asyncAddressOffset
        INTEGER,
      asyncRTC
        OCTET STRING,
      asyncCTS
        INTEGER,
      asyncDCD
        INTEGER,
      asyncDSR
        INTEGER,
      asyncDTR
        INTEGER,
      asyncRTS
        INTEGER,
      asyncReturnClock
        INTEGER,
      asyncOrt
        INTEGER
    }

  asyncConfigPortIndex  OBJECT-TYPE
    SYNTAX  INTEGER
    ACCESS  read-only
    STATUS  mandatory
    DESCRIPTION
      "The port number that uniquely identifies
      this port."
    ::= { asyncConfigEntry 1 }

  asyncConfigType  OBJECT-TYPE
    SYNTAX  INTEGER {
      hasc-type(9),
      tasc-type(10)
      }
    ACCESS  read-only
    STATUS  mandatory
    DESCRIPTION
      "The port type.
      HASC (Host Async) ports are for attaching to an
                        Async Alarm Central Processor.
      TASC ports (Terminal Async) ports are for attaching
                        to Alarm Controllers."

    ::= { asyncConfigEntry 2 }

  asyncNAUName   OBJECT-TYPE
    SYNTAX  DisplayString (SIZE(1..8))
    ACCESS  read-only
    STATUS  mandatory
    DESCRIPTION
      "The NAU name of this port.
      The default value for this field is all blank
      (filled with ASCII space 0x20 characters)."
    ::= { asyncConfigEntry 3 }

  asyncInitState  OBJECT-TYPE
    SYNTAX  INTEGER {
      in-service(1),
      out-of-service(2)
      }
    ACCESS  read-only
    STATUS  mandatory
    DESCRIPTION
      "The initial state of the async port.

      If configured for 'in-service', then the Async port will
      be brougt up automattically when the unit is powered
      up.

      If configured for 'out-of-service', then the Async port must
      be manually enabled by operator intervention (i.e.
      enable command must be sent).

      The default value is 'enabled'."
    ::= { asyncConfigEntry 4 }

  asyncCarrier  OBJECT-TYPE
    SYNTAX  INTEGER {
      constant(1),
      switched(2)
      }
    ACCESS  read-only
    STATUS  mandatory
    DESCRIPTION
      "This field indicates whether Carrier (a.k.a. CD or
      DCD, RS-232 pin 8) is constant or switched for
      DCE devices (internally clocked), or Request To
      Send (a.k.a. RTS, RS-232 pin 4) is constant or
      switched.

      The default value for this parameter is 'constant'."
    ::= { asyncConfigEntry 5 }

  asyncSpeed  OBJECT-TYPE
    SYNTAX  INTEGER {
      speed75(75),
      speed150(150),
      speed300(300),
      speed600(600),
      speed1200(1200),
      speed2400(2400),
      speed4800(4800),
      speed9600(9600),
      speed19200(19200)
      }
    ACCESS  read-only
    STATUS  mandatory
    DESCRIPTION
      "The ports speed in bits per second.
      The default value is 300 bits per second.
      Speeds higher than 19200 are not supported."
    ::= { asyncConfigEntry 6 }

  asyncPhysicalType  OBJECT-TYPE
    SYNTAX  INTEGER {
      dte(1),
      dce(2)
      }
    ACCESS  read-only
    STATUS  mandatory
    DESCRIPTION
      "Physical RS-232 type emulated by the port.
      The default value is 2 or DCE."
    ::= { asyncConfigEntry 7 }

  asyncStopBits           OBJECT-TYPE
    SYNTAX  INTEGER {
      sto1(1),
      sto1-5(2),
      sto2(3)
      }
    ACCESS  read-only
    STATUS  mandatory
    DESCRIPTION
      "Number of stop bits generated for transmit characters
      (received characters may have any number of bits
      regardless of the configuration).
      The default value is 1."
    ::= { asyncConfigEntry 8 }

  asyncParity  OBJECT-TYPE
    SYNTAX  INTEGER {
      odd(1),
      even(2),
      none(3)
      }
    ACCESS  read-only
    STATUS  mandatory
    DESCRIPTION
      "Parity type generated for transmit characters and
      checked for receive characters. If ODD or EVEN, then
      if a character is received with invalid parity, it is
      discarded and the message once completely received is
      also discarded (i.e. not forwarded to the network).
      If NONE, then no parity bit is expected within the
      character or generated to the line.
      The default value is 1 or NONE."
    ::= { asyncConfigEntry 9 }

  asyncDataBits  OBJECT-TYPE
    SYNTAX  INTEGER (5..8)
    ACCESS  read-only
    STATUS  mandatory
    DESCRIPTION
      "Number of data bits (not including the parity bit).
       The default value is 8."
    ::= { asyncConfigEntry 10 }

  asyncIdleTimer  OBJECT-TYPE
    SYNTAX  INTEGER (0..5000)
    ACCESS  read-only
    STATUS  mandatory
    DESCRIPTION
      "The idle timer is amount of time (in milliseconds)
      used to determine when a complete message has been
      received from the line.  If configured as 0, then
      this timer is disabled and the message will be sent
      to the network only when the RX forwarding count is
      reached. If configured greater than 0, then the timer
      must be configured for a time longer than the time it
      takes to receive one character,  otherwise the timer
      will not function properly.
      The default value is 40."
    ::= { asyncConfigEntry 11 }

  asyncTxFrameGap  OBJECT-TYPE
    SYNTAX  INTEGER (0..5000)
    ACCESS  read-only
    STATUS  mandatory
    DESCRIPTION
      "The TX frame gap is analogous to the idle timer, but
      is used to separate messages received from the network
      by gaps in time so that the Async device can distinguish
      between multiple messages. If configured as 0, then this
      function is disabled and if messages are received while
      transmitting a current message, the the two messages
      from the network will be sent out with no gap between
      them. If configured greater than 0, then a gap of the
      specified number of milliseconds will be inserted.
      The default value is 40."
    ::= { asyncConfigEntry 12 }

  asyncRxForwardingCount  OBJECT-TYPE
    SYNTAX  INTEGER (1..1024)
    ACCESS  read-only
    STATUS  mandatory
    DESCRIPTION
      "The Async receive forwarding count is used to forward
      messages when a configured number of characters is
      received from the Async line. This must be configured
      to greater than or equal to the maximum message length
      for a given protocol.
      The default value is 256."
    ::= { asyncConfigEntry 13 }

  asyncEiaSignalForwarding  OBJECT-TYPE
    SYNTAX  INTEGER {
      yes(1),
      no(2)
      }
    ACCESS  read-only
    STATUS  mandatory
    DESCRIPTION
      "The Async EIA signal forwarding is used to cause
      receive data to be forwarding based on a change of
      EIA RS-232 control signals. If configured as a DCE,
      and this field is set ot YES, then if the Request
      To Send (RTS) control signal (RS-232 DB25 pin 4)
      changes from active to inactive, any characters already
      received are forwarded and sent to the network. If
      configured as a DTE, and this field is set to YES,
      then if the DCD (Data Carrier Detect) control signal
      (RS-232 DB25 pin 8) changes from active to inactive,
      forwarding to the network will occur.
      The default value is 1 or YES."
    ::= { asyncConfigEntry 14 }

  asyncAddressOffset  OBJECT-TYPE
    SYNTAX  INTEGER (0..255)
    ACCESS  read-only
    STATUS  mandatory
    DESCRIPTION
      "If the address offset is specified as zero, then the
      data is not parsed to find a device address in order
      to direct the data to a specified LLC connection. If
      the address offset is 1 to 255, then the 8 bits
      specified at that offset (where offset 1 is the first
      byte of a message received) are interpreted as an
      address. If this field is set 0 zero, then only
      one CU record is allowed (i.e. all data sent/received
      to/from the line is to/from one network connection).
      If this field is greater than 0 (address offset
      specified) then one or more CU records can be
      configured to route the data based on the device
      address.
      The default value is 1."
    ::= { asyncConfigEntry 15 }

  asyncRTC  OBJECT-TYPE
    SYNTAX  OCTET STRING (SIZE(1))
    ACCESS  read-only
    STATUS  mandatory
    DESCRIPTION
      "Defines whether the alarms system protocol has a
       record termination(forwarding character). The valid
      range is from hex 01 to hex ff.

      The default value is not defined."
    ::= { asyncConfigEntry 16 }

  asyncCTS  OBJECT-TYPE
    SYNTAX  INTEGER {
      yes(1),
      no(2)
      }
    ACCESS  read-only
    STATUS  mandatory
    DESCRIPTION
      "Defines whether CTS is an input signal used to
      determine the port status. This parameter is applicable
      if clocking is set to external.  For internal clocking
      the parameter is ignored and DCD is asserted when port
      is enabled. The range is yes and no.

      The default value is 'No'."
    ::= { asyncConfigEntry 17 }

  asyncDCD  OBJECT-TYPE
    SYNTAX  INTEGER {
      yes(1),
      no(2)
      }
    ACCESS  read-only
    STATUS  mandatory
    DESCRIPTION
      "Defines whether DCD is required as input signal
      or ignored. This parameter is applicable if the
      clocking is set to external.  For internal clocking
      the parameter is ignored and DCD is asserted when port
      is enabled. The range is yes and no.

      The default value is 'yes'."
    ::= { asyncConfigEntry 18 }

  asyncDSR  OBJECT-TYPE
    SYNTAX  INTEGER {
      yes(1),
      no(2)
      }
    ACCESS  read-only
    STATUS  mandatory
    DESCRIPTION
      "Defines whether DSR is required as input signal
      or ignored. This parameter is applicable if the
      clocking is set to external.  For internal clocking
      the parameter is ignored and DSR is asserted when port
      is enabled. The range is yes and no.

      The default value is 'yes'."
    ::= { asyncConfigEntry 19 }

  asyncDTR  OBJECT-TYPE
    SYNTAX  INTEGER {
      yes(1),
      no(2)
      }
    ACCESS  read-only
    STATUS  mandatory
    DESCRIPTION
      "Defines whether DTR is required as input signal
      or ignored. This parameter is applicable if the
      clocking is set to internal.  For external clocking
      the parameter is ignored and DTR is asserted when port
      is enabled. The range is yes and no.

      The default value is 'yes'."
    ::= { asyncConfigEntry 20 }

  asyncRTS  OBJECT-TYPE
    SYNTAX  INTEGER {
      yes(1),
      no(2)
      }
    ACCESS  read-only
    STATUS  mandatory
    DESCRIPTION
      "Defines whether RTS is an input signal to determine
      the port status. This parameter is applicable if the
      clocking is set to internal.  For external clocking
      the parameter is ignored and RTS is asserted when port
      is enabled. The range is yes and no.

      The default value is 'No'."
    ::= { asyncConfigEntry 21 }

  asyncReturnClock  OBJECT-TYPE
    SYNTAX  INTEGER {
      yes(1),
      no(2),
      default(3)
      }
    ACCESS  read-only
    STATUS  mandatory
    DESCRIPTION
      "Defines whether Return Clock (SCTE) is available as
      input signal or ignored. This parameter is applicable
      if the clocking is set to internal. For external clocking
      the parameter is ignored. The range is yes and no.

      The default value is 'yes'."
    ::= { asyncConfigEntry 22 }

  asyncOrt  OBJECT-TYPE
    SYNTAX  INTEGER {
      yes(1),
      no(2)
      }
    ACCESS  read-only
    STATUS  mandatory
    DESCRIPTION
      "The ORT command is a new port level command.  By default,
      the setting will be YES to set the N2 value to zero,
      but can be set to NO to indicate that the normal LLC N2
      setting should be used.

      The default value is 'yes'."
    ::= { asyncConfigEntry 23 }

--
  -- The Async Port Statistics Table:
  --

  asyncStatsTable   OBJECT-TYPE
    SYNTAX SEQUENCE OF AsyncStatsEntry
    ACCESS  not-accessible
    STATUS  mandatory
    DESCRIPTION
      "A table of Async information."
    ::= { lineAsyncGroup 2 }

  asyncStatsEntry   OBJECT-TYPE
    SYNTAX  AsyncStatsEntry
    ACCESS  not-accessible
    STATUS  mandatory
    DESCRIPTION
      "An entry consisting of port information for a
      particular Async port."
    INDEX { asyncStatsPortIndex }
    ::= { asyncStatsTable 1 }

  AsyncStatsEntry ::=
    SEQUENCE {
      asyncStatsPortIndex
        INTEGER,
      asyncPortType
        INTEGER,
      asyncInOctets
        Counter,
      asyncOutOctets
        Counter,
      asyncInMessages
        Counter,
      asyncOutMessages
        Counter,
      asyncInMsgDiscarded
        Counter,
      asyncOutMsgDiscarded
        Counter,
      asyncXmtFailures
        Counter,
      asyncRcvMsgForwarded
        Counter,
      asyncRcvMsgErrors
        Counter,
      asyncRcvCharsDiscarded
        Counter,
      asyncRcvParityErrors
        Counter,
      asyncRcvFramingErrors
        Counter,
      asyncRcvFifoOverruns
        Counter,
      asyncRcvCharsOverruns
        Counter,
      asyncRcvBreakConditions
        Counter
    }

  asyncStatsPortIndex OBJECT-TYPE
    SYNTAX  INTEGER
    ACCESS  read-only
    STATUS  mandatory
    DESCRIPTION
      "The port number that uniquely identifies
      this Async port."
    ::= { asyncStatsEntry 1 }

  asyncPortType  OBJECT-TYPE
    SYNTAX  INTEGER {
                     hasc-type(9),
                     tasc-type(10)
                     }
    ACCESS  read-only
    STATUS  mandatory
    DESCRIPTION
      "The port type.
      HASC (Host Async) ports are for attaching to an
                        Async Alarm Central Processor.
      TASC ports (Terminal Async) ports are for attaching
                        to Alarm Controllers."
    ::= { asyncStatsEntry 2 }

  asyncInOctets OBJECT-TYPE
    SYNTAX  Counter
    ACCESS  read-only
    STATUS  mandatory
    DESCRIPTION
      "The number of bytes received."
    ::= { asyncStatsEntry 3 }

  asyncOutOctets OBJECT-TYPE
    SYNTAX  Counter
    ACCESS  read-only
    STATUS  mandatory
    DESCRIPTION
      "The number of bytes sent."
    ::= { asyncStatsEntry 4 }

  asyncInMessages OBJECT-TYPE
    SYNTAX  Counter
    ACCESS  read-only
    STATUS  mandatory
    DESCRIPTION
      "The number of messages received."
    ::= { asyncStatsEntry 5 }

  asyncOutMessages OBJECT-TYPE
    SYNTAX  Counter
    ACCESS  read-only
    STATUS  mandatory
    DESCRIPTION
      "The number of messages sent."
    ::= { asyncStatsEntry 6 }


  asyncInMsgDiscarded     OBJECT-TYPE
    SYNTAX  Counter
    ACCESS  read-only
    STATUS  mandatory
    DESCRIPTION
      "The number of received messages discarded."
    ::= { asyncStatsEntry 7 }

  asyncOutMsgDiscarded    OBJECT-TYPE
    SYNTAX  Counter
    ACCESS  read-only
    STATUS  mandatory
    DESCRIPTION
      "The number of sent messages discarded."
    ::= { asyncStatsEntry 8 }

  asyncXmtFailures        OBJECT-TYPE
    SYNTAX  Counter
    ACCESS  read-only
    STATUS  mandatory
    DESCRIPTION
      "The number of failures in transmission."
    ::= { asyncStatsEntry 9 }

  asyncRcvMsgForwarded   OBJECT-TYPE
    SYNTAX  Counter
    ACCESS  read-only
    STATUS  mandatory
    DESCRIPTION
      "The number of received messages forwarded."
    ::= { asyncStatsEntry 10 }

  asyncRcvMsgErrors      OBJECT-TYPE
    SYNTAX  Counter
    ACCESS  read-only
    STATUS  mandatory
    DESCRIPTION
      "The number of errors detected in receiving
                         messages."
    ::= { asyncStatsEntry 11 }

  asyncRcvCharsDiscarded  OBJECT-TYPE
    SYNTAX  Counter
    ACCESS  read-only
    STATUS  mandatory
    DESCRIPTION
      "The number of received characters discarded."
    ::= { asyncStatsEntry 12 }

  asyncRcvParityErrors   OBJECT-TYPE
    SYNTAX  Counter
    ACCESS  read-only
    STATUS  mandatory
    DESCRIPTION
      "The number of parity errors detected."
    ::= { asyncStatsEntry 13 }

  asyncRcvFramingErrors  OBJECT-TYPE
    SYNTAX  Counter
    ACCESS  read-only
    STATUS  mandatory
    DESCRIPTION
      "The number of errors detected in receiving
                         frames."
    ::= { asyncStatsEntry 14 }

  asyncRcvFifoOverruns   OBJECT-TYPE
    SYNTAX  Counter
    ACCESS  read-only
    STATUS  mandatory
    DESCRIPTION
      "The number FIFO receive overruns detected."
    ::= { asyncStatsEntry 15 }

  asyncRcvCharsOverruns  OBJECT-TYPE
    SYNTAX  Counter
    ACCESS  read-only
    STATUS  mandatory
    DESCRIPTION
      "The number of character receive overruns detected."
    ::= { asyncStatsEntry 16 }

  asyncRcvBreakConditions  OBJECT-TYPE
    SYNTAX  Counter
    ACCESS  read-only
    STATUS  mandatory
    DESCRIPTION
      "The number of receive break conditions."
    ::= { asyncStatsEntry 17 }

  --
  -- The Bisync RJE Port Level Group
  --
  --
  -- The Bisync RJE Configuration Table:
  --

  bisyncrjeConfigTable  OBJECT-TYPE
    SYNTAX SEQUENCE OF BisyncrjeConfigEntry
    ACCESS  not-accessible
    STATUS  mandatory
    DESCRIPTION
      "A table of Bisync port information."
    ::= { lineBisyncRjeGroup 1 }

  bisyncrjeConfigEntry  OBJECT-TYPE
    SYNTAX  BisyncrjeConfigEntry
    ACCESS  not-accessible
    STATUS  mandatory
    DESCRIPTION
      "An entry consisting of port information for a
       particular Bisync port."
    INDEX { bisyncrjeConfigPortIndex }
    ::= { bisyncrjeConfigTable 1 }

  BisyncrjeConfigEntry ::=
    SEQUENCE {
      bisyncrjeConfigPortIndex
        INTEGER,
      bisyncrjeConfigType
        INTEGER,
      bisyncrjeNAUName
        DisplayString,
      bisyncrjeInitState
        INTEGER,
      bisyncrjeCarrier
        INTEGER,
      bisyncrjeClocking
        INTEGER,
      bisyncrjeSpeed
        INTEGER,
      bisyncrjeReplyTimer
        INTEGER,
      bisyncrjeRetries
        INTEGER,
      bisyncrjeCodeSet
        INTEGER,
      bisyncrjeCTS
        INTEGER,
      bisyncrjeDCD
        INTEGER,
      bisyncrjeDSR
        INTEGER,
      bisyncrjeDTR
        INTEGER,
      bisyncrjeRTS
        INTEGER,
      bisyncrjeReturnClock
        INTEGER
    }

  bisyncrjeConfigPortIndex  OBJECT-TYPE
    SYNTAX  INTEGER
    ACCESS  read-only
    STATUS  mandatory
    DESCRIPTION
      "The port number that uniquely identifies
      this port.
      Current supported Bisync Rje numbers are 1-4."
    ::= { bisyncrjeConfigEntry 1 }


  bisyncrjeConfigType  OBJECT-TYPE
    SYNTAX  INTEGER {
      secondaryRJE-type(13),
      primaryRJE-type(14)
    }
    ACCESS  read-only
    STATUS  mandatory
    DESCRIPTION
      "The port type.

      PRJE (Primary RJE) ports emulate a Host
      and polls the downstream controllers).

      SRJE ports (Secondary RJE) ports emulate a line with
      Terminal Controllers (CUs) and respond to polls
      from the Host."

    ::= { bisyncrjeConfigEntry 2 }

  bisyncrjeNAUName   OBJECT-TYPE
    SYNTAX  DisplayString (SIZE(1..8))
    ACCESS  read-only
    STATUS  mandatory
    DESCRIPTION
      "The NAU name of this port.
      The default value for this field is all blank
      (filled with ASCII space 0x20 characters)."
    ::= { bisyncrjeConfigEntry 3 }

  bisyncrjeInitState  OBJECT-TYPE
    SYNTAX  INTEGER {
      in-service(1),
      out-of-service(2)
      }
    ACCESS  read-only
    STATUS  mandatory
    DESCRIPTION
      "The initial state of the Bisync RJE port.

      If configured for 'in-service', then the Bisync RJE port
      will be brougt up automattically when the unit is powered
      up.

      If configured for 'out-of-service', then the Bisync RJE port
      must be manually enabled by operator intervention (i.e.
      enable command must be sent).

      The default value is 'enabled'."
    ::= { bisyncrjeConfigEntry 4 }

  bisyncrjeCarrier  OBJECT-TYPE
    SYNTAX  INTEGER {
      constant(1),
      switched(2)
      }
    ACCESS  read-only
    STATUS  mandatory
    DESCRIPTION
      "This field indicates whether Carrier is constant
      or switched.

      The default value for this parameter is 'constant'."
    ::= { bisyncrjeConfigEntry 5 }

  bisyncrjeClocking  OBJECT-TYPE
    SYNTAX  INTEGER {
      external(1),
      internal(2)
      }
    ACCESS  read-only
    STATUS  mandatory
    DESCRIPTION
      "Clocking source for this port.
      Setting 'internal' will cause the
      port to emulate a physical DCE, and setting
      external will cause the port to emulate a
      physical DTE.

      The default value for this field is 'external'."
    ::= { bisyncrjeConfigEntry 6 }

  bisyncrjeSpeed  OBJECT-TYPE
    SYNTAX  INTEGER {
      speed1200(12),
      speed2000(20),
      speed2400(24),
      speed3600(36),
      speed4800(48),
      speed7200(72),
      speed9600(96),
      speed14400(144),
      speed19200(192),
      speed28800(288),
      speed48000(480),
      speed56000(560),
      speed64000(640),
      speed128000(1280)
      }
    ACCESS  read-only
    STATUS  mandatory
    DESCRIPTION
      "The ports speed in bits per second.
      The default value is 9600 bits per second.
      Speeds higher than 128000 are not supported."
    ::= { bisyncrjeConfigEntry 7 }

  bisyncrjeReplyTimer  OBJECT-TYPE
    SYNTAX  INTEGER (1..10)
    ACCESS  read-only
    STATUS  mandatory
    DESCRIPTION
      "The time to wait for a response in seconds.
      The default value for this field is 3 seconds."

    ::= { bisyncrjeConfigEntry 8 }

  bisyncrjeRetries  OBJECT-TYPE
    SYNTAX  INTEGER (1..20)
    ACCESS  read-only
    STATUS  mandatory
    DESCRIPTION
      "The maximum number of retries (N2 value) before
      failing a CU.

      The default value for this field is 8."

    ::= { bisyncrjeConfigEntry 9 }

  bisyncrjeCodeSet OBJECT-TYPE
    SYNTAX  INTEGER {
        ascii(1),
        ebcdic(2)
        }
    ACCESS  read-only
    STATUS  mandatory
    DESCRIPTION
      "This parameter sets code set to be used for RJE line.
      The range of this parameter is ASCII and EBCDIC.

      The default value for this field is EBCDIC."

    ::= { bisyncrjeConfigEntry 10 }

  bisyncrjeCTS  OBJECT-TYPE
    SYNTAX  INTEGER {
      yes(1),
      no(2)
      }
    ACCESS  read-only
    STATUS  mandatory
    DESCRIPTION
      "Defines whether CTS is an input signal used to
      determine the port status. This parameter is applicable
      if clocking is set to external.  For internal clocking
      the parameter is ignored and DCD is asserted when port
      is enabled. The range is yes and no.

      The default value is 'No'."
    ::= { bisyncrjeConfigEntry 11 }

  bisyncrjeDCD  OBJECT-TYPE
    SYNTAX  INTEGER {
      yes(1),
      no(2)
      }
    ACCESS  read-only
    STATUS  mandatory
    DESCRIPTION
      "Defines whether DCD is required as input signal
      or ignored. This parameter is applicable if the
      clocking is set to external.  For internal clocking
      the parameter is ignored and DCD is asserted when port
      is enabled. The range is yes and no.

      The default value is 'yes'."
    ::= { bisyncrjeConfigEntry 12 }

  bisyncrjeDSR  OBJECT-TYPE
    SYNTAX  INTEGER {
      yes(1),
      no(2)
      }
    ACCESS  read-only
    STATUS  mandatory
    DESCRIPTION
      "Defines whether DSR is required as input signal
      or ignored. This parameter is applicable if the
      clocking is set to external.  For internal clocking
      the parameter is ignored and DSR is asserted when port
      is enabled. The range is yes and no.

      The default value is 'yes'."
    ::= { bisyncrjeConfigEntry 13 }

  bisyncrjeDTR  OBJECT-TYPE
    SYNTAX  INTEGER {
      yes(1),
      no(2)
      }
    ACCESS  read-only
    STATUS  mandatory
    DESCRIPTION
      "Defines whether DTR is required as input signal
      or ignored. This parameter is applicable if the
      clocking is set to internal.  For external clocking
      the parameter is ignored and DTR is asserted when port
      is enabled. The range is yes and no.

      The default value is 'yes'."
    ::= { bisyncrjeConfigEntry 14 }

  bisyncrjeRTS  OBJECT-TYPE
    SYNTAX  INTEGER {
      yes(1),
      no(2)
      }
    ACCESS  read-only
    STATUS  mandatory
    DESCRIPTION
      "Defines whether RTS is an input signal to determine
      the port status. This parameter is applicable if the
      clocking is set to internal.  For external clocking
      the parameter is ignored and RTS is asserted when port
      is enabled. The range is yes and no.

      The default value is 'No'."
    ::= { bisyncrjeConfigEntry 15 }

  bisyncrjeReturnClock  OBJECT-TYPE
    SYNTAX  INTEGER {
      yes(1),
      no(2),
      default(3)
      }
    ACCESS  read-only
    STATUS  mandatory
    DESCRIPTION
      "Defines whether Return Clock (SCTE) is available as
      input signal or ignored. This parameter is applicable
      if the clocking is set to internal. For external clocking
      the parameter is ignored. The range is yes and no.

      The default value is 'yes'."
    ::= { bisyncrjeConfigEntry 16 }


  --
  -- The Bisync RJE Port Statistics Table:
  --

  bisyncrjeStatsTable   OBJECT-TYPE
    SYNTAX SEQUENCE OF BisyncrjeStatsEntry
    ACCESS  not-accessible
    STATUS  mandatory
    DESCRIPTION
      "A table of Bisync information."
    ::= { lineBisyncRjeGroup 2 }

  bisyncrjeStatsEntry   OBJECT-TYPE
    SYNTAX  BisyncrjeStatsEntry
    ACCESS  not-accessible
    STATUS  mandatory
    DESCRIPTION
      "An entry consisting of port information for a
       particular Bisync port."
    INDEX { bisyncrjeStatsPortIndex }
    ::= { bisyncrjeStatsTable 1 }

  BisyncrjeStatsEntry ::=
    SEQUENCE {
      bisyncrjeStatsPortIndex
        INTEGER,
      bisyncrjePortType
        INTEGER,
      bisyncrjeInChrs
        Counter,
      bisyncrjeOutChrs
        Counter,
      bisyncrjeInTrns
        Counter,
      bisyncrjeOutTrns
        Counter,
      bisyncrjeInRetr
        Counter,
      bisyncrjeOutRetr
        Counter,
      bisyncrjeInEnq
        Counter,
      bisyncrjeOutEnq
        Counter,
      bisyncrjeInEtb
        Counter,
      bisyncrjeOutEtb
        Counter,
      bisyncrjeInEtx
        Counter,
      bisyncrjeOutEtx
        Counter,
      bisyncrjeWack
        Counter,
      bisyncrjeRvi
        Counter
    }


  bisyncrjeStatsPortIndex OBJECT-TYPE
    SYNTAX  INTEGER
    ACCESS  read-only
    STATUS  mandatory
    DESCRIPTION
      "The port number that uniquely identifies
      this Bisync RJE port.
      Current supported numbers are 1-4."
    ::= { bisyncrjeStatsEntry 1 }


  bisyncrjePortType  OBJECT-TYPE
    SYNTAX  INTEGER {
      srje-SecondaryRJE(13),
      prje-PrimaryRJE(14)
      }
    ACCESS  read-only
    STATUS  mandatory
    DESCRIPTION
      "The port type."
    ::= { bisyncrjeStatsEntry 2 }

  bisyncrjeInChrs OBJECT-TYPE
    SYNTAX  Counter
    ACCESS  read-only
    STATUS  mandatory
    DESCRIPTION
      "The number of Characters received."
    ::= { bisyncrjeStatsEntry 3 }

  bisyncrjeOutChrs OBJECT-TYPE
    SYNTAX  Counter
    ACCESS  read-only
    STATUS  mandatory
    DESCRIPTION
      "The number of Characters sent."
    ::= { bisyncrjeStatsEntry 4 }

  bisyncrjeInTrns OBJECT-TYPE
    SYNTAX  Counter
    ACCESS  read-only
    STATUS  mandatory
    DESCRIPTION
      "The number of Transactions received."
    ::= { bisyncrjeStatsEntry 5 }

  bisyncrjeOutTrns OBJECT-TYPE
    SYNTAX  Counter
    ACCESS  read-only
    STATUS  mandatory
    DESCRIPTION
      "The number of Transactions sent."
    ::= { bisyncrjeStatsEntry 6 }

  bisyncrjeInRetr OBJECT-TYPE
    SYNTAX  Counter
    ACCESS  read-only
    STATUS  mandatory
    DESCRIPTION
      "The number of Retransmits received."
    ::= { bisyncrjeStatsEntry 7 }

  bisyncrjeOutRetr OBJECT-TYPE
    SYNTAX  Counter
    ACCESS  read-only
    STATUS  mandatory
    DESCRIPTION
      "The number of Retransmits sent."
    ::= { bisyncrjeStatsEntry 8 }

  bisyncrjeInEnq OBJECT-TYPE
    SYNTAX  Counter
    ACCESS  read-only
    STATUS  mandatory
    DESCRIPTION
      "The number of ENQ received."
    ::= { bisyncrjeStatsEntry 9 }

  bisyncrjeOutEnq  OBJECT-TYPE
    SYNTAX  Counter
    ACCESS  read-only
    STATUS  mandatory
    DESCRIPTION
      "The number of ENQ sent."
    ::= { bisyncrjeStatsEntry 10 }

  bisyncrjeInEtb OBJECT-TYPE
    SYNTAX  Counter
    ACCESS  read-only
    STATUS  mandatory
    DESCRIPTION
      "The number of ETB received."
    ::= { bisyncrjeStatsEntry 11 }

  bisyncrjeOutEtb  OBJECT-TYPE
    SYNTAX  Counter
    ACCESS  read-only
    STATUS  mandatory
    DESCRIPTION
      "The number of ETB sent."
    ::= { bisyncrjeStatsEntry 12 }

  bisyncrjeInEtx OBJECT-TYPE
    SYNTAX  Counter
    ACCESS  read-only
    STATUS  mandatory
    DESCRIPTION
      "The number of ETX received."
    ::= { bisyncrjeStatsEntry 13 }

  bisyncrjeOutEtx  OBJECT-TYPE
    SYNTAX  Counter
    ACCESS  read-only
    STATUS  mandatory
    DESCRIPTION
      "The number of ETX sent."
    ::= { bisyncrjeStatsEntry 14 }

  bisyncrjeWack OBJECT-TYPE
    SYNTAX  Counter
    ACCESS  read-only
    STATUS  mandatory
    DESCRIPTION
      "The number of WACK received."
    ::= { bisyncrjeStatsEntry 15 }

  bisyncrjeRvi  OBJECT-TYPE
    SYNTAX  Counter
    ACCESS  read-only
    STATUS  mandatory
    DESCRIPTION
      "The number of RVI received."
    ::= { bisyncrjeStatsEntry 16 }

  --
  -- The Dial Backup Port Level Group
  --
  --
  -- The Dial Backup  Configuration Table:
  --

  dialbackupConfigTable  OBJECT-TYPE
    SYNTAX SEQUENCE OF DialbackupConfigEntry
    ACCESS  not-accessible
    STATUS  mandatory
    DESCRIPTION
      "A table of Sync product dial backup information."
    ::= { lineDialBackupGroup 1 }

  dialbackupConfigEntry  OBJECT-TYPE
    SYNTAX  DialbackupConfigEntry
    ACCESS  not-accessible
    STATUS  mandatory
    DESCRIPTION
      "An entry consisting of port information for a
      particular Sync product dial backup port."
    INDEX { dialbackupConfigPortIndex }
    ::= { dialbackupConfigTable 1 }

  DialbackupConfigEntry ::=
    SEQUENCE {
      dialbackupConfigPortIndex
        INTEGER,
      dialbackupPortType
        INTEGER,
      dialbackupConnectType
        INTEGER,
      dialbackupFirstDedicatedPort
        INTEGER,
      dialbackupassociatedDLCIDedicated
        INTEGER,
      dialbackupSecondDedicatedPort
        INTEGER,
      dialbackupassociatedDLCISecond
        INTEGER,
      dialbackupDedicatedPort
        INTEGER,
      dialbackupDedicatedLMIPort
        INTEGER,
      dialbackupDialInactivityTimer
        INTEGER,
      dialbackupDialSuspendTimer
        INTEGER,
      dialbackupModemInitString
        DisplayString,
      dialbackupModemDialString
        DisplayString,
      dialbackupModemHangString
        DisplayString,
      dialbackupDialDelayTimer
        INTEGER,
      dialbackupTreatLLCControlCharacters
        INTEGER
    }

  dialbackupConfigPortIndex  OBJECT-TYPE
    SYNTAX  INTEGER
    ACCESS  read-only
    STATUS  mandatory
    DESCRIPTION
      "This port uniquely identifies the dial backup port.
       Range is a valid port number."

    ::= { dialbackupConfigEntry 1 }

  dialbackupPortType  OBJECT-TYPE
    SYNTAX  INTEGER {
      frame-relay-dialbackup-type(20)
      }
    ACCESS  read-only
    STATUS  mandatory
    DESCRIPTION
      "The Dial backup connect Type."
    ::= { dialbackupConfigEntry 2 }

  dialbackupConnectType  OBJECT-TYPE
    SYNTAX  INTEGER {
      hayes(1),
      vtwentyfivebis(2),
      nullmodem(3)
      }
    ACCESS  read-only
    STATUS  mandatory
    DESCRIPTION
      "The Dial backup connect Type."
    ::= { dialbackupConfigEntry 3 }

  dialbackupFirstDedicatedPort OBJECT-TYPE
    SYNTAX  INTEGER
    ACCESS  read-only
    STATUS  mandatory
    DESCRIPTION
      "This defines a frame relay PVC which will cause
      dial backup if it is declared as failed (deactivated)
      by the network.  Port number is a valid Frame Relay
      and DLCI is a valid Frame Relay DLCI."

    ::= { dialbackupConfigEntry 4 }

  dialbackupassociatedDLCIDedicated OBJECT-TYPE
    SYNTAX  INTEGER
    ACCESS  read-only
    STATUS  mandatory
    DESCRIPTION
      "This defines a frame relay PVC which will cause
      dial backup if it is declared as failed (deactivated)
      by the network.  DLCI is a valid Frame Relay DLCI."

    ::= { dialbackupConfigEntry 5 }

  dialbackupSecondDedicatedPort OBJECT-TYPE
    SYNTAX  INTEGER
    ACCESS  read-only
    STATUS  mandatory
    DESCRIPTION
      "This defines a second frame relay PVC which will cause
      dial backup if it is declared as failed (deactivated)
      by the network.  Port number is a valid Frame Relay
      and DLCI is a valid Frame Relay DLCI."

    ::= { dialbackupConfigEntry 6 }

  dialbackupassociatedDLCISecond OBJECT-TYPE
    SYNTAX  INTEGER
    ACCESS  read-only
    STATUS  mandatory
    DESCRIPTION
      "This defines a second frame relay PVC which will cause
      dial backup if it is declared as failed (deactivated)
      by the network. DLCI is a valid Frame Relay DLCI."

    ::= { dialbackupConfigEntry 7 }

  dialbackupDedicatedPort OBJECT-TYPE
    SYNTAX  INTEGER
    ACCESS  read-only
    STATUS  mandatory
    DESCRIPTION
      "When this port fails, dial connection is
      activated. Range is a valid port number.

      The default value for this field is 1."
    ::= { dialbackupConfigEntry 8 }

  dialbackupDedicatedLMIPort OBJECT-TYPE
    SYNTAX  INTEGER
    ACCESS  read-only
    STATUS  mandatory
    DESCRIPTION
      "When this port looses LMI connectivity, dial
      connection is activated. Range is a valid number.

      The default value for this field is 1."
    ::= { dialbackupConfigEntry 9}

  dialbackupDialInactivityTimer OBJECT-TYPE
    SYNTAX  INTEGER (0..9999)
    ACCESS  read-only
    STATUS  mandatory
    DESCRIPTION
      "This parameter defines inactivity timer for dial
      connection.  Expiration of this timer will cause
      dial connection to disconnect. The range of this
      parameter is 0..9999 seconds. Value 0 disables
      inactivity timer usage.

      The default value for this field is 60 seconds."
    ::= { dialbackupConfigEntry 10 }

  dialbackupDialSuspendTimer  OBJECT-TYPE
    SYNTAX  INTEGER (0..9999)
    ACCESS  read-only
    STATUS  mandatory
    DESCRIPTION
      "Defines a duration for which the dial connection.
      will not be attempted after the dial connection is
      torn down.  The range is 0..9999 seconds. Value of
      0 disable inactivity timer usage.

      The default value for this field is 60 seconds."
    ::= { dialbackupConfigEntry 11 }

  dialbackupModemInitString   OBJECT-TYPE
    SYNTAX  DisplayString (SIZE(1..40))
    ACCESS  read-only
    STATUS  mandatory
    DESCRIPTION
      "Defins a modem intialization string. The field
      is 40 characters long.

      The default value for this field is all blank
      (filled with ASCII space 0x20 characters)."
    ::= { dialbackupConfigEntry 12 }

  dialbackupModemDialString   OBJECT-TYPE
    SYNTAX  DisplayString (SIZE(1..40))
    ACCESS  read-only
    STATUS  mandatory
    DESCRIPTION
      "Defins a modem dial string to activate dial
      connection. This field is up to 40 characters
      long.  Dial phone number may be specified here.

      The default value for this field is all blank
      (filled with ASCII space 0x20 characters)."
    ::= { dialbackupConfigEntry 13 }

  dialbackupModemHangString   OBJECT-TYPE
    SYNTAX  DisplayString (SIZE(1..20))
    ACCESS  read-only
    STATUS  mandatory
    DESCRIPTION
      "Defines a modem hang up string to deactivate
      dial connection.  This field is up to 20
      characters long.

      The default value for this field is all blank
      (filled with ASCII space 0x20 characters)."
    ::= { dialbackupConfigEntry 14 }

  dialbackupDialDelayTimer OBJECT-TYPE
    SYNTAX  INTEGER (0..9999)
    ACCESS  read-only
    STATUS  mandatory
    DESCRIPTION
      "Defines a duration for which the dial connecton
      will not be attempted after need to initiate dial
      connection is detected. The range of this
      parameter is 0..9999 seconds. Value 0 implies
      immediate dial initiation.

      The default value for this field is 60 seconds."
    ::= { dialbackupConfigEntry 15 }

  dialbackupTreatLLCControlCharacters OBJECT-TYPE
    SYNTAX  INTEGER {
      yes(1),
      no(2)
      }
    ACCESS  read-only
    STATUS  mandatory
    DESCRIPTION
      "Defines whether LLC control frames (TEST, XID,
      RR, RNR, REJ, DISC, UA, DM, FRMR etc. except I frames)
      are to be considered as user data or not.  For a dial
      backup up port if this contorl frames are not treated
      as user data, then idle LLC2 sessions on the port will
      cause inactivity timer to pop causing SNA session
      disconnect. The range of this parameter is YES or NO.

      Default value is YES"
    ::= { dialbackupConfigEntry 16 }

  --
  -- The Dial Backup Port Statistics Table:
  --

  dialbackupStatsTable  OBJECT-TYPE
    SYNTAX SEQUENCE OF DialbackupStatsEntry
    ACCESS  not-accessible
    STATUS  mandatory
    DESCRIPTION
      "A table of Frame Relay information."
    ::= { lineDialBackupGroup 2 }

  dialbackupStatsEntry  OBJECT-TYPE
    SYNTAX  DialbackupStatsEntry
    ACCESS  not-accessible
    STATUS  mandatory
    DESCRIPTION
      "An entry consisting of port information for a
       particular Frame Relay port."
    INDEX { dialbackupStatsPortIndex }
    ::= { dialbackupStatsTable 1 }

  DialbackupStatsEntry ::=
    SEQUENCE {
      dialbackupStatsPortIndex
        INTEGER,
      dialbackupSuccatmpt
        Counter,
      dialbackupunsuccatmpt
        Counter,
      dialbackupinact
        Counter
    }

  dialbackupStatsPortIndex OBJECT-TYPE
    SYNTAX  INTEGER
    ACCESS  read-only
    STATUS  mandatory
    DESCRIPTION
      "The port number that uniquely identifies
      this Dial Backup port."
    ::= { dialbackupStatsEntry 1 }

  dialbackupSuccatmpt OBJECT-TYPE
    SYNTAX  Counter
    ACCESS  read-only
    STATUS  mandatory
    DESCRIPTION
      "The number of successful dial backup attempts."
    ::= { dialbackupStatsEntry 2 }

  dialbackupunsuccatmpt OBJECT-TYPE
    SYNTAX  Counter
    ACCESS  read-only
    STATUS  mandatory
    DESCRIPTION
      "The number of unsuccessful dial backup attempts."
    ::= { dialbackupStatsEntry 3 }

  dialbackupinact OBJECT-TYPE
    SYNTAX  Counter
    ACCESS  read-only
    STATUS  mandatory
    DESCRIPTION
      "The Number of times inactivity timer expired."
    ::= { dialbackupStatsEntry 4 }

  --
  -- The X25 Configuration Table:
  --

  x25ConfigTable  OBJECT-TYPE
    SYNTAX  SEQUENCE OF X25ConfigEntry
    ACCESS  not-accessible
    STATUS  mandatory
    DESCRIPTION
      "A table of X25 information."
    ::= { lineX25Group 1 }

  x25ConfigEntry  OBJECT-TYPE
    SYNTAX  X25ConfigEntry
    ACCESS  not-accessible
    STATUS  mandatory
    DESCRIPTION
      "An entry consisting of port information for a
       particular X25 port."
    INDEX { x25ConfigPortIndex }
    ::= { x25ConfigTable 1 }

  X25ConfigEntry ::=
    SEQUENCE {
      x25ConfigPortIndex
        INTEGER,
      x25ConfigType
        INTEGER,
      x25NAUName
        DisplayString,
      x25InitState
        INTEGER,
      x25Clocking
        INTEGER,
      x25DTEAddress
        OCTET STRING,
      x25LinkWindowSize
        INTEGER,
      x25T1Timer
        INTEGER,
      x25MaxRetries
        INTEGER,
      x25PortSpeed
        INTEGER,
      x25ReceiveWindowSize
        INTEGER,
      x25TransmitWindowSize
        INTEGER,
      x25ReceivePacketSize
        INTEGER,
      x25TransmitPacketSize
        INTEGER,
      x25LowTwoWayChannel
        INTEGER,
      x25HighTwoWayChannel
        INTEGER,
      x25UseCallingAddress
        INTEGER,
      x25ForwardingUnit
        INTEGER,
      x25DevicePacketSize
        INTEGER,
      x25DeviceWindowSize
        INTEGER,
      x25PlaceReverseChargeCalls
        INTEGER,
      x25AcceptReverseChargeCalls
        INTEGER,
      x25NPS
        INTEGER,
      x25CTS
        INTEGER,
      x25DCD
        INTEGER,
      x25DSR
        INTEGER,
      x25DTR
        INTEGER,
      x25RTS
        INTEGER,
      x25ReturnClock
        INTEGER,
      x25IPAddress
        IpAddress,
      x25NetworkMask
        IpAddress,
      x25DefaultGatewayAddress
        IpAddress,
      x25SecondDefaultGatewayAddress
        IpAddress
    }


  x25ConfigPortIndex  OBJECT-TYPE
    SYNTAX  INTEGER
    ACCESS  read-only
    STATUS  mandatory
    DESCRIPTION
      "The port number that uniquely identifies
       this port.
       Current supported X.25 numbers are 1-4."
    ::= { x25ConfigEntry 1 }


  x25ConfigType  OBJECT-TYPE
    SYNTAX  INTEGER {
      xDTE-XLogicalDTE(7),
      xDCE-XLogicalDCE(8)
      }
    ACCESS  read-only
    STATUS  mandatory
    DESCRIPTION
      "The port type.

      XDCE () ports is a logical DCE device waits to
      receive an incoming call from the X.25 network.

      XDTE ports is a logical DTE device initiates a
      to the X.25 network.

      Note that all ports must currently be defined as
      the same time for a given unit (i.e. no mixing of
      XDCE and XDTE ports is allowed)."
    ::= { x25ConfigEntry 2 }

  x25NAUName   OBJECT-TYPE
    SYNTAX  DisplayString (SIZE(1..8))
    ACCESS  read-only
    STATUS  mandatory
    DESCRIPTION
      "The NAU name of this port.
      The default value for this field is all blank
      (filled with ASCII space 0x20 characters)."
    ::= { x25ConfigEntry 3 }

  x25InitState  OBJECT-TYPE
    SYNTAX  INTEGER {
      in-service(1),
      out-of-service(2)
      }
    ACCESS  read-only
    STATUS  mandatory
    DESCRIPTION
      "The initial state of the X.25 port.

      If configured for 'in-service', then the X.25 port will
      be brougt up automattically when the unit is powered
      up.

      If configured for 'out-of-service', the the X.25 port must
      be manually enabled by operator intervention (i.e.
      enable command must be sent).

      The default value is 'enabled'."
    ::= { x25ConfigEntry 4 }

  x25Clocking  OBJECT-TYPE
    SYNTAX  INTEGER {
      external(1),
      internal(2),
      x21-external(3),
      x21-internal(4)
      }
    ACCESS  read-only
    STATUS  mandatory
    DESCRIPTION
      "Clocking source for this port.
      Setting 'internal' will cause the
      port to emulate a physical DCE, and setting
      external will cause the port to emulate a
      physical DTE.
      X21 External and Internal are used (with the
      proper external adapter) to support X.21 Leased
      Line operation for RS-422/RS-530 (25 pin balanced)
      interfaces.  X21 operation is not supported for
      boards that operate RS-232 or V.35.
      The default value for this field is 'external'."
    ::= { x25ConfigEntry 5 }

  x25DTEAddress  OBJECT-TYPE
    SYNTAX  OCTET STRING
    ACCESS  read-only
    STATUS  mandatory
    DESCRIPTION
      "This parameter specifies the DTE address this
      port will use to access the X.25 network."
    ::= { x25ConfigEntry 6 }

  x25LinkWindowSize  OBJECT-TYPE
    SYNTAX  INTEGER(1..7)
    ACCESS  read-only
    STATUS  mandatory
    DESCRIPTION
      "This parameter sets the maximum number of concurrent
      unacknowledged I frames at the X.25 data link level.
      The default value is 7."
    ::= { x25ConfigEntry 7 }

  x25T1Timer  OBJECT-TYPE
    SYNTAX  INTEGER(1..1980)
    ACCESS  read-only
    STATUS  mandatory
    DESCRIPTION
      "The SDLC T1 timer value in 20ths of a second.
      The default value is 60 (3 seconds)."
    ::= { x25ConfigEntry 8 }

  x25MaxRetries  OBJECT-TYPE
    SYNTAX  INTEGER (1..20)
    ACCESS  read-only
    STATUS  mandatory
    DESCRIPTION
      "The maximum number of retries (N2 value) before
      failing a PU.
      The default value for this field is 8."

    ::= { x25ConfigEntry 9 }

  x25PortSpeed  OBJECT-TYPE
    SYNTAX  INTEGER {
      speed2000(20),
      speed2400(24),
      speed3600(36),
      speed4800(48),
      speed7200(72),
      speed9600(96),
      speed14400(144),
      speed19200(192),
      speed28800(288),
      speed48000(480),
      speed56000(560),
      speed64000(640),
      speed128000(1280),
      speed256000(2560)
      }
    ACCESS  read-only
    STATUS  mandatory
    DESCRIPTION
      "The ports speed in 100 bits per second.
      The default value is 64000 bits per second.
      Speeds higher than 19200 are not supported on
      RS-232 ports units (must be V.35 or RS-422)."
    ::= { x25ConfigEntry 10 }

  x25ReceiveWindowSize   OBJECT-TYPE
    SYNTAX  INTEGER(1..7)
    ACCESS  read-only
    STATUS  mandatory
    DESCRIPTION
      "This parameter determines the number of consecutive
      data packets that the sync unit can receive
      before requiring an acknowledgment.
      The default value is 2."
    ::= { x25ConfigEntry 11 }

  x25TransmitWindowSize   OBJECT-TYPE
    SYNTAX  INTEGER(1..7)
    ACCESS  read-only
    STATUS  mandatory
    DESCRIPTION
      "This parameter determines the number of consecutive
      data packets to be transmitted on the X.25
      network before requiring an acknowledgment.
      The value you configure in this field must match
      the value configured in the X.25 network.
      The default value is 2."
    ::= { x25ConfigEntry 12 }

  x25ReceivePacketSize   OBJECT-TYPE
    SYNTAX  INTEGER {
        sixteen(16),
        thirtytwo(32),
        onetwentyeight(128),
        twofiftsix(256),
        fivetwelve(512),
        onethousand(1024)
     }
    ACCESS  read-only
    STATUS  mandatory
    DESCRIPTION
      "This parameter defines the size of packets
      received from the X.25 network in bytes.
      This value must match the configuration of your X.25
      network provider.
      The default value is 128 bytes."
    ::= { x25ConfigEntry 13 }

  x25TransmitPacketSize   OBJECT-TYPE
    SYNTAX  INTEGER  {
        sixteen(16),
        thirtytwo(32),
        onetwentyeight(128),
        twofiftsix(256),
        fivetwelve(512),
        onethousand(1024)
     }
    ACCESS  read-only
    STATUS  mandatory
    DESCRIPTION
      "This parameter defines the size of packets transmitted
      across the X.25 network in bytes.
      This value must match the configuration of the X.25
      network.
      The default value is 128 bytes."
    ::= { x25ConfigEntry 14 }

  x25LowTwoWayChannel   OBJECT-TYPE
    SYNTAX  INTEGER(1..4095)
    ACCESS  read-only
    STATUS  mandatory
    DESCRIPTION
      "This parameter specifies the X.25 packet lower-bound
      channel number for this physical access line.
      The default value is 1."
    ::= { x25ConfigEntry 15 }

  x25HighTwoWayChannel   OBJECT-TYPE
    SYNTAX  INTEGER(1..4095)
    ACCESS  read-only
    STATUS  mandatory
    DESCRIPTION
      "This parameter specifies the X.25 packet upper-bound
      channel number for this physical access line.
      Note: This value must be greater than the Low Two-Way
      Channel Number.
      The default value is 127."
    ::= { x25ConfigEntry 16 }

  x25UseCallingAddress   OBJECT-TYPE
    SYNTAX  INTEGER {
      yes(1),
      no(2)
      }
    ACCESS  read-only
    STATUS  mandatory
    DESCRIPTION
      "This parameter determines whether the DTE
      Address assigned to the port you are configuring
      should be included as a calling address in outgoing
      call packets.
      The default value is 'No'."
    ::= { x25ConfigEntry 17 }

  x25ForwardingUnit   OBJECT-TYPE
    SYNTAX  INTEGER {
      one(1),
      two(2),
      three(3),
      four(4),
      five(5),
      six(6),
      seven(7),
      eom(8)
      }
    ACCESS  read-only
    STATUS  mandatory
    DESCRIPTION
      "This parameter limits how many message packets
      can accumulate before the unit forwards them to
      higher bytes.
      The default value is 'EOM'."
    ::= { x25ConfigEntry 18 }

  x25DevicePacketSize   OBJECT-TYPE
    SYNTAX  INTEGER  {
        thirtytwo(32),
        onetwentyeight(128),
        twofiftsix(256),
        fivetwelve(512),
        onethousand(1024),
        none(1)
    }
    ACCESS  read-only
    STATUS  mandatory
    DESCRIPTION
      "When the sync unit makes a call on behalf of
      any configured device, the packet size determines
      parameter negotiation between the calling and the
      called packet handlers.
      Note: This parameter is not currently supported.
      do no change the default value.
      The default value is 'NONE'."
    ::= { x25ConfigEntry 19 }

  x25DeviceWindowSize   OBJECT-TYPE
    SYNTAX  INTEGER {
      one(1),
      two(2),
      three(3),
      four(4),
      five(5),
      six(6),
      seven(7),
      none(8)
    }
    ACCESS  read-only
    STATUS  mandatory
    DESCRIPTION
      "When the sync unit makes a call on behalf of
      any device, the window size determines parameter
      negotiation between the calling and the
      called packet handlers.
      Note: This parameter is not currently supported.
      do no change the default value.
      The default value is 'NONE'."
    ::= { x25ConfigEntry 20 }

  x25PlaceReverseChargeCalls   OBJECT-TYPE
    SYNTAX  INTEGER {
      yes(1),
      no(2)
      }
    ACCESS  read-only
    STATUS  mandatory
    DESCRIPTION
      "This parameter determines whether the Sync unit
      will place reverse charge requests on outgoing
      calls.
      The default value is 'No'."
    ::= { x25ConfigEntry 21 }

  x25AcceptReverseChargeCalls   OBJECT-TYPE
    SYNTAX  INTEGER {
      yes(1),
      no(2)
      }
    ACCESS  read-only
    STATUS  mandatory
    DESCRIPTION
      "This parameter determines whether the Sync unit
      will accept reverse charge requests from incoming
      calls.
      The default value is 'No'."
    ::= { x25ConfigEntry 22 }

  x25NPS   OBJECT-TYPE
    SYNTAX  INTEGER {
      yes(1),
      no(2)
      }
    ACCESS  read-only
    STATUS  mandatory
    DESCRIPTION
      "This parameter indicates if the QLLC conversion
      NODE is connecting to a NPSI front-end and is to
      take on a secondary role.

      The default value is 'No'."
    ::= { x25ConfigEntry 23 }

  x25CTS  OBJECT-TYPE
    SYNTAX  INTEGER {
      yes(1),
      no(2)
      }
    ACCESS  read-only
    STATUS  mandatory
    DESCRIPTION
      "Defines whether CTS is an input signal used to
      determine the port status. This parameter is applicable
      if clocking is set to external.  For internal clocking
      the parameter is ignored and DCD is asserted when port
      is enabled. The range is yes and no.

      The default value is 'No'."
    ::= { x25ConfigEntry 24 }

  x25DCD  OBJECT-TYPE
    SYNTAX  INTEGER {
      yes(1),
      no(2)
      }
    ACCESS  read-only
    STATUS  mandatory
    DESCRIPTION
      "Defines whether DCD is required as input signal
      or ignored. This parameter is applicable if the
      clocking is set to external.  For internal clocking
      the parameter is ignored and DCD is asserted when port
      is enabled. The range is yes and no.

      The default value is 'yes'."
    ::= { x25ConfigEntry 25 }

  x25DSR  OBJECT-TYPE
    SYNTAX  INTEGER {
      yes(1),
      no(2)
      }
    ACCESS  read-only
    STATUS  mandatory
    DESCRIPTION
      "Defines whether DSR is required as input signal
      or ignored. This parameter is applicable if the
      clocking is set to external.  For internal clocking
      the parameter is ignored and DSR is asserted when port
      is enabled. The range is yes and no.

      The default value is 'yes'."
    ::= { x25ConfigEntry 26 }

  x25DTR  OBJECT-TYPE
    SYNTAX  INTEGER {
      yes(1),
      no(2)
      }
    ACCESS  read-only
    STATUS  mandatory
    DESCRIPTION
      "Defines whether DTR is required as input signal
      or ignored. This parameter is applicable if the
      clocking is set to internal.  For external clocking
      the parameter is ignored and DTR is asserted when port
      is enabled. The range is yes and no.

      The default value is 'yes'."
    ::= { x25ConfigEntry 27 }

  x25RTS  OBJECT-TYPE
    SYNTAX  INTEGER {
      yes(1),
      no(2)
      }
    ACCESS  read-only
    STATUS  mandatory
    DESCRIPTION
      "Defines whether RTS is an input signal to determine
      the port status. This parameter is applicable if the
      clocking is set to internal.  For external clocking
      the parameter is ignored and RTS is asserted when port
      is enabled. The range is yes and no.

      The default value is 'No'."
    ::= { x25ConfigEntry 28 }

  x25ReturnClock  OBJECT-TYPE
    SYNTAX  INTEGER {
      yes(1),
      no(2),
      default(3)
      }
    ACCESS  read-only
    STATUS  mandatory
    DESCRIPTION
      "Defines whether Return Clock (SCTE) is available as
      input signal or ignored. This parameter is applicable
      if the clocking is set to internal. For external clocking
      the parameter is ignored. The range is yes and no.

      The default value is 'yes'."
    ::= { x25ConfigEntry 29 }

  x25IPAddress OBJECT-TYPE
    SYNTAX  IpAddress
    ACCESS  read-only
    STATUS  mandatory
    DESCRIPTION
      "This is the IP Address of this interface."
    ::= { x25ConfigEntry 30 }

  x25NetworkMask OBJECT-TYPE
    SYNTAX  IpAddress
    ACCESS  read-only
    STATUS  mandatory
    DESCRIPTION
      "This is the network mask to be used on this
      interface."
    ::= { x25ConfigEntry 31 }

  x25DefaultGatewayAddress OBJECT-TYPE
    SYNTAX  IpAddress
    ACCESS  read-only
    STATUS  mandatory
    DESCRIPTION
      "Default gateway address to be used when sending
      responses on this interface."
    ::= { x25ConfigEntry 32 }

  x25SecondDefaultGatewayAddress OBJECT-TYPE
    SYNTAX  IpAddress
    ACCESS  read-only
    STATUS  mandatory
    DESCRIPTION
      "Second Default gateway address to be used when sending
      responses on this interface."
    ::= { x25ConfigEntry 33 }

  --
  -- The X25 Port Statistics Table:
  --

  x25StatsTable  OBJECT-TYPE
    SYNTAX SEQUENCE OF X25StatsEntry
    ACCESS  not-accessible
    STATUS  mandatory
    DESCRIPTION
      "A table of X25 information."
    ::= { lineX25Group 2 }

  x25StatsEntry  OBJECT-TYPE
    SYNTAX  X25StatsEntry
    ACCESS  not-accessible
    STATUS  mandatory
    DESCRIPTION
      "An entry consisting of port information for a
      particular X25 port."
    INDEX { x25StatsPortIndex }
    ::= { x25StatsTable 1 }

  X25StatsEntry ::=
    SEQUENCE {
      x25StatsPortIndex
        INTEGER,
      x25PortType
        INTEGER,
      x25InFrames
        Counter,
      x25OutFrames
        Counter,
      x25CInFrames
        Counter,
      x25COutFrames
        Counter,
      x25FRMRInFrames
        Counter,
      x25FRMROutFrames
        Counter,
      x25Timeouts
        Counter,
      x25UFrames
        Counter,
      x25Samples
        Counter,
      x25Sum
        Counter,
      x25SumsQ
        Counter,
      x25DataInPkts
        Counter,
      x25DataOutPkts
        Counter,
      x25DataInChrs
        Counter,
      x25DataOutChrs
        Counter,
      x25QInPkts
        Counter,
      x25QOutPkts
        Counter,
      x25QInChrs
        Counter,
      x25QOutChrs
        Counter,
      x25SigInPkts
        Counter,
      x25SigOutPkts
        Counter,
      x25InResets
        Counter,
      x25OutResets
        Counter,
      x25InRestarts
        Counter,
      x25OutRestarts
        Counter
    }


  x25StatsPortIndex OBJECT-TYPE
    SYNTAX  INTEGER
    ACCESS  read-only
    STATUS  mandatory
    DESCRIPTION
      "The port number that uniquely identifies
      this X25 port.
      Current supported numbers on are 1-8."
    ::= { x25StatsEntry 1 }

  x25PortType  OBJECT-TYPE
    SYNTAX  INTEGER {
      xDTE-XLogicalDTE(7),
      xDCE-XLogicalDCE(8)
      }
    ACCESS  read-only
    STATUS  mandatory
    DESCRIPTION
      "The port type.

      XDCE () ports is a logical DCE device waits to
      receive an incoming call from the X.25 network.

      XDTE ports is a logical DTE device initiates a
      to the X.25 network.

      Note that all ports must currently be defined as
      the same time for a given unit (i.e. no mixing of
      XDCE and XDTE ports is allowed)."
    ::= { x25StatsEntry 2 }

  x25InFrames OBJECT-TYPE
    SYNTAX  Counter
    ACCESS  read-only
    STATUS  mandatory
    DESCRIPTION
      "The number of I-frames received."
    ::= { x25StatsEntry 3 }

  x25OutFrames OBJECT-TYPE
    SYNTAX  Counter
    ACCESS  read-only
    STATUS  mandatory
    DESCRIPTION
      "The number of I-frames sent."
    ::= { x25StatsEntry 4 }

  x25CInFrames OBJECT-TYPE
    SYNTAX  Counter
    ACCESS  read-only
    STATUS  mandatory
    DESCRIPTION
      "The number of Control-frames received."
    ::= { x25StatsEntry 5 }

  x25COutFrames OBJECT-TYPE
    SYNTAX  Counter
    ACCESS  read-only
    STATUS  mandatory
    DESCRIPTION
      "The number of Control-frames sent."
    ::= { x25StatsEntry 6 }

  x25FRMRInFrames OBJECT-TYPE
    SYNTAX  Counter
    ACCESS  read-only
    STATUS  mandatory
    DESCRIPTION
      "The number of FRMR-frames received."
    ::= { x25StatsEntry 7 }

  x25FRMROutFrames OBJECT-TYPE
    SYNTAX  Counter
    ACCESS  read-only
    STATUS  mandatory
    DESCRIPTION
      "The number of FRMR-frames sent."
    ::= { x25StatsEntry 8 }

  x25Timeouts  OBJECT-TYPE
    SYNTAX  Counter
    ACCESS  read-only
    STATUS  mandatory
    DESCRIPTION
      "The number of Timeouts."
    ::= { x25StatsEntry 9 }

  x25UFrames  OBJECT-TYPE
    SYNTAX  Counter
    ACCESS  read-only
    STATUS  mandatory
    DESCRIPTION
      "The number of Undefined Frames."
    ::= { x25StatsEntry 10 }

  x25Samples OBJECT-TYPE
    SYNTAX  Counter
    ACCESS  read-only
    STATUS  mandatory
    DESCRIPTION
      "The number of Samples."
    ::= { x25StatsEntry 11 }

  x25Sum OBJECT-TYPE
    SYNTAX  Counter
    ACCESS  read-only
    STATUS  mandatory
    DESCRIPTION
      "The number of Active Channels Sum."
    ::= { x25StatsEntry 12 }

  x25SumsQ OBJECT-TYPE
    SYNTAX  Counter
    ACCESS  read-only
    STATUS  mandatory
    DESCRIPTION
      "The number of Active Channels SumsQ."
    ::= { x25StatsEntry 13 }

  x25DataInPkts OBJECT-TYPE
    SYNTAX  Counter
    ACCESS  read-only
    STATUS  mandatory
    DESCRIPTION
      "The number of Data Packets received."
    ::= { x25StatsEntry 14 }

  x25DataOutPkts OBJECT-TYPE
    SYNTAX  Counter
    ACCESS  read-only
    STATUS  mandatory
    DESCRIPTION
      "The number of Data Packets sent."
    ::= { x25StatsEntry 15 }

  x25DataInChrs OBJECT-TYPE
    SYNTAX  Counter
    ACCESS  read-only
    STATUS  mandatory
    DESCRIPTION
      "The number of Data Characters received."
    ::= { x25StatsEntry 16 }

  x25DataOutChrs OBJECT-TYPE
    SYNTAX  Counter
    ACCESS  read-only
    STATUS  mandatory
    DESCRIPTION
      "The number of Data Characters sent."
    ::= { x25StatsEntry 17 }

  x25QInPkts OBJECT-TYPE
    SYNTAX  Counter
    ACCESS  read-only
    STATUS  mandatory
    DESCRIPTION
      "The number of Q-Packets received."
    ::= { x25StatsEntry 18 }

  x25QOutPkts OBJECT-TYPE
    SYNTAX  Counter
    ACCESS  read-only
    STATUS  mandatory
    DESCRIPTION
      "The number of Q-Packets sent."
    ::= { x25StatsEntry 19 }

  x25QInChrs OBJECT-TYPE
    SYNTAX  Counter
    ACCESS  read-only
    STATUS  mandatory
    DESCRIPTION
      "The number of Q-Characters received."
    ::= { x25StatsEntry 20 }

  x25QOutChrs OBJECT-TYPE
    SYNTAX  Counter
    ACCESS  read-only
    STATUS  mandatory
    DESCRIPTION
      "The number of Q-Characters sent."
    ::= { x25StatsEntry 21 }

  x25SigInPkts OBJECT-TYPE
    SYNTAX  Counter
    ACCESS  read-only
    STATUS  mandatory
    DESCRIPTION
      "The number of Sig-Packets received."
    ::= { x25StatsEntry 22 }

  x25SigOutPkts OBJECT-TYPE
    SYNTAX  Counter
    ACCESS  read-only
    STATUS  mandatory
    DESCRIPTION
      "The number of Sig-Packets sent."
    ::= { x25StatsEntry 23 }

  x25InResets OBJECT-TYPE
    SYNTAX  Counter
    ACCESS  read-only
    STATUS  mandatory
    DESCRIPTION
      "The number of Resets received."
    ::= { x25StatsEntry 24 }

  x25OutResets OBJECT-TYPE
    SYNTAX  Counter
    ACCESS  read-only
    STATUS  mandatory
    DESCRIPTION
      "The number of Resets sent."
    ::= { x25StatsEntry 25 }

  x25InRestarts OBJECT-TYPE
    SYNTAX  Counter
    ACCESS  read-only
    STATUS  mandatory
    DESCRIPTION
      "The number of Restarts received."
    ::= { x25StatsEntry 26 }

  x25OutRestarts OBJECT-TYPE
    SYNTAX  Counter
    ACCESS  read-only
    STATUS  mandatory
    DESCRIPTION
      "The number of Restarts sent."
    ::= { x25StatsEntry 27 }

  --
  -- The ALC Configuration Table:
  --

  alcConfigTable  OBJECT-TYPE
    SYNTAX SEQUENCE OF AlcConfigEntry
    ACCESS  not-accessible
    STATUS  mandatory
    DESCRIPTION
      "A table of ALC information."
    ::= { lineAlcGroup 1 }

  alcConfigEntry  OBJECT-TYPE
    SYNTAX  AlcConfigEntry
    ACCESS  not-accessible
    STATUS  mandatory
    DESCRIPTION
      "An entry consisting of port information for a
       particular ALC port."
    INDEX { alcConfigPortIndex }
    ::= { alcConfigTable 1 }

  AlcConfigEntry ::=
    SEQUENCE {
      alcConfigPortIndex
        INTEGER,
      alcConfigType
        INTEGER,
      alcNAUName
        DisplayString,
      alcInitState
        INTEGER,
      alcClocking
        INTEGER,
      alcPortSpeed
        INTEGER,
      alcLimitSegsCharsBetweenPolls
        INTEGER,
      alcNumberOfSegments
        INTEGER,
      alcNumberOfCharacters
        INTEGER,
      alcNumberOfNullSeg
        INTEGER,
      alcCTS
        INTEGER,
      alcDCD
        INTEGER,
      alcDSR
        INTEGER,
      alcDTR
        INTEGER,
      alcRTS
        INTEGER,
      alcReturnClock
        INTEGER
    }


  alcConfigPortIndex  OBJECT-TYPE
    SYNTAX  INTEGER
    ACCESS  read-only
    STATUS  mandatory
    DESCRIPTION
      "The port number that uniquely identifies
       this port.
       Current supported X.25 numbers are 1-4."
    ::= { alcConfigEntry 1 }


  alcConfigType  OBJECT-TYPE
    SYNTAX  INTEGER {
      tALC-TerminalALC(23),
      hALC-HostALC(24)
      }
    ACCESS  read-only
    STATUS  mandatory
    DESCRIPTION
      "The port type.

      The default  is Teminal ALC."
    ::= { alcConfigEntry 2 }

  alcNAUName   OBJECT-TYPE
    SYNTAX  DisplayString (SIZE(1..8))
    ACCESS  read-only
    STATUS  mandatory
    DESCRIPTION
      "The NAU name of this port.
      The default value for this field is all blank
      (filled with ASCII space 0x20 characters)."
    ::= { alcConfigEntry 3 }

  alcInitState  OBJECT-TYPE
    SYNTAX  INTEGER {
      in-service(1),
      out-of-service(2)
      }
    ACCESS  read-only
    STATUS  mandatory
    DESCRIPTION
      "The initial state of the X.25 port.

      If configured for 'in-service', then the ALC port will
      be brougt up automattically when the unit is powered
      up.

      If configured for 'out-of-service', the the ALC port must
      be manually enabled by operator intervention (i.e.
      enable command must be sent).

      The default value is 'inservice'."
    ::= { alcConfigEntry 4 }

  alcClocking  OBJECT-TYPE
    SYNTAX  INTEGER {
      external(1),
      internal(2)
      }
    ACCESS  read-only
    STATUS  mandatory
    DESCRIPTION
      "Clocking source for this port.
      Setting 'internal' will cause the
      port to emulate a physical DCE, and setting
      external will cause the port to emulate a
      physical DTE.
      The default value for this field is 'internal'."
    ::= { alcConfigEntry 5 }

  alcPortSpeed  OBJECT-TYPE
    SYNTAX  INTEGER {
      speed1200(12),
      speed2400(24),
      speed4800(48),
      speed9600(96),
      speed19200(192)
      }
    ACCESS  read-only
    STATUS  mandatory
    DESCRIPTION
      "The ports speed in 100 bits per second.
      The default value is 9600 bits per second."
    ::= { alcConfigEntry 6 }

  alcLimitSegsCharsBetweenPolls   OBJECT-TYPE
    SYNTAX  INTEGER {
      yes(1),
      no(2)
      }
    ACCESS  read-only
    STATUS  mandatory
    DESCRIPTION
      "This parameter specifies whether to limit
      the number of segments sent between pools.
      If this parameter is set to 'yes' the
      parameter 'Number of Segments' and
      'Number of Characters' should be configured
      appropriately.

      The defualt value is 'yes'."
    ::= { alcConfigEntry 7 }

  alcNumberOfSegments   OBJECT-TYPE
    SYNTAX  INTEGER (3..99)
    ACCESS  read-only
    STATUS  mandatory
    DESCRIPTION
      "This parameter specifies the maximum number
      of segments that may be sent between polls.
      This parameter is applicable only if
      'Limit SEGs/Chars between polls' is set to
      yes.

      The defualt value is 5."
    ::= { alcConfigEntry 8 }

  alcNumberOfCharacters   OBJECT-TYPE
    SYNTAX  INTEGER (500..9999)
    ACCESS  read-only
    STATUS  mandatory
    DESCRIPTION
      "This parameter specifies the maximum number
      of characters that may be sent between polls.
      This parameter is applicable only if
      'Limit SEGs/Chars between polls' is set to
      yes.

      The defualt value is 2000."
    ::= { alcConfigEntry 9 }

  alcNumberOfNullSeg   OBJECT-TYPE
    SYNTAX  INTEGER (0..10)
    ACCESS  read-only
    STATUS  mandatory
    DESCRIPTION
      "This parameter specifies the maximum number
      of null characters that may be sent between segments.

      The defualt value is 0."
    ::= { alcConfigEntry 10 }

  alcCTS  OBJECT-TYPE
    SYNTAX  INTEGER {
      yes(1),
      no(2)
      }
    ACCESS  read-only
    STATUS  mandatory
    DESCRIPTION
      "Defines whether CTS is an input signal used to
      determine the port status. This parameter is applicable
      if clocking is set to external.  For internal clocking
      the parameter is ignored and DCD is asserted when port
      is enabled. The range is yes and no.

      The default value is 'No'."
    ::= { alcConfigEntry 11 }

  alcDCD  OBJECT-TYPE
    SYNTAX  INTEGER {
      yes(1),
      no(2)
      }
    ACCESS  read-only
    STATUS  mandatory
    DESCRIPTION
      "Defines whether DCD is required as input signal
      or ignored. This parameter is applicable if the
      clocking is set to external.  For internal clocking
      the parameter is ignored and DCD is asserted when port
      is enabled. The range is yes and no.

      The default value is 'yes'."
    ::= { alcConfigEntry 12 }

  alcDSR  OBJECT-TYPE
    SYNTAX  INTEGER {
      yes(1),
      no(2)
      }
    ACCESS  read-only
    STATUS  mandatory
    DESCRIPTION
      "Defines whether DSR is required as input signal
      or ignored. This parameter is applicable if the
      clocking is set to external.  For internal clocking
      the parameter is ignored and DSR is asserted when port
      is enabled. The range is yes and no.

      The default value is 'yes'."
    ::= { alcConfigEntry 13 }

  alcDTR  OBJECT-TYPE
    SYNTAX  INTEGER {
      yes(1),
      no(2)
      }
    ACCESS  read-only
    STATUS  mandatory
    DESCRIPTION
      "Defines whether DTR is required as input signal
      or ignored. This parameter is applicable if the
      clocking is set to internal.  For external clocking
      the parameter is ignored and DTR is asserted when port
      is enabled. The range is yes and no.

      The default value is 'yes'."
    ::= { alcConfigEntry 14 }

  alcRTS  OBJECT-TYPE
    SYNTAX  INTEGER {
      yes(1),
      no(2)
      }
    ACCESS  read-only
    STATUS  mandatory
    DESCRIPTION
      "Defines whether RTS is an input signal to determine
      the port status. This parameter is applicable if the
      clocking is set to internal.  For external clocking
      the parameter is ignored and RTS is asserted when port
      is enabled. The range is yes and no.

      The default value is 'No'."
    ::= { alcConfigEntry 15 }

  alcReturnClock  OBJECT-TYPE
    SYNTAX  INTEGER {
      yes(1),
      no(2),
      default(3)
      }
    ACCESS  read-only
    STATUS  mandatory
    DESCRIPTION
      "Defines whether Return Clock (SCTE) is available as
      input signal or ignored. This parameter is applicable
      if the clocking is set to internal. For external clocking
      the parameter is ignored. The range is yes and no.

      The default value is 'yes'."
    ::= { alcConfigEntry 16 }

  --
  -- The Alc Port Statistics Table:
  --

  alcStatsTable  OBJECT-TYPE
    SYNTAX SEQUENCE OF AlcStatsEntry
    ACCESS  not-accessible
    STATUS  mandatory
    DESCRIPTION
      "A table of X25 information."
    ::= { lineAlcGroup 2 }

  alcStatsEntry  OBJECT-TYPE
    SYNTAX  AlcStatsEntry
    ACCESS  not-accessible
    STATUS  mandatory
    DESCRIPTION
      "An entry consisting of port information for a
      particular X25 port."
    INDEX { alcStatsPortIndex }
    ::= { alcStatsTable 1 }

  AlcStatsEntry ::=
    SEQUENCE {
      alcStatsPortIndex
        INTEGER,
      alcPortType
        INTEGER,
      alcRxOverruns
        Counter,
      alcBytesRx
        Counter,
      alcBytesTx
        Counter,
      alcBytesRxDisc
        Counter,
      alcBytesTxDisc
        Counter,
      alcPortFaults
        Counter,
      alcRcvCCCErrors
        Counter,
      alcPollTx
        Counter,
      alcResponseTimeouts
        Counter,
      alcSegRx
        Counter,
      alcSegTx
        Counter,
      alcSegRxDisc
        Counter,
      alcSegTxDisc
        Counter
    }


  alcStatsPortIndex OBJECT-TYPE
    SYNTAX  INTEGER
    ACCESS  read-only
    STATUS  mandatory
    DESCRIPTION
      "The port number that uniquely identifies
      this Alc port.
      Current supported numbers on are 1-8."
    ::= { alcStatsEntry 1 }

  alcPortType  OBJECT-TYPE
    SYNTAX  INTEGER {
      tALC-TerminalALC(23),
      hALC-HostALC(24)
      }
    ACCESS  read-only
    STATUS  mandatory
    DESCRIPTION
      "The port type.

      The default is Terminal Alc."
    ::= { alcStatsEntry 2 }

  alcRxOverruns OBJECT-TYPE
    SYNTAX  Counter
    ACCESS  read-only
    STATUS  mandatory
    DESCRIPTION
      "The number of Received Overruns."
    ::= { alcStatsEntry 3 }

  alcBytesRx OBJECT-TYPE
    SYNTAX  Counter
    ACCESS  read-only
    STATUS  mandatory
    DESCRIPTION
      "The number of Bytes Received."
    ::= { alcStatsEntry 4 }

  alcBytesTx OBJECT-TYPE
    SYNTAX  Counter
    ACCESS  read-only
    STATUS  mandatory
    DESCRIPTION
      "The number of Bytes Transmitted."
    ::= { alcStatsEntry 5 }

  alcBytesRxDisc OBJECT-TYPE
    SYNTAX  Counter
    ACCESS  read-only
    STATUS  mandatory
    DESCRIPTION
      "The number of Bytes Received."
    ::= { alcStatsEntry 6 }

  alcBytesTxDisc OBJECT-TYPE
    SYNTAX  Counter
    ACCESS  read-only
    STATUS  mandatory
    DESCRIPTION
      "The number of Bytes Transmitted."
    ::= { alcStatsEntry 7 }

  alcPortFaults OBJECT-TYPE
    SYNTAX  Counter
    ACCESS  read-only
    STATUS  mandatory
    DESCRIPTION
      "The number of Bytes Transmitted."
    ::= { alcStatsEntry 8 }

  alcRcvCCCErrors OBJECT-TYPE
    SYNTAX  Counter
    ACCESS  read-only
    STATUS  mandatory
    DESCRIPTION
      "The number of Bytes Transmitted."
    ::= { alcStatsEntry 9 }

  alcPollTx  OBJECT-TYPE
    SYNTAX  Counter
    ACCESS  read-only
    STATUS  mandatory
    DESCRIPTION
      "The number of Bytes Transmitted."
    ::= { alcStatsEntry 10 }

  alcResponseTimeouts  OBJECT-TYPE
    SYNTAX  Counter
    ACCESS  read-only
    STATUS  mandatory
    DESCRIPTION
      "The number of Bytes Transmitted."
    ::= { alcStatsEntry 11 }

  alcSegRx OBJECT-TYPE
    SYNTAX  Counter
    ACCESS  read-only
    STATUS  mandatory
    DESCRIPTION
      "The number of Segments Received."
    ::= { alcStatsEntry 12 }

  alcSegTx OBJECT-TYPE
    SYNTAX  Counter
    ACCESS  read-only
    STATUS  mandatory
    DESCRIPTION
      "The number of Segments Transmitted."
    ::= { alcStatsEntry 13 }

  alcSegRxDisc OBJECT-TYPE
    SYNTAX  Counter
    ACCESS  read-only
    STATUS  mandatory
    DESCRIPTION
      "The number of Received Segments Discarded."
    ::= { alcStatsEntry 14 }

  alcSegTxDisc OBJECT-TYPE
    SYNTAX  Counter
    ACCESS  read-only
    STATUS  mandatory
    DESCRIPTION
      "The number of Transmitted Segments Discarded."
    ::= { alcStatsEntry 15 }

  --
  -- The PU Control Group
  --

  puControlTable OBJECT-TYPE
    SYNTAX SEQUENCE OF PuControlEntry
    ACCESS  not-accessible
    STATUS  mandatory
    DESCRIPTION
      "A table for controlling lines and obtaining
      information."
    ::= { puControlGroup 1 }

  puControlEntry OBJECT-TYPE
    SYNTAX  PuControlEntry
    ACCESS  not-accessible
    STATUS  mandatory
    DESCRIPTION
      "An entry consisting of PU information for a
      particular port."
    INDEX { puControlLineIndex, puControlPUAddress }
    ::= { puControlTable 1 }

  PuControlEntry ::=
    SEQUENCE {
      puControlLineIndex
        INTEGER,
      puControlPUAddress
        OCTET STRING,
      puStatus
        INTEGER,
      puConnectionStatus
        INTEGER,
      puLastClearCode
        OCTET STRING,
      puControlFailureCode
        OCTET STRING,
      puControlNAUName
        DisplayString,
      puConnectionAttemptCount
        INTEGER,
      puStatusIgnored
        INTEGER,
      puStatusAcknowledged
        INTEGER,
      puLastDlciCleared
        INTEGER,
      puCurrentDlci
        INTEGER,
      puLastMACCleared
        PhysAddress,
      puCurrentMAC
        PhysAddress,
      puNetworkType
        INTEGER,
      puCurrentConnectionType
        INTEGER,
      puLastSVCCleared
        INTEGER,
      puCurrentSVC
        INTEGER,
      puLastLocalDTECleared
        OCTET STRING,
      puLastRemoteDTECleared
        OCTET STRING,
      puCurrentLocalDTE
        OCTET STRING,
      puCurrentRemoteDTE
        OCTET STRING,
      puIsDynamic
        INTEGER
    }

  puControlLineIndex OBJECT-TYPE
    SYNTAX  INTEGER
    ACCESS  read-only
    STATUS  mandatory
    DESCRIPTION
      "The port number that has a given PU."
    ::= { puControlEntry 1 }


  puControlPUAddress OBJECT-TYPE
    SYNTAX  OCTET STRING (SIZE(1))
    ACCESS  read-only
    STATUS  mandatory
    DESCRIPTION
      "The PU address in the range of 0x01 to 0xfe."
    ::= { puControlEntry 2 }

  puStatus  OBJECT-TYPE
    SYNTAX  INTEGER {
      enable(1),
      disable(2),
      failed(3),
      restart(4),
      enable-all(5)
      }
    ACCESS  read-write
    STATUS  mandatory
    DESCRIPTION
      "The status of the PU.
      To change status of a port an enable, enable all
      or disable may be set.


      Valid Return status are enable(d), disable(d),
      or failed.

      Commands:
      An enable command will attempt to bring up the PU.
      An enable all command will attempt to bring up
      the line and any lower layer entities (e.g. PUs).
      A disable command will disable the PU.

      Status:
      Enable(d) indicates the PU is enabled and running.
      Disable(d) indicates the PU has been disabled.
      Failed indicates the PU is enabled and not
      Running.
      For a access LAN/X25 PU, the status is enabled when
      the connection status is connected. Otherwise its status
      is failed."

    ::= { puControlEntry 3 }

  puConnectionStatus  OBJECT-TYPE
    SYNTAX  INTEGER  {
      connected(1),
      not-connected(2)
      }
    ACCESS  read-only
    STATUS  mandatory
    DESCRIPTION
      "The status of the LLC type 2 Connection for this
       SDLC PU."
    ::= { puControlEntry 4 }


  puLastClearCode    OBJECT-TYPE
    SYNTAX  OCTET STRING (SIZE(2))
    ACCESS  read-only
    STATUS  mandatory
    DESCRIPTION
      "A two octet field indicating the Last Clearing
      Cause and Diagnostic Field of the last failed
      connection attempt (a.k.a. call attempt) or
      active connection (a.k.a. session).

      For LLC type 2 connections the second octet (cause)
      is always 0.  The first octet (diagnostic)
      indicates the reason for the last connection failure.
      A value of 255 (xff) indicates that no call has ever
      been placed (e.g. PU never came up) or received. Even
      if the session call attempt is successful, the first
      octect still indicates the reason of LAST TIME when
      the session call attempt failed.

      See User's Guide for information"

    ::= { puControlEntry 5 }

  puControlFailureCode   OBJECT-TYPE
    SYNTAX  OCTET STRING (SIZE (2))
    ACCESS  read-only
    STATUS  mandatory
    DESCRIPTION
      "This entry contains the failure codes if the
      associated PU is in the failed state."
    ::= { puControlEntry 6 }

  puControlNAUName   OBJECT-TYPE
    SYNTAX  DisplayString (SIZE(1..8))
    ACCESS  read-only
    STATUS  mandatory
    DESCRIPTION
      "The NAU name of this PU.
      The default value for this field is all blank
      (filled with ASCII space 0x20 characters)."
    ::= { puControlEntry 7 }

  puConnectionAttemptCount   OBJECT-TYPE
    SYNTAX  INTEGER
    ACCESS  read-only
    STATUS  mandatory
    DESCRIPTION
      "The number of connection attempts performed. This
      count is set to zero at startup, and after every
      loss of an estabished session."
    ::= { puControlEntry 8 }

  puStatusIgnored   OBJECT-TYPE
    SYNTAX  INTEGER {
      yes (1),
      no  (2)
      }
    ACCESS  read-write
    STATUS  mandatory
    DESCRIPTION
      "This field is used for consolidating status of the
      unit. The status of this pu is not put into
      consideration when consolidating status of the
      unit if this field is set to yes."
    ::= { puControlEntry 9 }

  puStatusAcknowledged   OBJECT-TYPE
    SYNTAX  INTEGER {
      yes (1),
      no  (2)
      }
    ACCESS  read-write
    STATUS  mandatory
    DESCRIPTION
      "This field is used for consolidating status of the
      unit. When this field is set to yes, the unit will
      re-consolidate its status without putting the status
      of this pu into consideration. Subseqent status change
      of the pu will cause the unit to include it in
      computing the status of the unit. Setting this value to
      no has no effect."
    ::= { puControlEntry 10 }

  puLastDlciCleared   OBJECT-TYPE
    SYNTAX  INTEGER
    ACCESS  read-only
    STATUS  mandatory
    DESCRIPTION
      "Specifies the dlci that the last clear code was associated with.
       If the last clear code was not associated with a virtual route,
       i.e. the clear was associated with the lan for example, this field
       is set to 9999."
    ::= { puControlEntry 11 }

  puCurrentDlci   OBJECT-TYPE
    SYNTAX  INTEGER
    ACCESS  read-only
    STATUS  mandatory
    DESCRIPTION
      "Specifies the DLCI active for a session at this time.
       For LAN or X25 network interface, this field is set to 0"
    ::= { puControlEntry 12 }

  puLastMACCleared   OBJECT-TYPE
    SYNTAX  PhysAddress
    ACCESS  read-only
    STATUS  mandatory
    DESCRIPTION
      "Specifies the MAC address that the last clear code was associated with."
    ::= { puControlEntry 13 }

  puCurrentMAC   OBJECT-TYPE
    SYNTAX  PhysAddress
    ACCESS  read-only
    STATUS  mandatory
    DESCRIPTION
      "Specifies the MAC address that the current session is associated with.
       For X25 network type, this is set to 0."
 ::= { puControlEntry 14 }

puNetworkType  OBJECT-TYPE
    SYNTAX  INTEGER {
      xDTE-XLogicalDTE(7),
      xDCE-XLogicalDCE(8),
      ethernet-type(17),
      frame-relay-type(19),
      frame-relay-dialbackup-type(20),
      token-ring-type(21)
      }
    ACCESS  read-only
    STATUS  mandatory
    DESCRIPTION
      "Specifies netowrk type that the current session is associated with."
    ::= { puControlEntry 15 }

  puCurrentConnectionType   OBJECT-TYPE
    SYNTAX  INTEGER {
        dsp (1),
        qllc (2),
        llc2 (3)
        }
    ACCESS  read-only
    STATUS  mandatory
    DESCRIPTION
      "Specifies network layer that the current session is associated with."
    ::= { puControlEntry 16 }

  puLastSVCCleared   OBJECT-TYPE
    SYNTAX  INTEGER
    ACCESS  read-only
    STATUS  mandatory
    DESCRIPTION
      "Specifies the LCN that the last clear code is associated with.
       If the last clear code was not associated with a X25 SVC,
       i.e. the clear was associated with the lan for example, this field
       is set to 9999."
    ::= { puControlEntry 17 }

  puCurrentSVC   OBJECT-TYPE
    SYNTAX  INTEGER
    ACCESS  read-only
    STATUS  mandatory
    DESCRIPTION
      "Specifies the that the current session is associated with. For non
       X25 network type, this field is set to 0"
    ::= { puControlEntry 18 }

  puLastLocalDTECleared   OBJECT-TYPE
    SYNTAX  OCTET STRING
    ACCESS  read-only
    STATUS  mandatory
    DESCRIPTION
      "Specifies the local DTE address that the last clear code is associated with.
       For non X25 network type, this field is set to 0"
    ::= { puControlEntry 19 }

  puLastRemoteDTECleared   OBJECT-TYPE
    SYNTAX  OCTET STRING
    ACCESS  read-only
    STATUS  mandatory
    DESCRIPTION
      "Specifies the remote DTE address that the last clear code is associated with.
       For non X25 network type, this field is set to 0"
    ::= { puControlEntry 20 }

  puCurrentLocalDTE   OBJECT-TYPE
    SYNTAX  OCTET STRING
    ACCESS  read-only
    STATUS  mandatory
    DESCRIPTION
      "Specifies the local DTE address that the current session is associated with.
       For non X25 network type, this field is set to 0"
    ::= { puControlEntry 21 }

  puCurrentRemoteDTE   OBJECT-TYPE
    SYNTAX  OCTET STRING
    ACCESS  read-only
    STATUS  mandatory
    DESCRIPTION
      "Specifies the remote DTE address that the current session is associated with.
       For non X25 network type, this field is set to 0"
    ::= { puControlEntry 22 }

  puIsDynamic  OBJECT-TYPE
    SYNTAX  INTEGER {
      yes (1),
      no (2)
      }
    ACCESS  read-write
    STATUS  mandatory
    DESCRIPTION
      "The type of PU. YES means that the PU is a dynamic pu created
       by auto LLC. The puStatus for any dynamic PU must be enabled"
    ::= { puControlEntry 23 }

  --
  -- The PU Configuration Group
  --
  -- The PU Configuration Group contains information on the lines'
  -- configured PUs.

  sdlcPuConfigTable  OBJECT-TYPE
      SYNTAX  SEQUENCE OF SdlcPuConfigEntry
      ACCESS  not-accessible
      STATUS  mandatory
      DESCRIPTION
        "A list of PU entries."
      ::= { puSDLCGroup 1 }

  sdlcPuConfigEntry  OBJECT-TYPE
      SYNTAX  SdlcPuConfigEntry
      ACCESS  not-accessible
      STATUS  mandatory
      DESCRIPTION
        "This entry contains information about
        a given PU. The entry is indexed by the
        port number and the PU number."
      INDEX  { sdlcPuConfigLineIndex, sdlcPuConfigAddress }
      ::= { sdlcPuConfigTable 1 }

  SdlcPuConfigEntry ::=
    SEQUENCE {
      sdlcPuConfigLineIndex
        INTEGER,
      sdlcPuConfigAddress
        OCTET STRING,
      sdlcPuNAUName
        DisplayString,
      sdlcPuInitialState
        INTEGER,
      sdlcPuXID
        OCTET STRING,
      sdlcPuType
        INTEGER,
      sdlcPuGroupPollAddress
        OCTET STRING,
      sdlcPuConnectionID
        OCTET STRING,
      sdlcPuMAXOUT
        INTEGER,
      sdlcPuConnectType
        INTEGER
      }


  sdlcPuConfigLineIndex OBJECT-TYPE
    SYNTAX  INTEGER
    ACCESS  read-only
    STATUS  mandatory
    DESCRIPTION
      "The port number for which the line (CU)is configured
      (first level)."
    ::= { sdlcPuConfigEntry 1 }

  sdlcPuConfigAddress  OBJECT-TYPE
    SYNTAX  OCTET STRING (SIZE(1))
    ACCESS  read-only
    STATUS  mandatory
    DESCRIPTION
      "The PU address in the range of 0x00 to 0xfe."
    ::= { sdlcPuConfigEntry 2 }

  sdlcPuNAUName   OBJECT-TYPE
    SYNTAX  DisplayString (SIZE(1..8))
    ACCESS  read-only
    STATUS  mandatory
    DESCRIPTION
      "The NAU name of this PU.
      The default value for this field is all blank
      (filled with ASCII space 0x20 characters)."
    ::= { sdlcPuConfigEntry 3 }

  sdlcPuInitialState  OBJECT-TYPE
    SYNTAX  INTEGER  {
      in-service(1),
      out-of-service(2)
      }
    ACCESS  read-only
    STATUS  mandatory
    DESCRIPTION
      "The initial state of the PU.

      If configured for 'in-service', then the SDLC PU will
      be brougt up automattically when the unit is powered
      up.

      If configured for 'out-of-service', the the SDLC PU must
      be manually enabled by operator intervention (i.e.
      enable command must be sent).

      The default value is 'in-service'."
    ::= { sdlcPuConfigEntry 4 }

  sdlcPuXID    OBJECT-TYPE
    SYNTAX  OCTET STRING (SIZE(4))
    ACCESS  read-only
    STATUS  mandatory
    DESCRIPTION
      "The XID value for this PU.

      The XID is used to identify the PU during the LLC
      connection process to the remote Host or Gateway.
      If the field is configured to 0 then the unit
      will solicit the XID from the downstream PU
      and send the XID data received from SDLC to the XID
      data sent for the LLC connection process.
      If not sent to 0, then the unit will insert the
      data configured in the LLC sent to the host
      during the LLC connection process on behalf of
      the CU.

      For incoming LLC connections on Sync Research
      products this field is parsed to route the
      connection to the proper PU.

      The default value for this field is all zeroes
      (solicit XID from PU)."
    ::= { sdlcPuConfigEntry 5 }

  sdlcPuType    OBJECT-TYPE
    SYNTAX  INTEGER {
      type1(1),
      type2(2),
      type2-1(3),
      type4(4),
      type5(5)
      }
    ACCESS  read-only
    STATUS  mandatory
    DESCRIPTION
      "The SNA PU type.
      1 = PU type 1
      2 = PU type 2
      3 = PU type 2.1
      4 = PU type 4
      5 = PU type 5 (not supported, reserved)
      This parameter defaults to a value of 2."
    ::= { sdlcPuConfigEntry 6 }

  sdlcPuGroupPollAddress  OBJECT-TYPE
    SYNTAX  OCTET STRING (SIZE(1))
    ACCESS  read-only
    STATUS  mandatory
    DESCRIPTION
      "The PU's group address in the range of 0x01 to 0xfe.
      setting this value to 0 will disable the group poll
      feature for polling this and other PUs in a group.
      The default value for this field is 0."
    ::= { sdlcPuConfigEntry 7 }

  sdlcPuConnectionID   OBJECT-TYPE
    SYNTAX  OCTET STRING (SIZE(2))
    ACCESS  read-only
    STATUS  mandatory
    DESCRIPTION
      "This entry defines the Connection ID
      to a corresponding entry in the mapping table.

      The default value for this field is all zeroes."
    ::= { sdlcPuConfigEntry 8 }

  sdlcPuMAXOUT   OBJECT-TYPE
    SYNTAX  INTEGER
    ACCESS  read-only
    STATUS  mandatory
    DESCRIPTION
      "This entry defines the maximum number of outstanding
      I frames that the PU will allow.

      This field is applicable to TSDLC only."
    ::= { sdlcPuConfigEntry 9 }

  sdlcPuConnectType  OBJECT-TYPE
    SYNTAX  INTEGER {
      answer(1),
      originate(2)
      }
    ACCESS  read-only
    STATUS  mandatory
    DESCRIPTION
      "The SNA PU Connection type."
    ::= { sdlcPuConfigEntry 10 }

  --
  -- The SDLC PU Statistics Table:
  --
  -- The SDLC PU Statisctics table contains statistical information on the
  -- lines' configured PUs.

  sdlcPuStatsTable  OBJECT-TYPE
      SYNTAX  SEQUENCE OF SdlcPuStatsEntry
      ACCESS  not-accessible
      STATUS  mandatory
      DESCRIPTION
        "A list of PU statistics entries."
      ::= { puSDLCGroup 2 }

  sdlcPuStatsEntry  OBJECT-TYPE
      SYNTAX  SdlcPuStatsEntry
      ACCESS  not-accessible
      STATUS  mandatory
      DESCRIPTION
        "This entry contains information about
        a given PU. The entry is indexed by the
        port number and the PU number."
      INDEX  { sdlcPuStatsLineIndex, sdlcPuStatsAddress }
      ::= { sdlcPuStatsTable 1 }

  SdlcPuStatsEntry ::=
    SEQUENCE {
      sdlcPuStatsLineIndex
        INTEGER,
      sdlcPuStatsAddress
        OCTET STRING,
      sdlcPuInIFrames
        Counter,
      sdlcPuOutIFrames
        Counter,
      sdlcPuInRRFrames
        Counter,
      sdlcPuOutRRFrames
        Counter,
      sdlcPuInRNRFrames
        Counter,
      sdlcPuOutRNRFrames
        Counter,
      sdlcPuInXIDFrames
        Counter,
      sdlcPuOutXIDFrames
        Counter,
      sdlcPuInTESTFrames
        Counter,
      sdlcPuOutTESTFrames
        Counter,
      sdlcPuInSNRMFrames
        Counter,
      sdlcPuOutSNRMFrames
        Counter,
      sdlcPuInDISCFrames
        Counter,
      sdlcPuOutDISCFrames
        Counter,
      sdlcPuInDMFrames
        Counter,
      sdlcPuOutDMFrames
        Counter,
      sdlcPuInUAFrames
        Counter,
      sdlcPuOutUAFrames
        Counter,
      sdlcPuInFRMRFrames
        Counter,
      sdlcPuOutFRMRFrames
        Counter,
      sdlcPuInRDFrames
        Counter,
      sdlcPuOutRDFrames
        Counter,
      sdlcPuInUIFrames
        Counter,
      sdlcPuOutUIFrames
        Counter,
      sdlcPuReTxIFrames
        Counter,
      sdlcPuPollResponseTimeouts
        Counter
      }


  sdlcPuStatsLineIndex OBJECT-TYPE
    SYNTAX  INTEGER
    ACCESS  read-only
    STATUS  mandatory
    DESCRIPTION
      "The port number for which PU is configured on."
    ::= { sdlcPuStatsEntry 1 }

  sdlcPuStatsAddress  OBJECT-TYPE
    SYNTAX  OCTET STRING (SIZE(1))
    ACCESS  read-only
    STATUS  mandatory
    DESCRIPTION
      "The PU address in the range of 0x00 to 0xfe."
    ::= { sdlcPuStatsEntry 2 }

  sdlcPuInIFrames  OBJECT-TYPE
    SYNTAX  Counter
    ACCESS  read-only
    STATUS  mandatory
    DESCRIPTION
      "The number of I frames received on this PU."
    ::= { sdlcPuStatsEntry 3 }

  sdlcPuOutIFrames  OBJECT-TYPE
    SYNTAX  Counter
    ACCESS  read-only
    STATUS  mandatory
    DESCRIPTION
      "The number of I frames trasnmitted on this PU."
    ::= { sdlcPuStatsEntry 4 }

  sdlcPuInRRFrames  OBJECT-TYPE
    SYNTAX  Counter
    ACCESS  read-only
    STATUS  mandatory
    DESCRIPTION
      "The number of RR frames received on this PU."
    ::= { sdlcPuStatsEntry 5 }

  sdlcPuOutRRFrames  OBJECT-TYPE
    SYNTAX  Counter
    ACCESS  read-only
    STATUS  mandatory
    DESCRIPTION
      "The number of RR frames transmitted on this PU."
    ::= { sdlcPuStatsEntry 6 }

  sdlcPuInRNRFrames  OBJECT-TYPE
    SYNTAX  Counter
    ACCESS  read-only
    STATUS  mandatory
    DESCRIPTION
      "The number of RNR frames received on this PU."
    ::= { sdlcPuStatsEntry 7 }

  sdlcPuOutRNRFrames  OBJECT-TYPE
    SYNTAX  Counter
    ACCESS  read-only
    STATUS  mandatory
    DESCRIPTION
      "The number of RNR frames transmitted on this PU."
    ::= { sdlcPuStatsEntry 8 }

  sdlcPuInXIDFrames  OBJECT-TYPE
    SYNTAX  Counter
    ACCESS  read-only
    STATUS  mandatory
    DESCRIPTION
      "The number of XID frames received on this PU."
    ::= { sdlcPuStatsEntry 9 }

  sdlcPuOutXIDFrames  OBJECT-TYPE
    SYNTAX  Counter
    ACCESS  read-only
    STATUS  mandatory
    DESCRIPTION
      "The number of XID frames transmitted on this PU."
    ::= { sdlcPuStatsEntry 10 }

  sdlcPuInTESTFrames  OBJECT-TYPE
    SYNTAX  Counter
    ACCESS  read-only
    STATUS  mandatory
    DESCRIPTION
      "The number of TEST frames received on this PU."
    ::= { sdlcPuStatsEntry 11 }

  sdlcPuOutTESTFrames  OBJECT-TYPE
    SYNTAX  Counter
    ACCESS  read-only
    STATUS  mandatory
    DESCRIPTION
      "The number of TEST frames transmitted on this PU."
    ::= { sdlcPuStatsEntry 12 }

  sdlcPuInSNRMFrames  OBJECT-TYPE
    SYNTAX  Counter
    ACCESS  read-only
    STATUS  mandatory
    DESCRIPTION
      "The number of SNRM frames received on this PU."
    ::= { sdlcPuStatsEntry 13 }

  sdlcPuOutSNRMFrames  OBJECT-TYPE
    SYNTAX  Counter
    ACCESS  read-only
    STATUS  mandatory
    DESCRIPTION
      "The number of SNRM frames transmitted on this PU."
    ::= { sdlcPuStatsEntry 14 }


  sdlcPuInDISCFrames  OBJECT-TYPE
    SYNTAX  Counter
    ACCESS  read-only
    STATUS  mandatory
    DESCRIPTION
      "The number of DISC frames received on this PU."
    ::= { sdlcPuStatsEntry 15 }

  sdlcPuOutDISCFrames  OBJECT-TYPE
    SYNTAX  Counter
    ACCESS  read-only
    STATUS  mandatory
    DESCRIPTION
      "The number of DISC frames transmitted on this PU."
    ::= { sdlcPuStatsEntry 16 }

  sdlcPuInDMFrames  OBJECT-TYPE
    SYNTAX  Counter
    ACCESS  read-only
    STATUS  mandatory
    DESCRIPTION
      "The number of DM frames received on this PU."
    ::= { sdlcPuStatsEntry 17 }

  sdlcPuOutDMFrames  OBJECT-TYPE
    SYNTAX  Counter

    ACCESS  read-only
    STATUS  mandatory
    DESCRIPTION
      "The number of DM frames transmitted on this PU."
    ::= { sdlcPuStatsEntry 18 }

  sdlcPuInUAFrames  OBJECT-TYPE
    SYNTAX  Counter
    ACCESS  read-only
    STATUS  mandatory
    DESCRIPTION
      "The number of UA frames received on this PU."
    ::= { sdlcPuStatsEntry 19 }

  sdlcPuOutUAFrames  OBJECT-TYPE
    SYNTAX  Counter
    ACCESS  read-only
    STATUS  mandatory
    DESCRIPTION
      "The number of UA frames transmitted on this PU."
    ::= { sdlcPuStatsEntry 20 }

  sdlcPuInFRMRFrames  OBJECT-TYPE
    SYNTAX  Counter
    ACCESS  read-only
    STATUS  mandatory
    DESCRIPTION
      "The number of FRMR frames received on this PU."
    ::= { sdlcPuStatsEntry 21 }

  sdlcPuOutFRMRFrames  OBJECT-TYPE
    SYNTAX  Counter
    ACCESS  read-only
    STATUS  mandatory
    DESCRIPTION
      "The number of FRMR frames transmitted on this PU."
    ::= { sdlcPuStatsEntry 22 }

  sdlcPuInRDFrames  OBJECT-TYPE
    SYNTAX  Counter
    ACCESS  read-only
    STATUS  mandatory
    DESCRIPTION
      "The number of RD frames received on this PU."
    ::= { sdlcPuStatsEntry 23 }

  sdlcPuOutRDFrames  OBJECT-TYPE
    SYNTAX  Counter
    ACCESS  read-only
    STATUS  mandatory
    DESCRIPTION
      "The number of RD frames transmitted on this PU."
    ::= { sdlcPuStatsEntry 24 }

  sdlcPuInUIFrames  OBJECT-TYPE
    SYNTAX  Counter
    ACCESS  read-only
    STATUS  mandatory
    DESCRIPTION
      "The number of UI frames received on this PU."
    ::= { sdlcPuStatsEntry 25 }

  sdlcPuOutUIFrames  OBJECT-TYPE
    SYNTAX  Counter
    ACCESS  read-only
    STATUS  mandatory
    DESCRIPTION
      "The number of UI frames transmitted on this PU."
    ::= { sdlcPuStatsEntry 26 }

  sdlcPuReTxIFrames  OBJECT-TYPE
    SYNTAX  Counter
    ACCESS  read-only
    STATUS  mandatory
    DESCRIPTION
      "The number of re-transmitted I frames on this PU."
    ::= { sdlcPuStatsEntry 27 }

  sdlcPuPollResponseTimeouts OBJECT-TYPE
    SYNTAX  Counter
    ACCESS  read-only
    STATUS  mandatory
    DESCRIPTION
      "The number of PU Poll Response timeouts for this PU."
    ::= { sdlcPuStatsEntry 28 }

  --
  -- The Bisync PU Group
  --

  -- The Bisync PU Configuration Table:
  --

  bisyncPuConfigTable  OBJECT-TYPE
      SYNTAX  SEQUENCE OF BisyncPuConfigEntry
      ACCESS  not-accessible
      STATUS  mandatory
      DESCRIPTION
        "A list of Bisync CU entries."
      ::= { puBisyncGroup 1 }

  bisyncPuConfigEntry  OBJECT-TYPE
      SYNTAX  BisyncPuConfigEntry
      ACCESS  not-accessible
      STATUS  mandatory
      DESCRIPTION
        "This entry contains information about
        a given PU. The entry is indexed by the
        port number and the PU number."
      INDEX  { bisyncPuConfigLineIndex, bisyncPuConfigAddress }
      ::= { bisyncPuConfigTable 1 }

  BisyncPuConfigEntry ::=
    SEQUENCE {
      bisyncPuConfigLineIndex
        INTEGER,
      bisyncPuConfigAddress
        OCTET STRING,
      bisyncPuNAUName
        DisplayString,
      bisyncPuInitialState
        INTEGER,
      bisyncPuXID
        OCTET STRING,
      bisyncPuTargetHostType
        INTEGER,
      bisyncPuMaxData
        INTEGER,
      bisyncPuConnectionID
        OCTET STRING,
      bisyncPuConnectType
        INTEGER
    }


  bisyncPuConfigLineIndex OBJECT-TYPE
    SYNTAX  INTEGER
    ACCESS  read-only
    STATUS  mandatory
    DESCRIPTION
      "The port number for which PU is configured on."
    ::= { bisyncPuConfigEntry 1 }

  bisyncPuConfigAddress  OBJECT-TYPE
    SYNTAX  OCTET STRING (SIZE(1))
    ACCESS  read-only
    STATUS  mandatory
    DESCRIPTION
      "The PU address in the range of 0x00 to 0xfe."
    ::= { bisyncPuConfigEntry 2 }

  bisyncPuNAUName   OBJECT-TYPE
    SYNTAX  DisplayString (SIZE(1..8))
    ACCESS  read-only
    STATUS  mandatory
    DESCRIPTION
      "The NAU name of this PU.
      The default value for this field is all blank
      (filled with ASCII space 0x20 characters)."
    ::= { bisyncPuConfigEntry 3 }

  bisyncPuInitialState  OBJECT-TYPE
    SYNTAX  INTEGER  {
      in-service(1),
      out-of-service(2)
      }
    ACCESS  read-only
    STATUS  mandatory
    DESCRIPTION
      "The initial state of the PU.

      If configured for 'in-service', then the Bisync PU will
      be brougt up automattically when the unit is powered
      up.

      If configured for 'out-of-service', the the SDLC PU must
      be manually enabled by operator intervention (i.e.
      enable command must be sent).

      The default value is 'in-service'."
    ::= { bisyncPuConfigEntry 4 }

  bisyncPuXID    OBJECT-TYPE
    SYNTAX  OCTET STRING (SIZE(4))
    ACCESS  read-only
    STATUS  mandatory
    DESCRIPTION
      "The XID value for this PU.

      The XID is used to identify the PU during the LLC
      connection process to the remote Host or Gateway.

      The unit will insert the
      data configured in the LLC XID sent to the host
      during the LLC connection process on behalf of
      the CU.

      For bisync control units, this field is required
      as bisync cannot solicit an XID.

      For incoming LLC connections on Sync Research
      products this field is parsed to route the
      connection to the proper PU.

      The default value for this field is all zeroes."
    ::= { bisyncPuConfigEntry 5 }

  bisyncPuTargetHostType    OBJECT-TYPE
    SYNTAX  INTEGER {
      sna-host-type(1),
      bisync-host-type(2),
      ice-host-type(3)
      }
    ACCESS  read-only
    STATUS  mandatory
    DESCRIPTION
      "The Target Host type.
       This field specifies the target host type for TBSC
       and is applicable to BSC-to-SNA conversion only.

       This parameter defaults to a value of 2."
    ::= { bisyncPuConfigEntry 6 }

  bisyncPuMaxData   OBJECT-TYPE
    SYNTAX  INTEGER
    ACCESS  read-only
    STATUS  mandatory
    DESCRIPTION
      "This entry defines the SNA frame size which is
      the sum of SNA data and SNA header.  This value must
      match the MAXData configured for SNA host and is
      applicable to BSC-to-SNA conversion only.

      The default value is 521. The valid range  is 265,
      521, 777, 1033, 1289."
    ::= { bisyncPuConfigEntry 7 }

  bisyncPuConnectionID  OBJECT-TYPE
    SYNTAX  OCTET STRING (SIZE(2))
    ACCESS  read-only
    STATUS  mandatory
    DESCRIPTION
      "This entry defines the Connection ID
      to a corresponding entry in the mapping table.

      The default value for this field is all zeroes."
    ::= { bisyncPuConfigEntry 8 }

  bisyncPuConnectType  OBJECT-TYPE
    SYNTAX  INTEGER {
      answer(1),
      originate(2)
      }
    ACCESS  read-only
    STATUS  mandatory
    DESCRIPTION
      "The Bisync PU Connection type."
    ::= { bisyncPuConfigEntry 9 }

  --
  -- The Bisync PU Statistics Table:
  --
  -- The Bisync PU Statisctics table contains statistical information on
  -- the lines' configured PUs.

  bisyncPuStatsTable  OBJECT-TYPE
      SYNTAX  SEQUENCE OF BisyncPuStatsEntry
      ACCESS  not-accessible
      STATUS  mandatory
      DESCRIPTION
        "A list of PU statistics entries."
      ::= { puBisyncGroup 2 }

  bisyncPuStatsEntry  OBJECT-TYPE
      SYNTAX  BisyncPuStatsEntry
      ACCESS  not-accessible
      STATUS  mandatory
      DESCRIPTION
        "This entry contains information about
        a given PU. The entry is indexed by the
        port number and the PU number."
      INDEX  { bisyncPuStatsLineIndex, bisyncPuStatsAddress }
      ::= { bisyncPuStatsTable 1 }

  BisyncPuStatsEntry ::=
    SEQUENCE {
      bisyncPuStatsLineIndex
        INTEGER,
      bisyncPuStatsAddress
        OCTET STRING,
      bisyncPuInTransactions
        Counter,
      bisyncPuOutTransactions
        Counter,
      bisyncPuSlowPolls
        Counter,
      bisyncPuPolls
        Counter
      }


  bisyncPuStatsLineIndex OBJECT-TYPE
    SYNTAX  INTEGER
    ACCESS  read-only
    STATUS  mandatory
    DESCRIPTION
      "The port number for which PU is configured on."
    ::= { bisyncPuStatsEntry 1 }

  bisyncPuStatsAddress  OBJECT-TYPE
    SYNTAX  OCTET STRING (SIZE(1))
    ACCESS  read-only
    STATUS  mandatory
    DESCRIPTION
      "The PU address in the range of 0x00 to 0xfe."
    ::= { bisyncPuStatsEntry 2 }

  bisyncPuInTransactions OBJECT-TYPE
    SYNTAX  Counter
    ACCESS  read-only
    STATUS  mandatory
    DESCRIPTION
      "The number of PU Poll Response timeouts for this PU."
    ::= { bisyncPuStatsEntry 3 }

  bisyncPuOutTransactions OBJECT-TYPE
    SYNTAX  Counter
    ACCESS  read-only
    STATUS  mandatory
    DESCRIPTION
      "The number of PU Poll Response timeouts for this PU."
    ::= { bisyncPuStatsEntry 4 }

  bisyncPuSlowPolls OBJECT-TYPE
    SYNTAX  Counter
    ACCESS  read-only
    STATUS  mandatory
    DESCRIPTION
      "The number of PU slow polls for this PU."
    ::= { bisyncPuStatsEntry 5 }

  bisyncPuPolls OBJECT-TYPE
    SYNTAX  Counter
    ACCESS  read-only
    STATUS  mandatory
    DESCRIPTION
      "The number of PU Polls for this PU."
    ::= { bisyncPuStatsEntry 6 }


  --
  -- The Mapping PU Group
  --
  --                     ********
  -- This whole group is obsolete and is replaced by puRemoteGroup
  --                     ********
  --
  -- The Mapping PU Configuration Table contains mapping information
  -- on the lines' configured PUs.

  mappingPuConfigTable  OBJECT-TYPE
      SYNTAX  SEQUENCE OF MappingPuConfigEntry
      ACCESS  not-accessible
      STATUS  mandatory
      DESCRIPTION
         "This Table is obsolete.
         A list of PU mapping entries."
      ::= { puMappingGroup 1 }

  mappingPuConfigEntry  OBJECT-TYPE
      SYNTAX  MappingPuConfigEntry
      ACCESS  not-accessible
      STATUS  mandatory
      DESCRIPTION
        "This field is obsolete.
         This entry contains information about a given
         mapping PU. Each entry includes MAC/SAP
         information for a source PU and a similar
         information for the partner (mapped) PU.
         Depending upon whether the PU is LAN-attached,
         SDLC-attached or Frame Relay-attached, one
         or more fields may not apply.  Some fields,
         for example, mappingPuNAU, mappingPuXID,
         mappingPuConnectID are common to both end
         points.  The entry is indexed by the port
         number and the PU number."
      INDEX  { mappingPuConfigLineIndex, mappingPuConfigAddress }
      ::= { mappingPuConfigTable 1 }

  MappingPuConfigEntry ::=
    SEQUENCE {
      mappingPuConfigLineIndex
        INTEGER,
      mappingPuConfigAddress
        OCTET STRING,
      mappingPuSourceSAP
        OCTET STRING,
      mappingPuDestinationSAP
        OCTET STRING,
      mappingPuDestinationMAC
        PhysAddress,
      mappingPuPartnerConfigLineIndex
        INTEGER,
      mappingPuPartnerConfigAddress
        OCTET STRING,
      mappingPuPartnerSourceSAP
        OCTET STRING,
      mappingPuPartnerDestSAP
        OCTET STRING,
      mappingPuPartnerDestMAC
        PhysAddress,
      mappingPuNAU
        DisplayString,
      mappingPuConnectID
        OCTET STRING,
      mappingPuXID
        OCTET STRING,
      mappingPuDirectDLCI
        OCTET STRING,
      mappingPuLastClearCode
        OCTET STRING,
      mappingPuConnAttemptCnt
        Counter,
      mappingPuPartnerLastClearCode
        OCTET STRING,
      mappingPuPartnerConnAttemptCnt
        Counter
      }

  mappingPuConfigLineIndex OBJECT-TYPE
    SYNTAX  INTEGER
    ACCESS  read-only
    STATUS  mandatory
    DESCRIPTION
       "This field is obsolete.
       The port number for which PU is associated with.
       Port number 99 is a special value which is used to
       indicate NetView PU."
    ::= { mappingPuConfigEntry 1 }

  mappingPuConfigAddress  OBJECT-TYPE
    SYNTAX  OCTET STRING (SIZE(1))
    ACCESS  read-only
    STATUS  mandatory
    DESCRIPTION
       "This field is obsolete.
       The PU address in the range of 0x01 to 0xfe."
    ::= { mappingPuConfigEntry 2 }

  mappingPuSourceSAP  OBJECT-TYPE
    SYNTAX  OCTET STRING (SIZE(1))
    ACCESS  read-only
    STATUS  mandatory
    DESCRIPTION
       "This field is obsolete.
       The LLC source SAP value for this PU.

       Typically the source SAP will vary for each PU.
       This is due to the fact that most Sync products are
       configured to always call the same remote
       Token-Ring Host or Gateway for all connections
       configured.  This means that all the Destination
       SAP (usually set to 4) and Destination MAC addresses
       are the same, so the Source SAP field must be set
       to a unique value in order to uniquely identify
       the LLC connection to the Host.  (SNA does not allow
       multiplexing of PUs on one LLC connection.  Each
       PU must have its own LLC Type 2 connection.)
       This field must be set to a range between 04 and
       E8 hexadecimal and it must be evenly divisible by
       4 (802.2 LLC rules for user assigned SAPs).

       This field is not applicable in all cases, if not it
       returns a dummy value.

       This parameter defaults to a value of 4."
    ::= { mappingPuConfigEntry 3 }

  mappingPuDestinationSAP OBJECT-TYPE
    SYNTAX  OCTET STRING (SIZE(1))
    ACCESS  read-only
    STATUS  mandatory
    DESCRIPTION
       "This field is obsolete.
       The LLC Destination SAP value for this PU.

       For SNA typically the destination is almost
       always SAP 4.  However both Host Front Ends
       (e.g. 3745) or Gateways (e.g. 3174) allow SAPs
       to be configured for any value betwee 0x04 and
       0xEC as long as the SAP ID is a user assignable
       individual SAP ID (any value evenly divisable
       by 4).

       This field is not applicable to all cases.  If not it
       returns a dummy value.

       This parameter defaults to a value of 4."
    ::= { mappingPuConfigEntry 4 }

  mappingPuDestinationMAC OBJECT-TYPE
    SYNTAX  PhysAddress
    ACCESS  read-only
    STATUS  mandatory
    DESCRIPTION
       "This field is obsolete.
       The LAN Destination MAC address used in
       the LLC Type 2 connection for this PU.

       The Token-Ring format for this field is a 6 octet
       (48 bit) field represented in IEEE 802.5 format where
       the first bit transmitted is the most significant bit.
       The destination MAC must also be an 'Individual'
       address.  Therefore valid addresses are between
       000000000001 and 7FFFFFFFFFFF (an address of all
       zeroes is not supported).

       The Ethernet format for this field is a 6 octet
       (48 bit) field represented in IEEE 802.3 format where
       the first bit transmitted is the least significant bit.
       The destination MAC must also be an 'Individual'
       address.  Therefore valid addresses must start
       with the least significant bit equal to 0.  In other
       words, the first two digits must be in the set
       of 0x00, 0x02, 0x04, ... 0xFE (an address of all
       12 digits equal to zeroes is not supported).


       This field is not applicable to all cases.  If not it
       returns a dummy value."

    ::= { mappingPuConfigEntry 5 }


  mappingPuPartnerConfigLineIndex OBJECT-TYPE
    SYNTAX  INTEGER
    ACCESS  read-only
    STATUS  mandatory
    DESCRIPTION
       "This field is obsolete.
       The port number for the partner PU associated with
       source PU.  Port number 99 is a special value which
       is used to indicate NetView PU."
    ::= { mappingPuConfigEntry 6 }

  mappingPuPartnerConfigAddress  OBJECT-TYPE
    SYNTAX  OCTET STRING (SIZE(1))
    ACCESS  read-only
    STATUS  mandatory
    DESCRIPTION
       "This field is obsolete.
       The PU address of the partner PU in the range of
       0x01 to 0xfe."
    ::= { mappingPuConfigEntry 7 }

  mappingPuPartnerSourceSAP  OBJECT-TYPE
    SYNTAX  OCTET STRING (SIZE(1))
    ACCESS  read-only
    STATUS  mandatory
    DESCRIPTION
       "This field is obsolete.
       The LLC source SAP value for a partner PU.

       Typically the source SAP will vary for each PU.
       This is due to the fact that most Sync products are
       configured to always call the same remote
       Token-Ring Host or Gateway for all connections
       configured.  This means that all the Destination
       SAP (usually set to 4) and Destination MAC addresses
       are the same, so the Source SAP field must be set
       to a unique value in order to uniquely identify
       the LLC connection to the Host.  (SNA does not allow
       multiplexing of PUs on one LLC connection.  Each
       PU must have its own LLC Type 2 connection.)
       This field must be set to a range between 04 and
       E8 hexadecimal and it must be evenly divisible by
       4 (802.2 LLC rules for user assigned SAPs).

       This field is not applicable in all cases, if not it
       returns a dummy value.

       This parameter defaults to a value of 4."
    ::= { mappingPuConfigEntry 8 }

  mappingPuPartnerDestSAP OBJECT-TYPE
    SYNTAX  OCTET STRING (SIZE(1))
    ACCESS  read-only
    STATUS  mandatory
    DESCRIPTION
       "This field is obsolete.
       The LLC Destination SAP value for the partner PU.

       For SNA typically the destination is almost
       always SAP 4.  However both Host Front Ends
       (e.g. 3745) or Gateways (e.g. 3174) allow SAPs
       to be configured for any value betwee 0x04 and
       0xEC as long as the SAP ID is a user assignable
       individual SAP ID (any value evenly divisable
       by 4).

       This field is not applicable to all cases.  It
       returns a dummy value.

       This parameter defaults to a value of 4."
    ::= { mappingPuConfigEntry 9 }

  mappingPuPartnerDestMAC OBJECT-TYPE
    SYNTAX  PhysAddress
    ACCESS  read-only
    STATUS  mandatory
    DESCRIPTION
       "This field is obsolete.
       The LAN Destination MAC address used in
       the LLC Type 2 connection for the partner PU.

       The Token-Ring format for this field is a 6 octet
       (48 bit) field represented in IEEE 802.5 format where
       the first bit transmitted is the most significant bit.
       The destination MAC must also be an 'Individual'
       address.  Therefore valid addresses are between
       000000000001 and 7FFFFFFFFFFF (an address of all
       zeroes is not supported).

       The Ethernet format for this field is a 6 octet
       (48 bit) field represented in IEEE 802.3 format where
       the first bit transmitted is the least significant bit.
       The destination MAC must also be an 'Individual'
       address.  Therefore valid addresses must start
       with the least significant bit equal to 0.  In other
       words, the first two digits must be in the set
       of 0x00, 0x02, 0x04, ... 0xFE (an address of all
       12 digits equal to zeroes is not supported).

       This field is not applicable to all cases.  If not it
       returns a dummy value."

    ::= { mappingPuConfigEntry 10 }

  mappingPuNAU  OBJECT-TYPE
    SYNTAX  DisplayString (SIZE(1..8))
    ACCESS  read-only
    STATUS  mandatory
    DESCRIPTION
       "This field is obsolete.
       The NAU Name.  The NAU name is same for both the
             source PU and the partner PU.  It represents one
       physical PU in a network."
    ::= { mappingPuConfigEntry 11 }

  mappingPuConnectID OBJECT-TYPE
    SYNTAX  OCTET STRING (SIZE(2))
    ACCESS  read-only
    STATUS  mandatory
    DESCRIPTION
       "This field is obsolete.
       The connection ID. This must match a connection ID
       of an access line PU or another mapping PU Connection
        ID.

       The connnection ID is 0 if there is no mapping."
    ::= { mappingPuConfigEntry 12 }

  mappingPuXID    OBJECT-TYPE
    SYNTAX  OCTET STRING (SIZE(4))
    ACCESS  read-only
    STATUS  mandatory
    DESCRIPTION
                        "This field is obsolete.
       The XID value for this PU.

       The XID is used to identify the PU during the LLC
       connection process to the remote Host or Gateway.
       For incoming LLC connections on Sync Research
       products this field is parsed to route the
       connection to the proper PU.

              The XID is same for both the source PU and the partner
              PU.  It represents one physical PU in a network.

       The default value for this field is all zeroes."
    ::= { mappingPuConfigEntry 13 }

  mappingPuDirectDLCI OBJECT-TYPE
    SYNTAX  OCTET STRING (SIZE(4))
    ACCESS  read-only
    STATUS  mandatory
    DESCRIPTION
       "This field is obsolete.

       The Frame Relay DLCI used in
       the LLC Type 2 connection for this PU.

       The Frame Relay format for this field is a 2
       octet (16 bit) field represented in BCD format.
       A valid DLCI would be from 0001 to 1023 (0000 is
       reserved for AnnexD management. 1023 is reserved for
       LMI mangement.).

       This value is applicable to Frame Relay-attached PU
       only.  The field corresponds to a source port or a
       partner port depending upon whether the source PU is
       a Frame Relay-attached PU or the partner PU is
       Frame Relay-attached PU.  For Frame Relay-attached PU
       if this value is not configured, 0 is returned."

    ::= { mappingPuConfigEntry 14 }

  mappingPuLastClearCode OBJECT-TYPE
    SYNTAX  OCTET STRING (SIZE(2))
    ACCESS  read-only
    STATUS  mandatory
    DESCRIPTION
       "This field is obsolete.
       A two octet field indicating the Last Clearing
       Cause and Diagnostic Field of the last failed
       connection attempt (a.k.a. call attempt) or
       active connection (a.k.a. session) for this PU.

       For LLC type 2 connections the first octet (cause)
       is always 0.  The second octet (diagnostic)
       indicates the reason for the last connection failure.
       The second octet is set to 0 when a sucessful
       call has been placed, or if no call has ever been
       placed, or the clear is initiated by the partner for
       which mappingPuPartnerLastClearCode has the clear code.
       If the second octet is non-zero then it indicates
       the reason for the connection attempt failure.

       See User's Guide for more information"

    ::= { mappingPuConfigEntry 15 }


  mappingPuConnAttemptCnt   OBJECT-TYPE
    SYNTAX  Counter
    ACCESS  read-only
    STATUS  mandatory
    DESCRIPTION
       "This field is obsolete.
       The number of connection attempts performed for this
       PU. This count is set to zero at startup, and after
       every loss of an estabished session."

    ::= { mappingPuConfigEntry 16 }


  mappingPuPartnerLastClearCode OBJECT-TYPE
    SYNTAX  OCTET STRING (SIZE(2))
    ACCESS  read-only
    STATUS  mandatory
    DESCRIPTION
       "This field is obsolete.
       A two octet field indicating the Last Clearing
       Cause and Diagnostic Field of the last failed
       connection attempt (a.k.a. call attempt) or
       active connection (a.k.a. session) for the partner PU .

       For LLC type 2 connections the first octet (cause)
       is always 0.  The second octet (diagnostic)
       indicates the reason for the last connection failure.
       The second octet is set to 0 when a sucessful
       call has been placed, or if no call has ever been
       placed, or the clear is initiated by the partner for
                         which mappingPuLastClearCode has the clear code.
       If the second octet is non-zero then it indicates
       the reason for the connection attempt failure.

       See User's Guide for information"

    ::= { mappingPuConfigEntry 17 }

  mappingPuPartnerConnAttemptCnt   OBJECT-TYPE
    SYNTAX  Counter
    ACCESS  read-only
    STATUS  mandatory
    DESCRIPTION
      "This field is obsolete.
      The number of connection attempts performed for the
      partner PU. This count is set to zero at startup, and
                        after every loss of an estabished session."

    ::= { mappingPuConfigEntry 18 }


  --
  -- The Remote PU Group
  --
  -- The Mapping PU Configuration Table contains mapping information
  -- on the lines' configured PUs.

  remotePuConfigTable  OBJECT-TYPE
      SYNTAX  SEQUENCE OF RemotePuConfigEntry
      ACCESS  not-accessible
      STATUS  mandatory
      DESCRIPTION
        "A list of PU mapping entries."
      ::= { puRemoteGroup 1 }

  remotePuConfigEntry  OBJECT-TYPE
      SYNTAX  RemotePuConfigEntry
      ACCESS  not-accessible
      STATUS  mandatory
      DESCRIPTION
         "This entry contains information about a given
         mapping PU. Each entry includes MAC/SAP
         information for a source PU and a similar
         information for the partner (mapped) PU.
         Depending upon whether the PU is LAN-attached,
         SDLC-attached or Frame Relay-attached, one
         or more fields may not apply.  Some fields,
         for example, mappingPuNAU, mappingPuXID,
         mappingPuConnectID are common to both end
         points.  The entry is indexed by the port
         number and the PU number."
      INDEX  { accessPuConfigLineIndex, accessPuConfigAddress }
      ::= { remotePuConfigTable 1 }

  RemotePuConfigEntry ::=
    SEQUENCE {
      accessPuConfigLineIndex
        INTEGER,
      accessPuConfigAddress
        OCTET STRING,
      remotePuConfigLineIndex
        INTEGER,
      remotePuConfigAddress
        OCTET STRING,
      remotePuSourceSAP
        OCTET STRING,
      remotePuDestinationSAP
        OCTET STRING,
      remotePuMAC
        PhysAddress,
      remotePuPrimaryDLCI
        INTEGER,
      remotePuParallelDLCI
        INTEGER,
      remotePuAlternateDLCI
        INTEGER,
      remotePuAlternateMACAddress
        PhysAddress,
      remotePuTransmitPriority
        INTEGER,
      remotePuBroadcastAllDLCI
        INTEGER,
      remotePuLocalDTE
        OCTET STRING,
      remotePuRemoteDTE
        OCTET STRING
      }

  accessPuConfigLineIndex OBJECT-TYPE
    SYNTAX  INTEGER
    ACCESS  read-only
    STATUS  mandatory
    DESCRIPTION
      "The port number for which PU is associated with.
      Port number 99 is a special value which is used to
      indicate NetView PU."
    ::= { remotePuConfigEntry 1 }

  accessPuConfigAddress  OBJECT-TYPE
    SYNTAX  OCTET STRING (SIZE(1))
    ACCESS  read-only
    STATUS  mandatory
    DESCRIPTION
      "The PU address in the range of 0x01 to 0xfe.
      If the accessPuConfigLineIndex indicates a NetView PU
      then 01 is used to indicate the primary NetView PU and
      02 is used to indicate alternate NetView PU."
    ::= { remotePuConfigEntry 2 }

  remotePuConfigLineIndex OBJECT-TYPE
    SYNTAX  INTEGER
    ACCESS  read-only
    STATUS  mandatory
    DESCRIPTION
      "The port number for which an access PU, LCU or XCU is associated with."
    ::= { remotePuConfigEntry 3 }

  remotePuConfigAddress  OBJECT-TYPE
    SYNTAX  OCTET STRING (SIZE(1))
    ACCESS  read-only
    STATUS  mandatory
    DESCRIPTION
      "The access PU, LCU or XCU address in the range of 0x01 to 0xfe."
    ::= { remotePuConfigEntry 4 }

  remotePuSourceSAP  OBJECT-TYPE
    SYNTAX  OCTET STRING (SIZE(1))
    ACCESS  read-only
    STATUS  mandatory
    DESCRIPTION
      "The LLC source SAP value for this PU.

      Typically the source SAP will vary for each PU.
      This is due to the fact that most Sync products are
      configured to always call the same remote
      Token-Ring Host or Gateway for all connections
      configured.  This means that all the Destination
      SAP (usually set to 4) and Destination MAC addresses
      are the same, so the Source SAP field must be set
      to a unique value in order to uniquely identify
      the LLC connection to the Host.  (SNA does not allow
      multiplexing of PUs on one LLC connection.  Each
      PU must have its own LLC Type 2 connection.)
      This field must be set to a range between 04 and
      E8 hexadecimal and it must be evenly divisible by
      4 (802.2 LLC rules for user assigned SAPs).

      This field is not applicable in all cases, if not it
      returns a dummy value.

      This parameter defaults to a value of 4."
    ::= { remotePuConfigEntry 5 }

  remotePuDestinationSAP OBJECT-TYPE
    SYNTAX  OCTET STRING (SIZE(1))
     ACCESS  read-only
    STATUS  mandatory
    DESCRIPTION
      "The LLC Destination SAP value for this PU.

      For SNA typically the destination is almost
      always SAP 4.  However both Host Front Ends
      (e.g. 3745) or Gateways (e.g. 3174) allow SAPs
      to be configured for any value betwee 0x04 and
      0xEC as long as the SAP ID is a user assignable
      individual SAP ID (any value evenly divisable
      by 4).

      This field is not applicable to all cases.  If not it
      returns a dummy value.

      This parameter defaults to a value of 4."
    ::= { remotePuConfigEntry 6 }

  remotePuMAC OBJECT-TYPE
    SYNTAX  PhysAddress
    ACCESS  read-only
    STATUS  mandatory
    DESCRIPTION
      "The LAN Destination MAC address used in
      the LLC Type 2 connection for this PU.

      The Token-Ring format for this field is a 6 octet
      (48 bit) field represented in IEEE 802.5 format where
      the first bit transmitted is the most significant bit.
      The destination MAC must also be an 'Individual'
      address.  Therefore valid addresses are between
      000000000001 and 7FFFFFFFFFFF (an address of all
      zeroes is not supported).

      The Ethernet format for this field is a 6 octet
      (48 bit) field represented in IEEE 802.3 format where
      the first bit transmitted is the least significant bit.
      The destination MAC must also be an 'Individual'
      address.  Therefore valid addresses must start
      with the least significant bit equal to 0.  In other
      words, the first two digits must be in the set
      of 0x00, 0x02, 0x04, ... 0xFE (an address of all
      12 digits equal to zeroes is not supported).


      This field is not applicable to all cases.  If not it
      returns a dummy value."

    ::= { remotePuConfigEntry 7 }

  remotePuPrimaryDLCI   OBJECT-TYPE
    SYNTAX  INTEGER (0..1023)
    ACCESS  read-only
    STATUS  mandatory
    DESCRIPTION
      "The Frame Relay DLCI used in
      the LLC Type 2 connection for this PU.

      The Frame Relay format for this field is a 2
      octet (16 bit) field represented in BCD format.
      A valid DLCI would be from 0001 to 1023 (0000 is
      reserved for AnnexD management. 1023 is reserved for
      LMI mangement.).

      This value is applicable to Frame Relay-attached PU
      only.  The field corresponds to a source port or a
       partner port depending upon whether the source PU is
      a Frame Relay-attached PU or the partner PU is
      Frame Relay-attached PU.  For Frame Relay-attached PU
      if this value is not configured, 0 is returned."
    ::= { remotePuConfigEntry 8 }

  remotePuParallelDLCI   OBJECT-TYPE
    SYNTAX  INTEGER (0..1023)
    ACCESS  read-only
    STATUS  mandatory
    DESCRIPTION
      "Specifies a parallel DLCI indicating a virtual
      route in parallel to the primary DLCI path.  The
      parallel virtual route allows for session resiliency."
    ::= { remotePuConfigEntry 9 }

  remotePuAlternateDLCI   OBJECT-TYPE
    SYNTAX  INTEGER (0..1023)
    ACCESS  read-only
    STATUS  mandatory
    DESCRIPTION
      "Specifies an alternate DLCI indicating a virtual
      route to a disaster recovery site."
    ::= { remotePuConfigEntry 10 }

  remotePuAlternateMACAddress   OBJECT-TYPE
    SYNTAX  PhysAddress
    ACCESS  read-only
    STATUS  mandatory
    DESCRIPTION
      "Specifies an alternate MAC address indicating a virtual
      route to a disaster recovery site."
    ::= { remotePuConfigEntry 11 }

  remotePuTransmitPriority   OBJECT-TYPE
    SYNTAX  INTEGER
    ACCESS  read-only
    STATUS  mandatory
    DESCRIPTION
      "Specifies the transmission priority being
      URGENT, HIGH, MEDIUM or LOW for this PU."
    ::= { remotePuConfigEntry 12 }

  remotePuBroadcastAllDLCI   OBJECT-TYPE
    SYNTAX  INTEGER  {
      yes (1),
      no  (2)
      }
    ACCESS  read-only
    STATUS  mandatory
    DESCRIPTION
      "If this field is set to YES, after all specified
      paths are determined as unavailable, the session
      request is broadcast to all DLCIs.  IF the primary
      DLCI is set to 0, then this parameter is treated as
      YES regardless of its configured value."
    ::= { remotePuConfigEntry 13 }

  remotePuLocalDTE   OBJECT-TYPE
    SYNTAX  OCTET STRING
    ACCESS  read-only
    STATUS  mandatory
    DESCRIPTION
      "Specifies the local DTE address to match against any in-dial session
       for an access PU or LAN PU. For non X25 network type, this field is set to 0"
    ::= { remotePuConfigEntry 14 }

  remotePuRemoteDTE   OBJECT-TYPE
    SYNTAX  OCTET STRING
    ACCESS  read-only
    STATUS  mandatory
    DESCRIPTION
      "Specifies the remote DTE address that the X25 SVC connection uses for
       this access PU or LAN PU."
    ::= { remotePuConfigEntry 15 }

  --
  -- The Async PU Configuration Group
  --
  -- The PU Configuration Group contains information on the lines'
  -- configured PUs.

  asyncPuConfigTable  OBJECT-TYPE
      SYNTAX  SEQUENCE OF AsyncPuConfigEntry
      ACCESS  not-accessible
      STATUS  mandatory
      DESCRIPTION
        "A list of PU entries."
      ::= { puAsyncGroup 1 }

  asyncPuConfigEntry  OBJECT-TYPE
      SYNTAX  AsyncPuConfigEntry
      ACCESS  not-accessible
      STATUS  mandatory
      DESCRIPTION
        "This entry contains information about
        a given PU. The entry is indexed by the
        port number and the PU number."
      INDEX  { asyncPuConfigLineIndex, asyncPuConfigAddress }
      ::= { asyncPuConfigTable 1 }

  AsyncPuConfigEntry ::=
    SEQUENCE {
      asyncPuConfigLineIndex
        INTEGER,
      asyncPuConfigAddress
        OCTET STRING,
      asyncPuNAUName
        DisplayString,
      asyncPuInitialState
        INTEGER,
      asyncPuXID
        OCTET STRING,
      asyncPuConnectionID
        OCTET STRING,
      asyncPuConnectType
        INTEGER,
      asyncPuDeviceRangeLow
        OCTET STRING,
      asyncPuDeviceRangeHigh
        OCTET STRING
      }


  asyncPuConfigLineIndex OBJECT-TYPE
    SYNTAX  INTEGER
    ACCESS  read-only
    STATUS  mandatory
    DESCRIPTION
      "The port number for which the line (CU)is configured
       (first level)."
    ::= { asyncPuConfigEntry 1 }

  asyncPuConfigAddress  OBJECT-TYPE
    SYNTAX  OCTET STRING (SIZE(1))
    ACCESS  read-only
    STATUS  mandatory
    DESCRIPTION
      "The PU address in the range of 0x00 to 0xfe."
    ::= { asyncPuConfigEntry 2 }

  asyncPuNAUName   OBJECT-TYPE
    SYNTAX  DisplayString (SIZE(1..8))
    ACCESS  read-only
    STATUS  mandatory
    DESCRIPTION
      "The NAU name of this PU.
      The default value for this field is all blank
      (filled with ASCII space 0x20 characters)."
    ::= { asyncPuConfigEntry 3 }

  asyncPuInitialState  OBJECT-TYPE
    SYNTAX  INTEGER  {
      in-service(1),
      out-of-service(2)
      }
    ACCESS  read-only
    STATUS  mandatory
    DESCRIPTION
      "The initial state of the PU.

      If configured for 'in-service', then the async PU will
      be brougt up automattically when the unit is powered
      up.

      If configured for 'out-of-service', the the async PU must
      be manually enabled by operator intervention (i.e.
      enable command must be sent).

      The default value is 'in-service'."
    ::= { asyncPuConfigEntry 4 }

  asyncPuXID    OBJECT-TYPE
    SYNTAX  OCTET STRING (SIZE(4))
    ACCESS  read-only
    STATUS  mandatory
    DESCRIPTION
      "The XID value for this PU.

      The XID is used to identify the PU during the LLC
      connection process to the remote Host or Gateway.
      If the field is configured to 0 then the unit
      will solicit the XID from the downstream PU
      and send the XID data received from async to the XID
      data sent for the LLC connection process.
      If not sent to 0, then the unit will insert the
      data configured in the LLC sent to the host
      during the LLC connection process on behalf of
      the CU.

      For incoming LLC connections on Sync Research
      products this field is parsed to route the
      connection to the proper PU.

      The default value for this field is all zeroes
      (solicit XID from PU)."
    ::= { asyncPuConfigEntry 5 }

  asyncPuConnectionID  OBJECT-TYPE
    SYNTAX  OCTET STRING (SIZE(2))
    ACCESS  read-only
    STATUS  mandatory
    DESCRIPTION
      "This entry defines the Connection ID
      to a corresponding entry in the mapping table.

      The default value for this field is all zeroes."
    ::= { asyncPuConfigEntry 6 }

  asyncPuConnectType  OBJECT-TYPE
    SYNTAX  INTEGER {
      answer(1),
      originate(2)
      }
    ACCESS  read-only
    STATUS  mandatory
    DESCRIPTION
      "The Async PU Connection type."
    ::= { asyncPuConfigEntry 7 }

  asyncPuDeviceRangeLow  OBJECT-TYPE
    SYNTAX  OCTET STRING (SIZE(1))
    ACCESS  read-only
    STATUS  mandatory
    DESCRIPTION
      "The device range number low specifies the low number
      of a range one or more device addresses for which
      the data to be routed via the connection information
      (i.e. Connection ID and XID) contained in an individual
      CU record. This number must be less than or equal to
      the deviec range number high.
      This field is in the range of 0x00 to 0xff."
     ::= { asyncPuConfigEntry 8 }

  asyncPuDeviceRangeHigh  OBJECT-TYPE
    SYNTAX  OCTET STRING (SIZE(1))
    ACCESS  read-only
    STATUS  mandatory
    DESCRIPTION
      "The device range number high specifies the high
      number of a range of one or more device addresses for
      which the data to be routed via the connection
      information (i.e. Connection ID and XID) contained
      in an individual CU record. This number must be
      greater than or equal to the device range number low.
      This field is in the range of 0x00 to 0xff."
    ::= { asyncPuConfigEntry 9 }

  --
  -- The Async PU Statistics Table:
  --
  -- The Async PU Statisctics table contains statistical information on the
  -- lines' configured PUs.

  asyncPuStatsTable  OBJECT-TYPE
      SYNTAX  SEQUENCE OF AsyncPuStatsEntry
      ACCESS  not-accessible
      STATUS  mandatory
      DESCRIPTION
        "A list of PU statistics entries."
      ::= { puAsyncGroup 2 }

  asyncPuStatsEntry  OBJECT-TYPE
      SYNTAX  AsyncPuStatsEntry
      ACCESS  not-accessible
      STATUS  mandatory
      DESCRIPTION
        "This entry contains information about
        a given PU. The entry is indexed by the
        port number and the PU number."
      INDEX  { asyncPuStatsLineIndex, asyncPuStatsAddress }
      ::= { asyncPuStatsTable 1 }

  AsyncPuStatsEntry ::=
    SEQUENCE {
      asyncPuStatsLineIndex
        INTEGER,
      asyncPuStatsAddress
        OCTET STRING,
      asyncPuInChars
        Counter,
      asyncPuOutChars
        Counter,
      asyncPuInMessages
        Counter,
      asyncPuOutMessages
        Counter
      }


  asyncPuStatsLineIndex OBJECT-TYPE
    SYNTAX  INTEGER
    ACCESS  read-only
    STATUS  mandatory
    DESCRIPTION
      "The port number for which PU is configured on."
    ::= { asyncPuStatsEntry 1 }

  asyncPuStatsAddress  OBJECT-TYPE
    SYNTAX  OCTET STRING (SIZE(1))
    ACCESS  read-only
    STATUS  mandatory
    DESCRIPTION
      "The PU address in the range of 0x00 to 0xfe."
    ::= { asyncPuStatsEntry 2 }

  asyncPuInChars OBJECT-TYPE
    SYNTAX  Counter
    ACCESS  read-only
    STATUS  mandatory
    DESCRIPTION
      "The number of characters received for this PU."
    ::= { asyncPuStatsEntry 3 }

  asyncPuOutChars  OBJECT-TYPE
    SYNTAX  Counter
    ACCESS  read-only
    STATUS  mandatory
    DESCRIPTION
      "The number of characters transmitted to this PU."
    ::= { asyncPuStatsEntry 4 }

  asyncPuInMessages  OBJECT-TYPE
    SYNTAX  Counter
    ACCESS  read-only
    STATUS  mandatory
    DESCRIPTION
      "The number of messages received from this PU."
    ::= { asyncPuStatsEntry 5 }

  asyncPuOutMessages  OBJECT-TYPE
    SYNTAX  Counter
    ACCESS  read-only
    STATUS  mandatory
    DESCRIPTION
      "The number of messages transmitted to this PU."
    ::= { asyncPuStatsEntry 6 }

  --
  -- The LAN PU Configuration Group
  --
  -- The PU Configuration Group contains information on the lan'
  -- configured PUs.

  lanPuConfigTable  OBJECT-TYPE
      SYNTAX  SEQUENCE OF LanPuConfigEntry
      ACCESS  not-accessible
      STATUS  mandatory
      DESCRIPTION
        "A list of PU entries."
      ::= { puLanGroup 1 }

  lanPuConfigEntry  OBJECT-TYPE
      SYNTAX  LanPuConfigEntry
      ACCESS  not-accessible
      STATUS  mandatory
      DESCRIPTION
        "This entry contains information about
        a given PU. The entry is indexed by the
        port number and the PU number."
      INDEX  { lanPuConfigLineIndex, lanPuConfigAddress }
      ::= { lanPuConfigTable 1 }

  LanPuConfigEntry ::=
    SEQUENCE {
      lanPuConfigLineIndex
        INTEGER,
      lanPuConfigAddress
        OCTET STRING,
      lanPuNAUName
        DisplayString,
      lanPuXID
        OCTET STRING,
      lanPuConnectionID
        OCTET STRING,
      lanPuSourceSAP
        OCTET STRING,
      lanPuDestinationSAP
        OCTET STRING,
      lanPuMAC
        PhysAddress,
      lanPuAlternateMACAddress
        PhysAddress
      }

  lanPuConfigLineIndex OBJECT-TYPE
    SYNTAX  INTEGER
    ACCESS  read-only
    STATUS  mandatory
    DESCRIPTION
      "The port number for which the line (CU)is configured
     (first level)."
    ::= { lanPuConfigEntry 1 }

  lanPuConfigAddress  OBJECT-TYPE
    SYNTAX  OCTET STRING (SIZE(1))
    ACCESS  read-only
    STATUS  mandatory
    DESCRIPTION
      "The PU address in the range of 0x00 to 0xff."
    ::= { lanPuConfigEntry 2 }

  lanPuNAUName   OBJECT-TYPE
    SYNTAX  DisplayString (SIZE(1..8))
    ACCESS  read-only
    STATUS  mandatory
    DESCRIPTION
       "The NAU name of this PU.
      The default value for this field is all blank
      (filled with ASCII space 0x20 characters)."
    ::= { lanPuConfigEntry 3 }

  lanPuXID    OBJECT-TYPE
    SYNTAX  OCTET STRING (SIZE(4))
    ACCESS  read-only
    STATUS  mandatory
    DESCRIPTION
      "The XID value for this PU.

      The XID is used to identify the PU during the LLC
      connection process to the remote Host or Gateway.
      If the field is configured to 0 then the unit
      will solicit the XID from the downstream PU
      and send the XID data received from async to the XID
      data sent for the LLC connection process.
      If not sent to 0, then the unit will insert the
      data configured in the LLC sent to the host
      during the LLC connection process on behalf of
      the CU.

      For incoming LLC connections on Sync Research
      products this field is parsed to route the
      connection to the proper PU."

    ::= { lanPuConfigEntry 4 }

  lanPuConnectionID  OBJECT-TYPE
    SYNTAX  OCTET STRING (SIZE(2))
    ACCESS  read-only
    STATUS  mandatory
    DESCRIPTION
      "This entry defines the Connection ID
       to a corresponding entry in the mapping table.

       The default value for this field is all zeroes."
    ::= { lanPuConfigEntry 5 }

  lanPuSourceSAP  OBJECT-TYPE
    SYNTAX  OCTET STRING (SIZE(1))
    ACCESS  read-only
    STATUS  mandatory
    DESCRIPTION
      "The LLC source SAP value for this PU.

       Typically the source SAP will vary for each PU.
       This is due to the fact that most Sync products are
       configured to always call the same remote
       Token-Ring Host or Gateway for all connections
       configured.  This means that all the Destination
       SAP (usually set to 4) and Destination MAC addresses
       are the same, so the Source SAP field must be set
       to a unique value in order to uniquely identify
       the LLC connection to the Host.  (SNA does not allow
       multiplexing of PUs on one LLC connection.  Each
       PU must have its own LLC Type 2 connection.)
       This field must be set to a range between 04 and
       E8 hexadecimal and it must be evenly divisible by
       4 (802.2 LLC rules for user assigned SAPs).

       This field is not applicable in all cases, if not it
       returns a dummy value.

       This parameter defaults to a value of 4."
    ::= { lanPuConfigEntry 6 }

  lanPuDestinationSAP OBJECT-TYPE
    SYNTAX  OCTET STRING (SIZE(1))
    ACCESS  read-only
    STATUS  mandatory
    DESCRIPTION
      "The LLC Destination SAP value for this PU.

       For SNA typically the destination is almost
       always SAP 4.  However both Host Front Ends
       (e.g. 3745) or Gateways (e.g. 3174) allow SAPs
       to be configured for any value betwee 0x04 and
       0xEC as long as the SAP ID is a user assignable
       individual SAP ID (any value evenly divisable
       by 4).

       This field is not applicable to all cases.  If not it
       returns a dummy value.

       This parameter defaults to a value of 4."
    ::= { lanPuConfigEntry 7 }

  lanPuMAC OBJECT-TYPE
    SYNTAX  PhysAddress
    ACCESS  read-only
    STATUS  mandatory
    DESCRIPTION
      "The LAN Destination MAC address used in
       the LLC Type 2 connection for this PU.

       The Token-Ring format for this field is a 6 octet
       (48 bit) field represented in IEEE 802.5 format where
       the first bit transmitted is the most significant bit.
       The destination MAC must also be an 'Individual'
       address.  Therefore valid addresses are between
       000000000001 and 7FFFFFFFFFFF (an address of all
       zeroes is not supported).

       The Ethernet format for this field is a 6 octet
       (48 bit) field represented in IEEE 802.3 format where
       the first bit transmitted is the least significant bit.
       The destination MAC must also be an 'Individual'
       address.  Therefore valid addresses must start
       with the least significant bit equal to 0.  In other
       words, the first two digits must be in the set
       of 0x00, 0x02, 0x04, ... 0xFE (an address of all
       12 digits equal to zeroes is not supported).


       This field is not applicable to all cases.  If not it
       returns a dummy value."

    ::= { lanPuConfigEntry 8 }

  lanPuAlternateMACAddress   OBJECT-TYPE
    SYNTAX  PhysAddress
    ACCESS  read-only
    STATUS  mandatory
    DESCRIPTION
      "Specifies the second destination MAC address for a disaster
      recovery site."
    ::= { lanPuConfigEntry 9 }

  --
  -- The PU Configuration Group
  --
  -- The PU Configuration Group contains information on the lines'
  -- configured PUs.

  x25PuConfigTable  OBJECT-TYPE
      SYNTAX  SEQUENCE OF X25PuConfigEntry
      ACCESS  not-accessible
      STATUS  mandatory
      DESCRIPTION
        "A list of PU entries."
      ::= { puX25Group 1 }

  x25PuConfigEntry  OBJECT-TYPE
      SYNTAX  X25PuConfigEntry
      ACCESS  not-accessible
      STATUS  mandatory
      DESCRIPTION
        "This entry contains information about
        a given PU. The entry is indexed by the
        port number and the PU number."
      INDEX  { x25PuConfigLineIndex, x25PuConfigAddress }
      ::= { x25PuConfigTable 1 }

  X25PuConfigEntry ::=
    SEQUENCE {
      x25PuConfigLineIndex
        INTEGER,
      x25PuConfigAddress
        OCTET STRING,
      x25PuNAUName
        DisplayString,
      x25PuConnectionID
        OCTET STRING,
      x25PuXID
        OCTET STRING,
      x25PuSolicitXID
        INTEGER,
      x25PuSourceAddress
        OCTET STRING,
      x25PuRemoteDTEAddress
        OCTET STRING
      }

  x25PuConfigLineIndex OBJECT-TYPE
    SYNTAX  INTEGER
    ACCESS  read-only
    STATUS  mandatory
    DESCRIPTION
      "The port number for which PU is configured on."
    ::= { x25PuConfigEntry 1 }

  x25PuConfigAddress  OBJECT-TYPE
    SYNTAX  OCTET STRING (SIZE(1))
    ACCESS  read-only
    STATUS  mandatory
    DESCRIPTION
      "The PU address in the range of 0x00 to 0xfe."
    ::= { x25PuConfigEntry 2 }

  x25PuNAUName   OBJECT-TYPE
    SYNTAX  DisplayString (SIZE(1..8))
    ACCESS  read-only
    STATUS  mandatory
    DESCRIPTION
      "The NAU name of this PU.
      The default value for this field is all blank
      (filled with ASCII space 0x20 characters)."
    ::= { x25PuConfigEntry 3 }

  x25PuConnectionID  OBJECT-TYPE
    SYNTAX  OCTET STRING (SIZE(2))
    ACCESS  read-only
    STATUS  mandatory
    DESCRIPTION
      "This entry defines the Connection ID
       to a corresponding entry in the mapping table.

       The default value for this field is all zeroes."
    ::= { x25PuConfigEntry 4 }

  x25PuXID    OBJECT-TYPE
    SYNTAX  OCTET STRING (SIZE(4))
    ACCESS  read-only
    STATUS  mandatory
    DESCRIPTION
      "The XID value for this PU.

      The XID set the CU identification used to establish
      and negotiate PU-application sessions.  If the PU
      cannot respond to an XID request from the Host, you
      can configure the Sync unit to supply the XID for the
      PU by enabling Solicit XID.

      The default value for this field is all zeroes
      (solicit XID from PU)."
    ::= { x25PuConfigEntry 5 }

  x25PuSolicitXID    OBJECT-TYPE
    SYNTAX  INTEGER {
      yes(1),
      no(2)
      }
    ACCESS  read-only
    STATUS  mandatory
    DESCRIPTION
      "This parameter enables or disables soliciting an
      XID exchange between the Host and DSPU.  This
      determines whether the Sync unit will solicit an
      XID to the X.25-attached PU.
      This parameter defaults to a value of 'Yes'."
    ::= { x25PuConfigEntry 6 }

  x25PuSourceAddress  OBJECT-TYPE
    SYNTAX  OCTET STRING
    ACCESS  read-only
    STATUS  mandatory
    DESCRIPTION
      "The paramter specifies the Source Address. This is
      used to match DTE address."
    ::= { x25PuConfigEntry 7 }

  x25PuRemoteDTEAddress  OBJECT-TYPE
    SYNTAX  OCTET STRING
    ACCESS  read-only
    STATUS  mandatory
    DESCRIPTION
      "The paramter specifies a DTE address on the
      connection's remote end enabling the Host to initiate
      a session.

      If you would rather have the X.25 PU initiate
      the session(indial), do not specify a DTE Address.

      If the LAN is the incoming session path for this
      LCU, you do not need to configure this parameter if
      you are using XIDs to set up a connection.

      The default value for this field is NONE."
    ::= { x25PuConfigEntry  8 }

  --
  -- The PU Configuration Group
  --
  -- The PU Configuration Group contains information on the lines'
  -- configured PUs.

  alcPuConfigTable  OBJECT-TYPE
      SYNTAX  SEQUENCE OF AlcPuConfigEntry
      ACCESS  not-accessible
      STATUS  mandatory
      DESCRIPTION
        "A list of PU entries."
      ::= { puAlcGroup 1 }

  alcPuConfigEntry  OBJECT-TYPE
      SYNTAX  AlcPuConfigEntry
      ACCESS  not-accessible
      STATUS  mandatory
      DESCRIPTION
        "This entry contains information about
        a given PU. The entry is indexed by the
        port number and the PU number."
      INDEX  { alcPuConfigAddress }
      ::= { alcPuConfigTable 1 }

  AlcPuConfigEntry ::=
    SEQUENCE {
      alcPuConfigLineIndex
        INTEGER,
      alcPuConfigAddress
        OCTET STRING,
      alcPuNAUName
        DisplayString,
      alcPuCSS
        INTEGER,
      alcPuConnectionID
        OCTET STRING,
      alcPuXID
        OCTET STRING,
      alcPuConnectType
        INTEGER,
      alcPuLineNumber
        OCTET STRING,
      alcPuMaximumFastPoll
        INTEGER,
      alcPuMinimumFastPoll
        INTEGER,
      alcPuMaximumSlowPollInterval
        INTEGER,
      alcPuMinimumSlowPollInterval
        INTEGER,
      alcPuResponseTimeout
        INTEGER,
      alcPuUserData
        OCTET STRING,
      alcSourceDTEAddress
        OCTET STRING,
      alcDestinationDTEAddress
        OCTET STRING
      }

  alcPuConfigLineIndex OBJECT-TYPE
    SYNTAX  INTEGER
    ACCESS  read-only
    STATUS  mandatory
    DESCRIPTION
      "The port number for which PU is configured on."
    ::= { alcPuConfigEntry 1 }

  alcPuConfigAddress  OBJECT-TYPE
    SYNTAX  OCTET STRING (SIZE(1))
    ACCESS  read-only
    STATUS  mandatory
    DESCRIPTION
      "The PU address in the range of 0x01 to 0x3C (both
      inclusive) with addresses 0x0d, 0x1D and 0x20 being
      invalid addresses.

      The default value is 0x01"
    ::= { alcPuConfigEntry 2 }

  alcPuNAUName   OBJECT-TYPE
    SYNTAX  DisplayString (SIZE(1..8))
    ACCESS  read-only
    STATUS  mandatory
    DESCRIPTION
      "The NAU name of this PU.
      The default value for this field is all blank
      (filled with ASCII space 0x20 characters)."
    ::= { alcPuConfigEntry 3 }

  alcPuCSS  OBJECT-TYPE
    SYNTAX  INTEGER {
      in-service(1),
      out-of-service(2)
      }
    ACCESS  read-only
    STATUS  mandatory
    DESCRIPTION
      "The initial state of the CU.

      The Interchange (CU) should be enabled or not when
      the configuration is activated. The range is 'in-service'
      or 'out-of-service'.

      The default value is 'inservice'."
    ::= { alcPuConfigEntry 4 }

  alcPuConnectionID  OBJECT-TYPE
    SYNTAX  OCTET STRING (SIZE(2))
    ACCESS  read-only
    STATUS  mandatory
    DESCRIPTION
      "This entry defines the Connection ID
       to a corresponding entry in the mapping table.

       The default value for this field is all zeroes."
    ::= { alcPuConfigEntry 5 }

  alcPuXID    OBJECT-TYPE
    SYNTAX  OCTET STRING (SIZE(4))
    ACCESS  read-only
    STATUS  mandatory
    DESCRIPTION
      "The XID value for this PU.

      The XID defines an identifier call ID BLOCK and ID
      NUM, which is used in session establishment using
      LLC2.

      The default value for this field is all zeroes
      (solicit XID from PU)."
    ::= { alcPuConfigEntry 6 }

  alcPuConnectType  OBJECT-TYPE
    SYNTAX  INTEGER {
      answer(1),
      originate(2)
      }
    ACCESS  read-only
    STATUS  mandatory
    DESCRIPTION
      "The Alc PU Connection type."
    ::= { alcPuConfigEntry 7 }

  alcPuLineNumber  OBJECT-TYPE
    SYNTAX  OCTET STRING (SIZE(1))
    ACCESS  read-only
    STATUS  mandatory
    DESCRIPTION
      "The parmater defines a host reference to as line
      number.  The range of this parameter is 0x01 to
      0xFF(both inclusive). This parameter must match
      the Host configuration table.

      The default value is 0x01"
    ::= { alcPuConfigEntry 8 }

  alcPuMaximumFastPoll  OBJECT-TYPE
    SYNTAX  INTEGER(1..99)
    ACCESS  read-only
    STATUS  mandatory
    DESCRIPTION
      "This parameter defines the maximum time the
      unit will wait before it polls a device.
      Typicall the data transfer has priority over
      polling algorithm.  This parameter ensures
      that polling is not suspended in favor of data
      transmittal for a prolonged period of time.

      Range of this parameter is from 1 through 99 in
      seconds.
      The default value is 1."
    ::= { alcPuConfigEntry 9 }

  alcPuMinimumFastPoll  OBJECT-TYPE
    SYNTAX  INTEGER(1..65500)
    ACCESS  read-only
    STATUS  mandatory
    DESCRIPTION
      "This parameter defines the minimum time the
      unit will wait before it polls a device.
      This parameter ensures that the devices are
      not polled at a very high rate (allowing for
      a pause).

      Range of this parameter is from 1 through 65500 in
      100ths of a second.
      The default value is 300."
    ::= { alcPuConfigEntry 10 }

  alcPuMaximumSlowPollInterval  OBJECT-TYPE
    SYNTAX  INTEGER(1..99)
    ACCESS  read-only
    STATUS  mandatory
    DESCRIPTION
      "This parameter defines the maximum time an
      inactive device is left out of poll list
      before it is put back in the poll list.

      Range of this parameter is from 1 through 99 in
      seconds.
      The default value is 1."
    ::= { alcPuConfigEntry 11 }

  alcPuMinimumSlowPollInterval OBJECT-TYPE
    SYNTAX  INTEGER(1..990)
    ACCESS  read-only
    STATUS  mandatory
    DESCRIPTION
      "This parameter defines the minimum time an
      inactive device is left out of poll list
      before it is put back in the poll list.

      Range of this parameter is from 1 through 990 in
      10ths of a second.
      The default value is 10."
    ::= { alcPuConfigEntry 12 }

  alcPuResponseTimeout OBJECT-TYPE
    SYNTAX  INTEGER(1..99)
    ACCESS  read-only
    STATUS  mandatory
    DESCRIPTION
      "This parameter defines the duration that
      a unit will wait for a response from a
      device.

      Range of this parameter is from 1 through 99 in
      10ths of a second.
      The default value is 5."
    ::= { alcPuConfigEntry 13 }

  alcPuUserData  OBJECT-TYPE
    SYNTAX  OCTET STRING (SIZE(16))
    ACCESS  read-only
    STATUS  mandatory
    DESCRIPTION
      "The paramter specifies the user data upto sixteen
      hexadecimal bytes for AX.25 protocol."
    ::= { alcPuConfigEntry 14 }

  alcSourceDTEAddress  OBJECT-TYPE
    SYNTAX  OCTET STRING
    ACCESS  read-only
    STATUS  mandatory
    DESCRIPTION
      "This parameter specifies the DTE address this
      port will use to access the Alc network."
    ::= { alcPuConfigEntry 15 }

  alcDestinationDTEAddress  OBJECT-TYPE
    SYNTAX  OCTET STRING
    ACCESS  read-only
    STATUS  mandatory
    DESCRIPTION
      "This parameter specifies the DTE address this
      port will use to access the Alc network."
    ::= { alcPuConfigEntry 16 }

  --
  -- The Alc PU Statistics Table:
  --
  -- The Alc PU Statisctics table contains statistical information on the
  -- lines' configured PUs.

  alcPuStatsTable  OBJECT-TYPE
      SYNTAX  SEQUENCE OF AlcPuStatsEntry
      ACCESS  not-accessible
      STATUS  mandatory
      DESCRIPTION
        "A list of PU statistics entries."
      ::= { puAlcGroup 2 }

  alcPuStatsEntry  OBJECT-TYPE
      SYNTAX  AlcPuStatsEntry
      ACCESS  not-accessible
      STATUS  mandatory
      DESCRIPTION
        "This entry contains information about
        a given PU. The entry is indexed by the
        port number and the PU number."
      INDEX  { alcPuStatsLineIndex, alcPuStatsAddress }
      ::= { alcPuStatsTable 1 }

  AlcPuStatsEntry ::=
    SEQUENCE {
      alcPuStatsLineIndex
        INTEGER,
      alcPuStatsAddress
        OCTET STRING,
      alcPuPolls
        Counter,
      alcPuDeviceFaults
        Counter,
      alcPuBytesRcv
        Counter,
      alcPuBytesXmit
        Counter,
      alcPuSegRcv
        Counter,
      alcPuSegXmit
        Counter
      }


  alcPuStatsLineIndex OBJECT-TYPE
    SYNTAX  INTEGER
    ACCESS  read-only
    STATUS  mandatory
    DESCRIPTION
      "The port number for which PU is configured on."
    ::= { alcPuStatsEntry 1 }

  alcPuStatsAddress  OBJECT-TYPE
    SYNTAX  OCTET STRING (SIZE(1))
    ACCESS  read-only
    STATUS  mandatory
    DESCRIPTION
      "The PU address in the range of 0x00 to 0xfe."
    ::= { alcPuStatsEntry 2 }

  alcPuPolls  OBJECT-TYPE
    SYNTAX  Counter
    ACCESS  read-only
    STATUS  mandatory
    DESCRIPTION
      "The number of Polls."
    ::= { alcPuStatsEntry 3 }

  alcPuDeviceFaults  OBJECT-TYPE
    SYNTAX  Counter
    ACCESS  read-only
    STATUS  mandatory
    DESCRIPTION
      "The number of Device Faults."
    ::= { alcPuStatsEntry 4 }

  alcPuBytesRcv  OBJECT-TYPE
    SYNTAX  Counter
    ACCESS  read-only
    STATUS  mandatory
    DESCRIPTION
      "The number of Bytes Received to this PU."
    ::= { alcPuStatsEntry 5 }

  alcPuBytesXmit OBJECT-TYPE
    SYNTAX  Counter
    ACCESS  read-only
    STATUS  mandatory
    DESCRIPTION
      "The number of Bytes Transmitted for this PU."
    ::= { alcPuStatsEntry 6 }

  alcPuSegRcv  OBJECT-TYPE
    SYNTAX  Counter
    ACCESS  read-only
    STATUS  mandatory
    DESCRIPTION
      "The number of Segments Received to this PU."
    ::= { alcPuStatsEntry 7 }

  alcPuSegXmit   OBJECT-TYPE
    SYNTAX  Counter
    ACCESS  read-only
    STATUS  mandatory
    DESCRIPTION
      "The number of Segments Transmitted for this PU."
    ::= { alcPuStatsEntry 8 }


  --
  -- The Bisync RJE PU Group
  --
  -- The Bisync RJE PU Configuration Table:
  --

  bisyncrjePuConfigTable  OBJECT-TYPE
      SYNTAX  SEQUENCE OF BisyncrjePuConfigEntry
      ACCESS  not-accessible
      STATUS  mandatory
      DESCRIPTION
        "A list of Bisync CU entries."
      ::= { puBisyncRjeGroup 1 }

  bisyncrjePuConfigEntry  OBJECT-TYPE
      SYNTAX  BisyncrjePuConfigEntry
      ACCESS  not-accessible
      STATUS  mandatory
      DESCRIPTION
        "This entry contains information about
        a given PU. The entry is indexed by the
        port number and the PU number."
      INDEX  { bisyncrjePuConfigLineIndex, bisyncrjePuConfigAddress }
      ::= { bisyncrjePuConfigTable 1 }

  BisyncrjePuConfigEntry ::=
    SEQUENCE {
      bisyncrjePuConfigLineIndex
        INTEGER,
      bisyncrjePuConfigAddress
        OCTET STRING,
      bisyncrjePuNAUName
        DisplayString,
      bisyncrjePuInitialState
        INTEGER,
      bisyncrjePuConnectionID
        OCTET STRING,
      bisyncrjePuXID
        OCTET STRING,
      bisyncrjePuConnectType
        INTEGER
    }


  bisyncrjePuConfigLineIndex OBJECT-TYPE
    SYNTAX  INTEGER
    ACCESS  read-only
    STATUS  mandatory
    DESCRIPTION
      "The port number for which PU is configured on."
    ::= { bisyncrjePuConfigEntry 1 }

  bisyncrjePuConfigAddress  OBJECT-TYPE
    SYNTAX  OCTET STRING (SIZE(1))
    ACCESS  read-only
    STATUS  mandatory
    DESCRIPTION
      "The PU address in the range of 0x00 to 0xfe."
    ::= { bisyncrjePuConfigEntry 2 }

  bisyncrjePuNAUName   OBJECT-TYPE
    SYNTAX  DisplayString (SIZE(1..8))
    ACCESS  read-only
    STATUS  mandatory
    DESCRIPTION
      "The NAU name of this PU.
      The default value for this field is all blank
      (filled with ASCII space 0x20 characters)."
    ::= { bisyncrjePuConfigEntry 3 }

  bisyncrjePuInitialState  OBJECT-TYPE
    SYNTAX  INTEGER  {
      in-service(1),
      out-of-service(2)
      }
    ACCESS  read-only
    STATUS  mandatory
    DESCRIPTION
      "The initial state of the PU.

      If configured for 'in-service', then the Bisync RJE PU
      will be brougt up automattically when the unit is powered
      up.

      If configured for 'out-of-service', the the SDLC PU must
      be manually enabled by operator intervention (i.e.
      enable command must be sent).

      The default value is 'in-service'."
    ::= { bisyncrjePuConfigEntry 4 }

  bisyncrjePuConnectionID  OBJECT-TYPE
    SYNTAX  OCTET STRING (SIZE(2))
    ACCESS  read-only
    STATUS  mandatory
    DESCRIPTION
      "This entry defines the Connection ID
      to a corresponding entry in the mapping table.

      The default value for this field is all zeroes."
    ::= { bisyncrjePuConfigEntry 5 }

  bisyncrjePuXID    OBJECT-TYPE
    SYNTAX  OCTET STRING (SIZE(4))
    ACCESS  read-only
    STATUS  mandatory
    DESCRIPTION
      "The XID value for this PU.

      The default value for this field is all zeroes."
    ::= { bisyncrjePuConfigEntry 6 }

  bisyncrjePuConnectType  OBJECT-TYPE
    SYNTAX  INTEGER {
      answer(1),
      originate(2)
      }
    ACCESS  read-only
    STATUS  mandatory
    DESCRIPTION
      "The Bisync RJE PU Connection type."
    ::= { bisyncrjePuConfigEntry 7 }

  --
  -- The Device Control Group
  --

  deviceControlTable OBJECT-TYPE
    SYNTAX SEQUENCE OF DeviceControlEntry
    ACCESS  not-accessible
    STATUS  mandatory
    DESCRIPTION
      "A table for controlling devices and obtaining
     information."
    ::= { deviceControlGroup 1 }

  deviceControlEntry OBJECT-TYPE
    SYNTAX  DeviceControlEntry
    ACCESS  not-accessible
    STATUS  mandatory
    DESCRIPTION
      "An entry consisting of device information for a
      particular device."
    INDEX { deviceControlIndex, deviceControlCUIndex,
      deviceControlAddress }
    ::= { deviceControlTable 1 }

  DeviceControlEntry ::=
    SEQUENCE {
      deviceControlIndex
        INTEGER,
      deviceControlCUIndex
        INTEGER,
      deviceControlAddress
        OCTET STRING,
      deviceStatus
        INTEGER,
      deviceControlFailureCode
        OCTET STRING
    }


  deviceControlIndex  OBJECT-TYPE
    SYNTAX  INTEGER
    ACCESS  read-only
    STATUS  mandatory
    DESCRIPTION
      "The number that uniquely identifies
      this device."
    ::= { deviceControlEntry 1 }

  deviceControlCUIndex  OBJECT-TYPE
    SYNTAX  INTEGER
    ACCESS  read-only
    STATUS  mandatory
    DESCRIPTION
      "The CU index for this device."
    ::= { deviceControlEntry 2 }

  deviceControlAddress  OBJECT-TYPE
    SYNTAX  OCTET STRING (SIZE(1))
    ACCESS  read-only
    STATUS  mandatory
    DESCRIPTION
      "The device address."
    ::= { deviceControlEntry 3 }

  deviceStatus  OBJECT-TYPE
    SYNTAX  INTEGER {
      enable(1),
      disable(2),
      failed(3),
      restart(4),
      enable-all(5)
      }
    ACCESS  read-write
    STATUS  mandatory
    DESCRIPTION
      "The status of the device.

      To change (write) status of a device, enable, disable,
      restart or enable all may be set.

      Valid Return (read) status are enable(d), disable(d),
      or failed (d).

      Commands:
      An enable command will attempt to bring up the device.

      An enable all command will perform the same function
      as enable, since there are no sub elements on a device.

      A disable command will disable the device.

      Status:
      Enable(d) indicates the device is enabled and running.
      Disable(d) indicates the device has been disabled.
      Failed (d) indicates the device is enabled and not
      Running."
    ::= { deviceControlEntry 4 }

  deviceControlFailureCode   OBJECT-TYPE
    SYNTAX  OCTET STRING (SIZE (2))
    ACCESS  read-only
    STATUS  mandatory
    DESCRIPTION
      "This entry contains the failure codes if the
      associated device is in the failed state."
    ::= { deviceControlEntry 5 }

  --
  -- The Device Configuration Group
  --
  -- The Device Configuration Group contains information on the lines'
  -- configured Devices.
  --
  -- The Device Configuration Table

  deviceConfigTable  OBJECT-TYPE
      SYNTAX  SEQUENCE OF DeviceConfigEntry
      ACCESS  not-accessible
      STATUS  mandatory
      DESCRIPTION
        "A list of device entries."
      ::= { deviceBSCGroup 1 }

  deviceConfigEntry  OBJECT-TYPE
      SYNTAX  DeviceConfigEntry
      ACCESS  not-accessible

      STATUS  mandatory
      DESCRIPTION
        "This entry contains information about
        a given device. The entry is indexed by the
        port number, CU index, and device."
      INDEX  { deviceConfigLineIndex, deviceConfigCUIndex,
          deviceConfigAddress }
      ::= { deviceConfigTable 1 }

  DeviceConfigEntry ::=
    SEQUENCE {
      deviceConfigLineIndex
        INTEGER,
      deviceConfigCUIndex
        INTEGER,
      deviceConfigAddress
        OCTET STRING,
      deviceConfigType
        INTEGER
      }


  deviceConfigLineIndex OBJECT-TYPE
    SYNTAX  INTEGER
    ACCESS  read-only
    STATUS  mandatory
    DESCRIPTION
      "The port number for which the line (CU)is configured
       (line level)."
    ::= { deviceConfigEntry 1 }

  deviceConfigCUIndex  OBJECT-TYPE
    SYNTAX  INTEGER
    ACCESS  read-only
    STATUS  mandatory
    DESCRIPTION
      "The CU index which this device is configured on
      (CU level)."
    ::= { deviceConfigEntry 2 }

  deviceConfigAddress  OBJECT-TYPE
    SYNTAX  OCTET STRING (SIZE(1))
    ACCESS  read-only
    STATUS  mandatory
    DESCRIPTION
      "The device address in the legal range of BSC poll
      addresses (device level)."
    ::= { deviceConfigEntry 3 }

  deviceConfigType  OBJECT-TYPE
    SYNTAX  INTEGER {
      crt (1),
      printer (2)
      }
    ACCESS  read-only
    STATUS  mandatory
    DESCRIPTION
      "The device type. The default value is crt."
    ::= { deviceConfigEntry 4 }

  --
  -- The Device Statistics Table
  --

  deviceStatsTable  OBJECT-TYPE
      SYNTAX  SEQUENCE OF DeviceStatsEntry
      ACCESS  not-accessible
      STATUS  mandatory
      DESCRIPTION
        "A table of device statistics information."
      ::= { deviceBSCGroup 2 }

  deviceStatsEntry  OBJECT-TYPE
      SYNTAX  DeviceStatsEntry
      ACCESS  not-accessible
      STATUS  mandatory
      DESCRIPTION
        "This entry contains information about
        a given device. The entry is indexed by the
        port number, CU index, and device."
      INDEX  { bscDeviceLineIndex, bscDeviceCUIndex,
          bscDeviceAddress }
      ::= { deviceStatsTable 1 }

  DeviceStatsEntry ::=
    SEQUENCE {
      bscDeviceLineIndex
        INTEGER,
      bscDeviceCUIndex
        INTEGER,
      bscDeviceAddress
        OCTET STRING,
      bscDeviceInTransactions
        Counter,
      bscDeviceOutTransactions
        Counter,
      bscDeviceSumCount
        Counter,
      bscDeviceResponseDelaySum
        Counter,
      bscDeviceResponseDelaySqSum
        Counter
      }


  bscDeviceLineIndex OBJECT-TYPE
    SYNTAX  INTEGER
    ACCESS  read-only
    STATUS  mandatory
    DESCRIPTION
      "The port number for which the line (CU)is configured
      (line level)."
    ::= { deviceStatsEntry 1 }

  bscDeviceCUIndex  OBJECT-TYPE
    SYNTAX  INTEGER
    ACCESS  read-only
    STATUS  mandatory
    DESCRIPTION
      "The CU index which this device is configured on
       (CU level)."
    ::= { deviceStatsEntry 2 }

  bscDeviceAddress  OBJECT-TYPE
    SYNTAX  OCTET STRING (SIZE(1))
    ACCESS  read-only
    STATUS  mandatory
    DESCRIPTION
      "The device address in the legal range of BSC poll
      addresses (device level)."
    ::= { deviceStatsEntry 3 }

  bscDeviceInTransactions  OBJECT-TYPE
    SYNTAX  Counter
    ACCESS  read-only
    STATUS  mandatory
    DESCRIPTION
      "The number of device receiving transactions."
    ::= { deviceStatsEntry 4 }

  bscDeviceOutTransactions OBJECT-TYPE
    SYNTAX  Counter
    ACCESS  read-only
    STATUS  mandatory
    DESCRIPTION
      "The number of device transmitting transactions."
    ::= { deviceStatsEntry 5 }

  bscDeviceSumCount  OBJECT-TYPE
    SYNTAX  Counter
    ACCESS  read-only
    STATUS  mandatory
    DESCRIPTION
      "The device sum count."
    ::= { deviceStatsEntry 6 }

  bscDeviceResponseDelaySum OBJECT-TYPE
    SYNTAX  Counter
    ACCESS  read-only
    STATUS  mandatory
    DESCRIPTION
      "The device sum count."
    ::= { deviceStatsEntry 7 }

  bscDeviceResponseDelaySqSum OBJECT-TYPE
    SYNTAX  Counter
    ACCESS  read-only
    STATUS  mandatory
    DESCRIPTION
      "The device sum count."
    ::= { deviceStatsEntry 8 }

  --
  -- The Device Configuration Group
  --
  -- The Device Configuration Group contains information on the lines'
  -- configured Devices.
  --
  -- The Device Configuration Table

  alcdeviceConfigTable  OBJECT-TYPE
      SYNTAX  SEQUENCE OF AlcdeviceConfigEntry
      ACCESS  not-accessible
      STATUS  mandatory
      DESCRIPTION
        "A list of device entries."
      ::= { deviceALCGroup 1 }

  alcdeviceConfigEntry  OBJECT-TYPE
      SYNTAX  AlcdeviceConfigEntry
      ACCESS  not-accessible
      STATUS  mandatory
      DESCRIPTION
        "This entry contains information about
        a given device. The entry is indexed by the
        port number, CU index, and device."
      INDEX  { alcdeviceConfigLineIndex, alcdeviceConfigCUIndex,
          deviceConfigAddress }
      ::= { alcdeviceConfigTable 1 }

  AlcdeviceConfigEntry ::=
    SEQUENCE {
      alcdeviceConfigLineIndex
        INTEGER,
      alcdeviceConfigCUIndex
        INTEGER,
      alcdeviceConfigAddress
        OCTET STRING,
      alcdeviceConfigType
        INTEGER
      }


  alcdeviceConfigLineIndex OBJECT-TYPE
    SYNTAX  INTEGER
    ACCESS  read-only
    STATUS  mandatory
    DESCRIPTION
      "The port number for which the line (CU)is configured
       (line level)."
    ::= { alcdeviceConfigEntry 1 }

  alcdeviceConfigCUIndex  OBJECT-TYPE
    SYNTAX  INTEGER
    ACCESS  read-only
    STATUS  mandatory
    DESCRIPTION
      "The CU index which this device is configured on
      (CU level)."
    ::= { alcdeviceConfigEntry 2 }

  alcdeviceConfigAddress  OBJECT-TYPE
    SYNTAX  OCTET STRING (SIZE(1))
    ACCESS  read-only
    STATUS  mandatory
    DESCRIPTION
      "The device address in the legal range of ALC poll
      addresses (device level).
      The range is 0x01 to 0x3c with 0x20 being invalid
      address.
      The default value is 0x01."
    ::= { alcdeviceConfigEntry 3 }

  alcdeviceConfigType  OBJECT-TYPE
    SYNTAX  INTEGER {
      crt (1),
      printer (2)
      }
    ACCESS  read-only
    STATUS  mandatory
    DESCRIPTION
      "The device type. The default value is printer."
    ::= { alcdeviceConfigEntry 4 }

  --
  -- The T7 Configuration Group

  -- Contains the current operational configuration
  --

  t7ConfigTable OBJECT-TYPE
    SYNTAX SEQUENCE OF T7ConfigEntry
    ACCESS  not-accessible
    STATUS  mandatory
    DESCRIPTION
      "A table for T7 protocol configuration
      parameters."
    ::= { t7ConfigGroup 1 }

  t7ConfigEntry OBJECT-TYPE
    SYNTAX  T7ConfigEntry
    ACCESS  not-accessible
    STATUS  mandatory

    DESCRIPTION
      "An entry consisting of T7 protocol information for a
      particular port."
    INDEX { t7ConfigIndex }
    ::= { t7ConfigTable 1 }

  T7ConfigEntry ::=
    SEQUENCE {
      t7ConfigIndex
        INTEGER,
      t7ProtocolEnabled
        INTEGER,
      t7PortSpeed
        INTEGER,
      t7StopBits
        INTEGER,
      t7PortParity
        INTEGER,
      t7DataBits
        INTEGER,
      t7IdleTimer
        INTEGER,
      t7PortTxFrameGap
        INTEGER,
      t7RxForwardingCount
        INTEGER,
      t7PortIPAddress
        IpAddress,
      t7UDPPortNumber
        INTEGER
    }


  t7ConfigIndex  OBJECT-TYPE
    SYNTAX  INTEGER
    ACCESS  read-only
    STATUS  mandatory
    DESCRIPTION
      "The number that uniquely identifies
      this T7 port."
    ::= { t7ConfigEntry 1 }

  t7ProtocolEnabled OBJECT-TYPE
    SYNTAX  INTEGER {
      yes(1),
      no(2)
      }
    ACCESS  read-only
    STATUS  mandatory
    DESCRIPTION
      "This flag indicates if T7 protocol is enabled
      on this unit. If No, the following T7 variables
      will have no effect.

      The default value for this field is 'No'"
    ::= { t7ConfigEntry 2 }

  t7PortSpeed OBJECT-TYPE
    SYNTAX  INTEGER {
      speed75(75),
      speed150(150),
      speed300(300),
      speed600(600),
      speed1200(1200),
      speed2400(2400),
      speed4800(4800),
      speed9600(9600),
      speed19200(19200)
      }
    ACCESS  read-only
    STATUS  mandatory
    DESCRIPTION
      "The speed of the T7 port expressed in bits per
      second.

      The default speed is 75 bits per second"
    ::= { t7ConfigEntry 3 }

  t7StopBits OBJECT-TYPE
    SYNTAX  INTEGER (1..2)
    ACCESS  read-only
    STATUS  mandatory
    DESCRIPTION
      "Number of stop bits generated for T7 port transmit
      characters (received characters may have any number
      of bits regardless of the configuration).

      The default value is 2"
    ::= { t7ConfigEntry 4 }

  t7PortParity OBJECT-TYPE
    SYNTAX  INTEGER {
      odd(1),
      even(2),
      none(3)
      }
    ACCESS  read-only
    STATUS  mandatory
    DESCRIPTION
      "T7 port parity type generated for transmit characters
      and checked for receive characters. If ODD or EVEN,
      then if a character is received with invalid  parity,
      it is discarded and the message once completely
      received is also discarded (i.e. not forwarded to the
      network).  If NONE, then no parity bit is expected
      within the character or generated to the line.

      The default value is EVEN."
    ::= { t7ConfigEntry 5 }

  t7DataBits OBJECT-TYPE
    SYNTAX  INTEGER (5..8)
    ACCESS  read-only
    STATUS  mandatory
    DESCRIPTION
      "T7 port number of data bit (not including the parity
      bit).

      The default value is 7"
    ::= { t7ConfigEntry 6 }

  t7IdleTimer OBJECT-TYPE
    SYNTAX  INTEGER (0..1000)
    ACCESS  read-only
    STATUS  mandatory
    DESCRIPTION
      "The T7 Idle timer is amount of time (in milliseconds)
      used to determine when a complete message has been
      received from the line.  If configured as 0, then
      this timer is disabled and the message will be sent
      to the network only when the RX forwarding count is
      reached. If configured greater than 0, then the timer
      must be configured for a time longer than the time it
      takes to receive one character,  otherwise the timer
      will not function properly.

      The default value is 200"
    ::= { t7ConfigEntry 7 }

  t7PortTxFrameGap OBJECT-TYPE
    SYNTAX  INTEGER (0..5000)
    ACCESS  read-only
    STATUS  mandatory
    DESCRIPTION
      "The T7 port TX frame gap is analogous to the idle
      timer, but is used to separate messages received from
      the network by gaps in time so that the Async device
      can distinguish between multiple messages. If
      configured as 0, then this function is disabled and if
      messages are received while transmitting a current
      message, the the two messages from the network will be
      sent out with no gap between them. If configured
      greater than 0, then a gap of the specified number of
      milliseconds will be inserted.

      The default value is 200"
    ::= { t7ConfigEntry 8 }

  t7RxForwardingCount OBJECT-TYPE
    SYNTAX  INTEGER (1..1024)
    ACCESS  read-only
    STATUS  mandatory
    DESCRIPTION
      "The T7 port receive forwarding count is used to forward
      messages when a configured number of characters is
      received from the Async line. This must be configured
      to greater than or equal to the maximum message length
      for a given protocol.

      The default value is 256"
    ::= { t7ConfigEntry 9 }

  t7PortIPAddress OBJECT-TYPE
    SYNTAX  IpAddress
    ACCESS  read-only
    STATUS  mandatory
    DESCRIPTION
      "The T7 port IP address is used to configure the
      remote IP address in which to communicate with."
    ::= { t7ConfigEntry 10 }

  t7UDPPortNumber OBJECT-TYPE
    SYNTAX  INTEGER (1..1000)
    ACCESS  read-only
    STATUS  mandatory
    DESCRIPTION
      "The T7 port UDP port number address is used to
      configure the local and remot UDP port number (i.e.
      socket) address in which to communicate with.

      The default value is 600"
    ::= { t7ConfigEntry 11 }

  --
  -- The T7 Statistics Group

  -- Contains the current T7 Statistics
  --


  t7StatsTable OBJECT-TYPE
      SYNTAX  SEQUENCE OF T7StatsEntry
      ACCESS  not-accessible
      STATUS  mandatory
      DESCRIPTION
        "A table of T7 protocol statistics information."
      ::= { t7StatsGroup 1 }

  t7StatsEntry OBJECT-TYPE
      SYNTAX  T7StatsEntry
      ACCESS  not-accessible
      STATUS  mandatory
      DESCRIPTION
        "This entry contains information about
        a T7 port. The entry is indexed by the
        port number, CU index, and device."
      INDEX  { t7StatsIndex }
      ::= { t7StatsTable 1 }


  T7StatsEntry ::=
    SEQUENCE {
      t7StatsIndex
        INTEGER,
      t7InOctets
        Counter,
      t7OutOctets
        Counter,
      t7InMessages
        Counter,
      t7OutMessages
        Counter,
      t7InMsgDiscarded
        Counter,
      t7OutMsgDiscarded
        Counter,
      t7XmtFailures
        Counter,
      t7RcvMsgForwarded
        Counter,
      t7RcvMsgErrors
        Counter,
      t7RcvCharsDiscarded
        Counter,
      t7RcvParityErrors
        Counter,
      t7RcvFramingErrors
        Counter,
      t7RcvFifoOverruns
        Counter,
      t7RcvCharsOverruns
        Counter,
      t7RcvBreakConditions
        Counter
    }

  t7StatsIndex OBJECT-TYPE
    SYNTAX  INTEGER
    ACCESS  read-only
    STATUS  mandatory
    DESCRIPTION
      "The number that uniquely identifies
      this T7 port."
    ::= { t7StatsEntry 1 }


  t7InOctets OBJECT-TYPE
    SYNTAX  Counter
    ACCESS  read-only
    STATUS  mandatory
    DESCRIPTION
      "The number of bytes received."
    ::= { t7StatsEntry 2 }


  t7OutOctets OBJECT-TYPE
    SYNTAX  Counter
    ACCESS  read-only
    STATUS  mandatory
    DESCRIPTION
      "The number of bytes sent."
    ::= { t7StatsEntry 3 }

  t7InMessages OBJECT-TYPE
    SYNTAX  Counter
    ACCESS  read-only
    STATUS  mandatory
    DESCRIPTION
      "The number of messages received."
    ::= { t7StatsEntry 4 }

  t7OutMessages OBJECT-TYPE
    SYNTAX  Counter
    ACCESS  read-only
    STATUS  mandatory
    DESCRIPTION
      "The number of messages sent."
    ::= { t7StatsEntry 5 }


  t7InMsgDiscarded OBJECT-TYPE
    SYNTAX  Counter
    ACCESS  read-only
    STATUS  mandatory
    DESCRIPTION
      "The number of received messages discarded."
    ::= { t7StatsEntry 6 }

  t7OutMsgDiscarded OBJECT-TYPE
    SYNTAX  Counter
    ACCESS  read-only
    STATUS  mandatory
    DESCRIPTION
      "The number of sent messages discarded."
    ::= { t7StatsEntry 7 }

  t7XmtFailures OBJECT-TYPE
    SYNTAX  Counter
    ACCESS  read-only
    STATUS  mandatory
    DESCRIPTION
      "The number of failures in transmission."
    ::= { t7StatsEntry 8 }

  t7RcvMsgForwarded OBJECT-TYPE
    SYNTAX  Counter
    ACCESS  read-only
    STATUS  mandatory
    DESCRIPTION
      "The number of received messages forwarded."
    ::= { t7StatsEntry 9 }

  t7RcvMsgErrors OBJECT-TYPE
    SYNTAX  Counter
    ACCESS  read-only
    STATUS  mandatory
    DESCRIPTION
      "The number of errors detected in receiving
      messages."
    ::= { t7StatsEntry 10 }

  t7RcvCharsDiscarded OBJECT-TYPE
    SYNTAX  Counter
    ACCESS  read-only
    STATUS  mandatory
    DESCRIPTION
      "The number of received characters discarded."
    ::= { t7StatsEntry 11 }

  t7RcvParityErrors OBJECT-TYPE
    SYNTAX  Counter
    ACCESS  read-only
    STATUS  mandatory
    DESCRIPTION
      "The number of parity errors detected."
    ::= { t7StatsEntry 12 }

  t7RcvFramingErrors OBJECT-TYPE
    SYNTAX  Counter
    ACCESS  read-only
    STATUS  mandatory
    DESCRIPTION
      "The number of errors detected in receiving
      frames."
    ::= { t7StatsEntry 13 }

  t7RcvFifoOverruns OBJECT-TYPE
    SYNTAX  Counter
    ACCESS  read-only
    STATUS  mandatory
    DESCRIPTION
      "The number FIFO receive overruns detected."
    ::= { t7StatsEntry 14 }

  t7RcvCharsOverruns OBJECT-TYPE
    SYNTAX  Counter
    ACCESS  read-only
    STATUS  mandatory
    DESCRIPTION
      "The number of character receive overruns detected."
    ::= { t7StatsEntry 15 }

  t7RcvBreakConditions OBJECT-TYPE
    SYNTAX  Counter
    ACCESS  read-only
    STATUS  mandatory
    DESCRIPTION
      "The number of receive break conditions."
    ::= { t7StatsEntry 16 }

  --
  -- The Slip Configuration Group

  -- Contains the current operational configuration
  --

  slipConfigTable OBJECT-TYPE
    SYNTAX SEQUENCE OF SlipConfigEntry
    ACCESS  not-accessible
    STATUS  mandatory
    DESCRIPTION
      "A table for Slip protocol configuration
      parameters."
    ::= { slipConfigGroup 1 }

  slipConfigEntry OBJECT-TYPE
    SYNTAX  SlipConfigEntry
    ACCESS  not-accessible
    STATUS  mandatory
    DESCRIPTION
      "An entry consisting of Slip protocol information for a
      particular port."
    INDEX { slipConfigIndex }
    ::= { slipConfigTable 1 }

  SlipConfigEntry ::=
    SEQUENCE {
      slipConfigIndex
        INTEGER,
      slipProtocolEnabled
        INTEGER,
      slipPortSpeed
        INTEGER,
      slipStopBits
        INTEGER,
      slipIdleTimer
        INTEGER,
      slipPortIPAddress
        IpAddress,
      slipUsage
        INTEGER,
      slipNetworkMask
        IpAddress,
      slipDefaultGateway
        IpAddress,
      slipEnableRIP
        INTEGER
    }


  slipConfigIndex  OBJECT-TYPE
    SYNTAX  INTEGER
    ACCESS  read-only
    STATUS  mandatory
    DESCRIPTION
      "The number that uniquely identifies
      this Slip port."
    ::= { slipConfigEntry 1 }

  slipProtocolEnabled OBJECT-TYPE
    SYNTAX  INTEGER {
      yes(1),
      no(2)
      }
    ACCESS  read-only
    STATUS  mandatory
    DESCRIPTION
      "This flag indicates if COM2 port is enabled or
      disabled for usage for SLIP.

      The default value for this field is 'Yes'"
    ::= { slipConfigEntry 2 }

  slipPortSpeed OBJECT-TYPE
    SYNTAX  INTEGER {
      speed75(75),
      speed150(150),
      speed300(300),
      speed600(600),
      speed1200(1200),
      speed2400(2400),
      speed4800(4800),
      speed9600(9600),
      speed19200(19200)
      }
    ACCESS  read-only
    STATUS  mandatory
    DESCRIPTION
      "This parameter determines the COM2 port speed for
      the SLIP connection to the modem.

      The default speed is 9600 bits per second"
    ::= { slipConfigEntry 3 }

  slipStopBits OBJECT-TYPE
    SYNTAX  INTEGER (1..2)
    ACCESS  read-only
    STATUS  mandatory
    DESCRIPTION
      "This parameter specifies the number of transmit Stop
      Bits used on the SLIP connection to the modem.  The
      range of this parameter is 1 or 2 bits.

      The default value is 1"
    ::= { slipConfigEntry 4 }

  slipIdleTimer OBJECT-TYPE
    SYNTAX  INTEGER (0..5000)
    ACCESS  read-only
    STATUS  mandatory
    DESCRIPTION
      "The Slip Idle timer is amount of time (in milliseconds)
      used to determine the end of frame.  The idel timer
      is started every time a character is received.  The
      range of this parameter is from 0 to 5000 milliseconds.
      A valuse of zero implies the parameter is not used.

      The default value is 200"
    ::= { slipConfigEntry 5 }

  slipPortIPAddress OBJECT-TYPE
    SYNTAX  IpAddress
    ACCESS  read-only
    STATUS  mandatory
    DESCRIPTION
      "The Slip port IP address.

      The default valus is 0.0.0.0."
    ::= { slipConfigEntry 6 }

  slipUsage OBJECT-TYPE
    SYNTAX  INTEGER {
        modem-management(1),
        ipend-node(2),
        ip-routing(3)
        }
    ACCESS  read-only
    STATUS  mandatory
    DESCRIPTION
      "This parameter defines whether SLIP protocol is used
      to manage locally attached modem or is it used for IP
      end node function or IP forwarding function. The range
      of this parameter is MODEM MANAGEMENT, IPEND NODE, IP
      ROUTING.

      The default value is Modem Management"
    ::= { slipConfigEntry 7 }

  slipNetworkMask   OBJECT-TYPE
    SYNTAX  IpAddress
    ACCESS  read-only
    STATUS  mandatory
    DESCRIPTION
      "This parameter defines IP sub-netmask for this parameter.

      The default valus is 0.0.0.0."
    ::= { slipConfigEntry 8 }

  slipDefaultGateway   OBJECT-TYPE
    SYNTAX  IpAddress
    ACCESS  read-only
    STATUS  mandatory
    DESCRIPTION
      "This parameter defines IP default gateway.

      The default valus is 0.0.0.0."
    ::= { slipConfigEntry 9 }

  slipEnableRIP   OBJECT-TYPE
    SYNTAX  INTEGER {
      yes(1),
      no(2)
      }
    ACCESS  read-only
    STATUS  mandatory
    DESCRIPTION
      "This parameter defines whether RIP packets should be
      sent on this interface or not.  Range is yes or no.

      The default valus is 'no'."
    ::= { slipConfigEntry 10 }

  --
  -- The Slip Statistics Group

  -- Contains the current Slip Statistics
  --


  slipStatsTable OBJECT-TYPE
      SYNTAX  SEQUENCE OF SlipStatsEntry
      ACCESS  not-accessible
      STATUS  mandatory
      DESCRIPTION
        "A table of Slip protocol statistics information."
      ::= { slipStatsGroup 1 }

  slipStatsEntry OBJECT-TYPE
      SYNTAX  SlipStatsEntry
      ACCESS  not-accessible
      STATUS  mandatory
      DESCRIPTION
        "This entry contains information about
        a slip Com port."
      INDEX  { slipStatsIndex }
      ::= { slipStatsTable 1 }


  SlipStatsEntry ::=
    SEQUENCE {
      slipStatsIndex
        INTEGER,
      slipInChrs
        Counter,
      slipOutChrs
        Counter,
      slipInMessages
        Counter,
      slipOutMessages
        Counter,
      slipInMsgDiscarded
        Counter,
      slipOutMsgDiscarded
        Counter,
      slipXmtFailures
        Counter,
      slipRcvMsgForwarded
        Counter,
      slipRcvMsgErrors
        Counter,
      slipRcvCharsDiscarded
        Counter,
      slipRcvParityErrors
        Counter,
      slipRcvFramingErrors
        Counter,
      slipRcvFifoOverruns
        Counter,
      slipRcvCharsOverruns
        Counter,
      slipRcvBreakConditions
        Counter
    }

  slipStatsIndex OBJECT-TYPE
    SYNTAX  INTEGER
    ACCESS  read-only
    STATUS  mandatory
    DESCRIPTION
      "The number that uniquely identifies
      this Slip com port."
    ::= { slipStatsEntry 1 }


  slipInChrs OBJECT-TYPE
    SYNTAX  Counter
    ACCESS  read-only
    STATUS  mandatory
    DESCRIPTION
      "The number of Characters received."
    ::= { slipStatsEntry 2 }


  slipOutChrs OBJECT-TYPE
    SYNTAX  Counter
    ACCESS  read-only
    STATUS  mandatory
    DESCRIPTION
      "The number of characters sent."
    ::= { slipStatsEntry 3 }

  slipInMessages OBJECT-TYPE
    SYNTAX  Counter
    ACCESS  read-only
    STATUS  mandatory
    DESCRIPTION
      "The number of messages received."
    ::= { slipStatsEntry 4 }

  slipOutMessages OBJECT-TYPE
    SYNTAX  Counter
    ACCESS  read-only
    STATUS  mandatory
    DESCRIPTION
      "The number of messages sent."
    ::= { slipStatsEntry 5 }


  slipInMsgDiscarded OBJECT-TYPE
    SYNTAX  Counter
    ACCESS  read-only
    STATUS  mandatory
    DESCRIPTION
      "The number of received messages discarded."
    ::= { slipStatsEntry 6 }

  slipOutMsgDiscarded OBJECT-TYPE
    SYNTAX  Counter
    ACCESS  read-only
    STATUS  mandatory
    DESCRIPTION
      "The number of sent messages discarded."
    ::= { slipStatsEntry 7 }

  slipXmtFailures OBJECT-TYPE
    SYNTAX  Counter
    ACCESS  read-only
    STATUS  mandatory
    DESCRIPTION
      "The number of failures in transmission."
    ::= { slipStatsEntry 8 }

  slipRcvMsgForwarded OBJECT-TYPE
    SYNTAX  Counter
    ACCESS  read-only
    STATUS  mandatory
    DESCRIPTION
      "The number of received messages forwarded."
    ::= { slipStatsEntry 9 }

  slipRcvMsgErrors OBJECT-TYPE
    SYNTAX  Counter
    ACCESS  read-only
    STATUS  mandatory
    DESCRIPTION
      "The number of errors detected in receiving
      messages."
    ::= { slipStatsEntry 10 }

  slipRcvCharsDiscarded OBJECT-TYPE
    SYNTAX  Counter
    ACCESS  read-only
    STATUS  mandatory
    DESCRIPTION
      "The number of received characters discarded."
    ::= { slipStatsEntry 11 }

  slipRcvParityErrors OBJECT-TYPE
    SYNTAX  Counter
    ACCESS  read-only
    STATUS  mandatory
    DESCRIPTION
      "The number of parity errors detected."
    ::= { slipStatsEntry 12 }

  slipRcvFramingErrors OBJECT-TYPE
    SYNTAX  Counter
    ACCESS  read-only
    STATUS  mandatory
    DESCRIPTION
      "The number of errors detected in receiving
      frames."
    ::= { slipStatsEntry 13 }

  slipRcvFifoOverruns OBJECT-TYPE
    SYNTAX  Counter
    ACCESS  read-only
    STATUS  mandatory
    DESCRIPTION
      "The number FIFO receive overruns detected."
    ::= { slipStatsEntry 14 }

  slipRcvCharsOverruns OBJECT-TYPE
    SYNTAX  Counter
    ACCESS  read-only
    STATUS  mandatory
    DESCRIPTION
      "The number of character receive overruns detected."
    ::= { slipStatsEntry 15 }

  slipRcvBreakConditions OBJECT-TYPE
    SYNTAX  Counter
    ACCESS  read-only
    STATUS  mandatory
    DESCRIPTION
      "The number of receive break conditions."
    ::= { slipStatsEntry 16 }

  --
  -- Sync Research TRAP MIB
  --
  --
  --  This MIB module uses the extended TRAP-TYPE macro as
  --  defined in RFC 1215.


  configChanged TRAP-TYPE
    ENTERPRISE   syncResearch
    VARIABLES  { lastTrapSeqNumber, configId }
    DESCRIPTION
      "This trap indicates that the configuration of
      the unit has been changed."
    ::= 800

  configError TRAP-TYPE
    ENTERPRISE   syncResearch
    VARIABLES  { lastTrapSeqNumber,
                 lastInstallErrCode }
    DESCRIPTION
      "This trap indicates that the activation of configuration
      of the unit has resulted in an error.  New configuration
      has not been successfully activated."
    ::= 801

  dumpExists TRAP-TYPE
    ENTERPRISE   syncResearch
    VARIABLES  { lastTrapSeqNumber,
                 dumpFileName }
    DESCRIPTION
      "This trap indicates that a memory core dump exists."
    ::= 802

  dumpArchived TRAP-TYPE
    ENTERPRISE   syncResearch
    VARIABLES  { lastTrapSeqNumber }
    DESCRIPTION
      "This trap indicates that the memory dump file has been
      archived."
    ::= 803


  lineStatusChanged TRAP-TYPE
    ENTERPRISE   syncResearch
    VARIABLES  { lastTrapSeqNumber,
                 lineStatus,
                 lineControlFailureCode,
                 linePhysicalIndex,
                 lineCableType }
    DESCRIPTION
      "This trap indicates that the indicated Line or Port has
      changed state.  It has either been enabled, failed or
      disabled."
    ::= 804

  lanStatusChanged TRAP-TYPE
    ENTERPRISE   syncResearch
    VARIABLES  { lastTrapSeqNumber,
                 lanStatus,
                 lanControlFailureCode }
    DESCRIPTION
      "This trap indicates that the indicated LAN Port has
      changed state.  It has either been enabled, failed or
      disabled."
    ::= 805

  lineQuality TRAP-TYPE
    ENTERPRISE   syncResearch
    VARIABLES  { lastTrapSeqNumber,
                 lineQualityFrameCount,
                 lineQualityCRCErrors,
                 lineQualityAborts,
                 linePhysicalIndex }
    DESCRIPTION
      "This trap indicates that the line quality is changed.
      If the lineQualityAborts is greater than 5 or
      lineQualityCRCErrors is greater that 5 then it indicates
      a poor line quality, otherwise it indicates a change
      from a poor to good line quality."
    ::= 806

  puStatusChanged TRAP-TYPE
    ENTERPRISE   syncResearch
    VARIABLES  { lastTrapSeqNumber,
                 puStatus,
                 puControlFailureCode,
                 linePhysicalIndex,
                 puControlPUAddress }
    DESCRIPTION
      "This trap indicates that the indicated PU has
      changed state.  It has either been enabled, failed or
      disabled."
    ::= 807

  puConnectionStatusChanged TRAP-TYPE
    ENTERPRISE   syncResearch
    VARIABLES  { lastTrapSeqNumber,
                 puConnectionStatus,
                 puLastClearCode }
    DESCRIPTION
      "Note this trap is obsolete. This trap indicates that the indicated PU has
      changed connection state.  Its connection has either been
      established, disconnected, or rejected."
    ::= 808

  netviewConnectionStatusChanged TRAP-TYPE
    ENTERPRISE   syncResearch
    VARIABLES  { lastTrapSeqNumber,
                 netviewConnectionStatus,
                 netviewLastClearCode }
    DESCRIPTION
      "Note this trap is obsolete. This trap indicates that the NetView PU has
      changed connection state.  Its connection has either been
      established, disconnected, or rejected."
    ::= 809

  netviewAltConnectionStatusChanged TRAP-TYPE
    ENTERPRISE   syncResearch
    VARIABLES  { lastTrapSeqNumber,
                 netviewAltConnectionStatus,
                 netviewAltLastClearCode }
    DESCRIPTION
      "Note this trap is obsolete.
       This trap indicates that the Alternate NetView PU has
       changed connection state.  Its connection has either been
       established, disconnected, or rejected."
    ::= 810

  puConnectionStatusUp TRAP-TYPE
    ENTERPRISE   syncResearch
    VARIABLES  { lastTrapSeqNumber,
                 linePhysicalIndex,
                 puControlPUAddress }
    DESCRIPTION
      "This trap is obsolete.
       This trap indicates that the indicated PU has
       changed connection state.  Its connection had been established."
    ::= 811

  puConnectionStatusDown TRAP-TYPE
    ENTERPRISE   syncResearch
    VARIABLES  { lastTrapSeqNumber,
                 linePhysicalIndex,
                 puControlPUAddress,
                 puLastClearCode }
    DESCRIPTION
      "This trap is obsolete.
       This trap indicates that the indicated PU has
       changed connection state.  Its connection has been disconnected.
       If the indicated PU is not in session, the trap is generated only
       if the clear code is different from the puLastClearCode."
    ::= 812

  netviewConnectionStatusUp TRAP-TYPE
    ENTERPRISE   syncResearch
    VARIABLES  { lastTrapSeqNumber }
    DESCRIPTION
      "This trap is obsolete.
       This trap indicates that the indicated NetView PU has
       changed connection state.  Its connection has been established."
    ::= 813

  netviewConnectionStatusDown TRAP-TYPE
    ENTERPRISE   syncResearch
    VARIABLES  { lastTrapSeqNumber,
                 netviewLastClearCode }
    DESCRIPTION
      "This trap is obsolete.
       This trap indicates that the indicated NetView PU has
       changed connection state.  Its connection had been disconnected.
       If the indicated PU is not in session, the trap is generated only
       if the clear code is different from the netviewLastClearCode."
    ::= 814

  netviewAltConnectionStatusUp TRAP-TYPE
    ENTERPRISE   syncResearch
    VARIABLES  { lastTrapSeqNumber }
    DESCRIPTION
      "This trap is obsolete.
       This trap indicates that the indicated Alternate
       NetView PU has changed connection state.  Its connection has been
       established."
    ::= 815

  netviewAltConnectionStatusDown TRAP-TYPE
    ENTERPRISE   syncResearch
    VARIABLES  { lastTrapSeqNumber,
                 netviewAltLastClearCode }
    DESCRIPTION
      "This trap is obsolete.
       This trap indicates that the indicated Alternate
       NetView PU has changed connection state.  Its connection had been
       disconnected. If the indicated PU is not in session, the trap is generated
       only if the clear code is different from the netviewAltLastClearCode."
    ::= 816

  sessSwitchedToPrimaryDLCI TRAP-TYPE
    ENTERPRISE   syncResearch
    VARIABLES  { lastTrapSeqNumber,
                 puControlLineIndex,
                 puControlPUAddress,
                 puCurrentDlci,
                 puIsDynamic}
    DESCRIPTION
      "This trap indicates that a session switch has occured
       from a Parallel DLCI to Primary DLCI."
    ::= 817

  sessSwitchedToParallelDLCI TRAP-TYPE
    ENTERPRISE   syncResearch
    VARIABLES  { lastTrapSeqNumber,
                 puControlLineIndex,
                 puControlPUAddress,
                 puCurrentDlci,
                 puIsDynamic}
    DESCRIPTION
      "This trap indicates that a session switch has occured
       from the Primary DLCI to the Parallel DLCI."
    ::= 818

  sessUpOnPrimaryDLCI TRAP-TYPE
    ENTERPRISE   syncResearch
    VARIABLES  { lastTrapSeqNumber,
                 puControlLineIndex,
                 puControlPUAddress,
                 puCurrentDlci,
                 puCurrentMAC,
                 puIsDynamic}
    DESCRIPTION
      "This indicates that a PU session is established on a primary
      DLCI.  This TRAP is generated for Frame Nodes only.  For Conversion
      Node sessUpOnPrimaryMAC or sessUpOnAlternatMAC will be used instead.
      For NetView the puControlLineIndex is set to 99, and
      the puControlPUAddress is set to 01 for primary PU and 02
      for the alternate NetView PU."
    ::= 819

  sessUpOnParallelDLCI TRAP-TYPE
    ENTERPRISE   syncResearch
    VARIABLES  { lastTrapSeqNumber,
                 puControlLineIndex,
                 puControlPUAddress,
                 puCurrentDlci,
                 puCurrentMAC,
                 puIsDynamic}
    DESCRIPTION
      "This indicates that a PU session is established on a parallel
       DLCI.  This TRAP is generated for Frame Nodes only.  For Conversion
       Node sessUpOnPrimaryMAC or sessUpOnAlternatMAC will be used instead.
       For NetView the puControlLineIndex is set to 99, and
       the puControlPUAddress is set to 01 for primary PU and 02
       for the alternate NetView PU."
    ::= 820

  sessUpOnAlternateDLCI TRAP-TYPE
    ENTERPRISE   syncResearch
    VARIABLES  { lastTrapSeqNumber,
                 puControlLineIndex,
                 puControlPUAddress,
                 puCurrentDlci,
                 puCurrentMAC,
                 puIsDynamic}
    DESCRIPTION
      "This indicates that a PU session is established on an alternate
      DLCI.  This TRAP is generated for Frame Nodes only.  For Conversion
      Node sessUpOnPrimaryMAC or sessUpOnAlternatMAC will be used instead.
      For NetView the puControlLineIndex is set to 99, and
      the puControlPUAddress is set to 01 for primary PU and 02
      for the alternate NetView PU."
    ::= 821

  sessUpOnPrimaryMAC TRAP-TYPE
    ENTERPRISE   syncResearch
    VARIABLES  { lastTrapSeqNumber,
                 puControlLineIndex,
                 puControlPUAddress,
                 puCurrentDlci,
                 puCurrentMAC,
                 linePhysicalType,
                 puIsDynamic}

    DESCRIPTION
      "This indicates that a PU session is established on a non-explicit
      (dynamic, or broadcast) DLCI to the primary destination MAC.
      For Conversion Node, puCurrentDlci is set to 0. For NetView the
      puControlLineIndex is set to 99, and the puControlPUAddress
      is set to 01 for primary PU and 02 for the alternate NetView PU."
    ::= 822

  sessUpOnAlternateMAC TRAP-TYPE
    ENTERPRISE   syncResearch
    VARIABLES  { lastTrapSeqNumber,
                 puControlLineIndex,
                 puControlPUAddress,
                 puCurrentDlci,
                 puCurrentMAC,
                 linePhysicalType,
                 puIsDynamic}
    DESCRIPTION
      "This indicates that a PU session is established on a non-explicit
      (dynamic, or broadcast) DLCI to the alternate destination MAC, if
      configured. For Conversion Node, puCurrentDlci is set to 0.
      For NetView the puControlLineIndex is set to 99, and the
      puControlPUAddress is set to 01 for primary PU and 02 for
      the alternate NetView PU."
    ::= 823

  sessDownOnPrimaryMAC  TRAP-TYPE
    ENTERPRISE   syncResearch
    VARIABLES  { lastTrapSeqNumber,
                 puControlLineIndex,
                 puControlPUAddress,
                 puLastClearCode,
                 puLastDlciCleared,
                 puLastMACCleared,
                 linePhysicalType,
                 puIsDynamic}

    DESCRIPTION
       "This trap indicates that the session for the indicated PU
        associated with the primary destination MAC was cleared.
        If the indicated PU is not in session, the trap is generated only
        if the clear code is different from the puLastClearCode.
        For NetView the puControlLineIndex is set to 99, and
        the puControlPUAddress is set to 01 for primary PU and 02
        for the alternate NetView PU.
        For Conversion Node, puLastDlicCleared is not applicable and is
        therefore set to 0"
    ::= 824

  sessDownOnAlternateMAC  TRAP-TYPE
    ENTERPRISE   syncResearch
    VARIABLES  {lastTrapSeqNumber,
                 puControlLineIndex,
                 puControlPUAddress,
                 puLastClearCode,
                 puLastDlciCleared,
                 puLastMACCleared,
                 linePhysicalType,
                 puIsDynamic}
    DESCRIPTION
       "This trap indicates that the session for the indicated PU
        associated with the alternate destination MAC, if configured,
        was cleared. If the indicated PU is not in session, the trap
        is generated only if the clear code is different from the
        puLastClearCode.
        For NetView the puControlLineIndex is set to 99, and
        the puControlPUAddress is set to 01 for primary PU and 02
        for the alternate NetView PU.
        For Conversion Node, puLastDlicCleared is not applicable and is
        therefore set to 0"
    ::= 825

  lostUNI TRAP-TYPE
    ENTERPRISE   syncResearch
    VARIABLES  { lastTrapSeqNumber,
                 linePhysicalIndex }
    DESCRIPTION
      "This trap indicates that the indicated Frame Relay
      Line or Port has lost its UNI connectivity to the Frame
      Relay network."
    ::= 826

  restoredUNI TRAP-TYPE
    ENTERPRISE   syncResearch
    VARIABLES  { lastTrapSeqNumber,
                 linePhysicalIndex }
    DESCRIPTION
      "This trap indicates that the indicated Frame Relay
      Line or Port has restored its UNI connectivity to the Frame
      Relay network."
    ::= 827


  switchedToBackup TRAP-TYPE
    ENTERPRISE   syncResearch
    VARIABLES  { lastTrapSeqNumber,
                 linePhysicalIndex }
    DESCRIPTION
      "This trap indicates that the indicated Frame Relay
      Line or Port has successfully switched to switched backup
      connection."
    ::= 828

  switchedToDed TRAP-TYPE
    ENTERPRISE   syncResearch
    VARIABLES  { lastTrapSeqNumber,
                 linePhysicalIndex }
    DESCRIPTION
      "This trap indicates that the indicated Frame Relay
      Line or Port has successfully switched to the dedicated
      Frame Relay connection to the network."
    ::= 829

  dialConnStatusChanged TRAP-TYPE
    ENTERPRISE   syncResearch
    VARIABLES  { lastTrapSeqNumber,
                 lineStatus,
                 lineControlFailureCode,
                 linePhysicalIndex }
    DESCRIPTION
      "This trap indicates that the indicated dial backup connection has
      changed state.  It has either been connected or disconnected."
    ::= 830

  sessUpOnSVC  TRAP-TYPE
    ENTERPRISE   syncResearch
    VARIABLES  { lastTrapSeqNumber,
                 puControlLineIndex,
                 puControlPUAddress,
                 puCurrentSVC,
                 puCurrentLocalDTE,
                 puCurrentRemoteDTE,
                 puIsDynamic}

    DESCRIPTION
       "This trap indicates that the session for the indicated PU or LAN
        PU  associated with the remote DTE address was established."
    ::= 831


  sessDownOnSVC  TRAP-TYPE
    ENTERPRISE   syncResearch
    VARIABLES  { lastTrapSeqNumber,
                 puControlLineIndex,
                 puControlPUAddress,
                 puLastClearCode,
                 puLastSVCCleared,
                 puLastLocalDTECleared,
                 puLastRemoteDTECleared,
                 puIsDynamic}

    DESCRIPTION
       "This trap indicates that the session for the indicated PU or LAN
        PU  associated with the last remote DTE address was cleared.
        If the indicated PU/LAN PU is not in session, the trap is generated
        only if the clear code is different from the puLastClearCode."
    ::= 832

END
