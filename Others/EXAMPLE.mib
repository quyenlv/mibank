EXAMPLE DEFINITIONS ::= BEGIN

IMPORTS
   DisplayString
        FROM SNMPv2-TC
	MODULE-IDENTITY, OBJECT-TYPE
		  FROM SNMPv2-SMI;

   exampleMIB MODULE-IDENTITY
       LAST-UPDATED "9905241000Z"
       ORGANIZATION "..."
       CONTACT-INFO "..."
       DESCRIPTION "mib-example MIB"
       ::= { experimental 4711 }

   internet-EXPERIMENTAL OBJECT IDENTIFIER ::= { exampleMIB 1 }

         examp-VERSION OBJECT-TYPE
             SYNTAX  INTEGER
             ACCESS  read-only
             STATUS  mandatory
             DESCRIPTION
                     "bla bla bla blabla bla."
             ::= { internet-EXPERIMENTAL 1 }

         examp-DESCR OBJECT-TYPE
             SYNTAX  DisplayString
             ACCESS  read-only
             STATUS  mandatory
             DESCRIPTION
                     "bla bla bla blabla bla"
             ::= { internet-EXPERIMENTAL 2 }

END

----------------------------------------------------------------------
