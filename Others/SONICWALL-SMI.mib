-- *****************************************************************
-- SONICWALL-SMI.MIB
--
-- February 2001, Susan Yan
-- Apr  2003,     Change Postal, Susan Yan
--
-- Copyright (c) 2001 - 2003 by SonicWall, Inc.
-- All rights reserved.
-- *****************************************************************


SONICWALL-SMI
 
--FORCE-INCLUDE <asn1conf.h>
--FORCE-INCLUDE <mib.h>
--FORCE-INCLUDE <snmpdefs.h>
--FORCE-INCLUDE "swMibhand.h"


DEFINITIONS ::= BEGIN

IMPORTS
	MODULE-IDENTITY,
	OBJECT-IDENTITY,
	enterprises
		FROM SNMPv2-SMI;

sonicwall MODULE-IDENTITY
	LAST-UPDATED "200304220000Z"
	ORGANIZATION "SonicWall, Inc."
	CONTACT-INFO
		"	SonicWall Inc.

		Postal: 1143 Borregas Avenue
			Sunnyvale, CA 94089
			USA

		   Tel: +1 408 745 9600
		   Fax: +1 408 745 9300

		E-mail: product@sonicwall.com"
	DESCRIPTION
		"The MIB Module for Sonicwall enterprise."
	REVISION      "200304220000Z"
	DESCRIPTION
		"Initial version."
	::= { enterprises 8741 }
	

sonicwallFw OBJECT-IDENTITY
	STATUS	current
	DESCRIPTION
		"sonicwallFw is the subtree for the sonicwall firewall production."
	::= { sonicwall 1 }

END
