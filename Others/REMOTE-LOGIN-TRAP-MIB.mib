-- SECTION 1: Top Level Definitions
 
REMOTE-LOGIN-TRAP-MIB DEFINITIONS ::= BEGIN
 
 
-- Copyright 1998 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
 
-- Imports
  
IMPORTS
      TRAP-TYPE   FROM RFC-1215
      remoteLoginTrap   FROM S5-ROOT-MIB
		s5AgRemoteLoginIp, s5AgRemoteLoginStatus FROM S5-AGENT-MIB;
  
  
-- SECTION 2: Remote login traps definitions
  
  
remoteLoginStatus  TRAP-TYPE
     ENTERPRISE  remoteLoginTrap
     VARIABLES   { s5AgRemoteLoginIp,
                  s5AgRemoteLoginStatus }
--   STATUS      mandatory
     DESCRIPTION
         " This trap is sent when someone login via telnet. 
           The status of login and the host ip are reported together."
     ::= 1

END
