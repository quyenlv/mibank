PDN-ATMSTATS-MIB DEFINITIONS ::= BEGIN

IMPORTS
	MODULE-IDENTITY , OBJECT-TYPE, Integer32, Gauge32, Counter32
		FROM SNMPv2-SMI
	TimeInterval,RowStatus
		FROM SNMPv2-TC
	ifIndex
		FROM IF-MIB
   pdnAtm
		FROM PDN-HEADER-MIB
	atmVclVpi, atmVclVci
		FROM ATM-MIB;


-- ===============================================================
--
--   ATM Stats Group
--
--  Release: 1.0  05/26/99 (Initial Release)
--
--  Last Updated:
--
--
    pdnAtmStatsMIB MODULE-IDENTITY
		LAST-UPDATED "0002281200Z"
		ORGANIZATION "Paradyne Networks
					  MIB Working Group"
		CONTACT-INFO
				      "Paradyne Networks
					   331 Newman Springs Road
		               Red Bank, NJ 07701
					   www.paradyne.com

					   General Comments to: mibwg_team@eng.paradyne.com"

		DESCRIPTION
		"This MIB Module supports ATM Statistics "

        REVISION "0004130000Z"
		DESCRIPTION "Z. Pan
			o	added pdnAtmVclCurrTable - a current 15 minute cells stats
			 	 and  pdnAtmVclHistTable - 96 -  15 minute history cells stats"

        REVISION "9905260000Z"
		DESCRIPTION "J. Strain
			o  Initial - VPL and VCL Stats Table"
	::= {  pdnAtm 3 }

pdnAtmVplStat OBJECT IDENTIFIER ::= { pdnAtmStatsMIB  1 }
pdnAtmVclStat OBJECT IDENTIFIER ::= { pdnAtmStatsMIB  2 }

-- ===============================================================
--
-- The following 2 tables were taken from draft-ietf-atommib-atm2-12.txt.
--			1) Atm VPL Statistics Table
--			2) Atm VCL Statistics Table
--
-- The following changes  were made to the VCL table:
--	  1)  This additional object 'pdnAtmVclStatRowStatus' is used to allow the
--		user to dynamically select the VCL's
--		the user would like to collect statistics on.
--				
-- ===============================================================
--
--                   Definitions of Supplemental Managed Objects
--                               for ATM Management
--
--                                  March 13, 1998
-- 
-- 						Original Authors
-- 
--                               Faye Ly  (editor)
--                               3Com Corporation
--                                 fayely@3com.com
-- 
-- 
--                              Michael Noto  (editor)
--                          Network Equipment Technologies
--                                mike_noto@net.com
-- 
-- 
--                              Andrew Smith  (editor)
--                                 Extreme Networks
--                           ansmith@extremenetworks.com
-- 
-- 
--                          Ethan Mickey Spiegel  (editor)
--                                  Cisco Systems
--                                mspiegel@cisco.com
-- 
-- 
--                               Kaj Tesink  (editor)
--                           Bell Communications Research
--                               kaj@cc.bellcore.com
-- 
-- 
-- ===============================================================

-- ===============================================================
--	
--			Atm VPL Statistics Table
--
-- ===============================================================

              pdnAtmVplStatTable   OBJECT-TYPE
                  SYNTAX       SEQUENCE OF PdnAtmVplStatEntry
                  MAX-ACCESS   not-accessible
                  STATUS       current
                  DESCRIPTION
                      "This table contains all statistic counters per
                      VPL.  It is used to monitor the usage of the VPL
                      in terms of incoming cells and outgoing cells."
                  ::= { pdnAtmVplStat 1 }
 
              pdnAtmVplStatEntry    OBJECT-TYPE
                  SYNTAX       PdnAtmVplStatEntry
                  MAX-ACCESS   not-accessible
                  STATUS       current
                  DESCRIPTION
                      "Each entry in this table represents a VPL."
                  INDEX { pdnAtmVplStatIfIndex, pdnAtmVplStatVpi }
                  ::= { pdnAtmVplStatTable 1 }
 
              PdnAtmVplStatEntry ::=
                  SEQUENCE {
                      pdnAtmVplStatIfIndex           Integer32,
                      pdnAtmVplStatVpi               Integer32,
                      pdnAtmVplStatTotalCellIns      Counter32,
                      pdnAtmVplStatClp0CellIns       Counter32,
                      pdnAtmVplStatTotalDiscards     Counter32,
                      pdnAtmVplStatClp0Discards      Counter32,
                      pdnAtmVplStatTotalCellOuts     Counter32,
                      pdnAtmVplStatClp0CellOuts      Counter32,
                      pdnAtmVplStatTaggedOuts        Counter32
              }

              pdnAtmVplStatIfIndex OBJECT-TYPE
                  SYNTAX  Integer32
                  MAX-ACCESS  read-only
                  STATUS current
                  DESCRIPTION
                      "A unique value for each interface.  Its value
                      ranges between 1 and the value of ifNumber.  The
                      value for each interface must remain constant at
                      least from one re-initialization of the entity's
                      network management system to the next re-
                      initialization."
                  ::= { pdnAtmVplStatEntry 1 }

              pdnAtmVplStatVpi OBJECT-TYPE
                  SYNTAX   Integer32
                  MAX-ACCESS   read-only
	              STATUS   current
                  DESCRIPTION
                      "The VPI value of the VPL."
                  ::= { pdnAtmVplStatEntry 2 }
 
              pdnAtmVplStatTotalCellIns OBJECT-TYPE
                  SYNTAX   Counter32
                  MAX-ACCESS   read-only
                  STATUS   current
                  DESCRIPTION
                      "The total number of valid ATM cells received by
 
                      this VPL including both CLP=0 and CLP=1 cells.
                      The cells are counted prior to the application of
                      the traffic policing."
                  ::= { pdnAtmVplStatEntry 3 }
 
              pdnAtmVplStatClp0CellIns OBJECT-TYPE
                  SYNTAX   Counter32
                  MAX-ACCESS   read-only
                  STATUS   current
                  DESCRIPTION
                      "The number of valid ATM cells received by this
                      VPL with CLP=0.  The cells are counted prior to
                      the application of the traffic policing."
                  ::= { pdnAtmVplStatEntry 4 }
 
              pdnAtmVplStatTotalDiscards OBJECT-TYPE
                  SYNTAX   Counter32
                  MAX-ACCESS   read-only
                  STATUS   current
                  DESCRIPTION
                      "The total number of valid ATM cells discarded by
                      the traffic policing entity.  This includes cells
                      originally received with CLP=0 and CLP=1."
                  ::= { pdnAtmVplStatEntry 5 }
 
              pdnAtmVplStatClp0Discards OBJECT-TYPE
                  SYNTAX   Counter32
                  MAX-ACCESS   read-only
                  STATUS   current
                  DESCRIPTION
                      "The total number of valid ATM cells received with
                      CLP=0 an  discarded by the traffic policing
                      entity."
                  ::= { pdnAtmVplStatEntry 6 }
 
              pdnAtmVplStatTotalCellOuts OBJECT-TYPE
                  SYNTAX   Counter32
                  MAX-ACCESS   read-only
                  STATUS   current
                  DESCRIPTION
                      "The total number of valid ATM cells transmitted
                      by this VPL.  This includes both CLP=0 and CLP=1
                      cells."
                  ::= { pdnAtmVplStatEntry 7 }
 
 
              pdnAtmVplStatClp0CellOuts OBJECT-TYPE
                  SYNTAX   Counter32
                  MAX-ACCESS   read-only
                  STATUS   current
                  DESCRIPTION
                      "The total number of valid ATM cells transmitted
                      with CLP=0 by this VPL."
                  ::= { pdnAtmVplStatEntry 8 }
 
              pdnAtmVplStatTaggedOuts OBJECT-TYPE
                  SYNTAX   Counter32
                  MAX-ACCESS   read-only
                  STATUS   current
                  DESCRIPTION
                      "The total number of valid ATM cells tagged by the
                      traffic policing entity from CLP=0 to CLP=1 and
                      transmitted by this VPL."
                  ::= { pdnAtmVplStatEntry 9 }

-- ===============================================================
--	
--			Atm VCL Statistics Table
--
-- ===============================================================
 
              pdnAtmVclStatTable   OBJECT-TYPE
                  SYNTAX   SEQUENCE OF PdnAtmVclStatEntry
                  MAX-ACCESS   not-accessible
                  STATUS   current
                  DESCRIPTION
                      "This table contains all statistic counters per
                      VCL.  It is used to monitor the usage of the VCL
                      in terms of incoming cells and outgoing cells."
                  ::= { pdnAtmVclStat 2 }
 
              pdnAtmVclStatEntry    OBJECT-TYPE
                  SYNTAX   PdnAtmVclStatEntry
                  MAX-ACCESS   not-accessible
                  STATUS   current
                  DESCRIPTION
                      "Each entry in this table represents a VCL."
                  INDEX {  pdnAtmVclStatIfIndex, pdnAtmVclStatVpi, pdnAtmVclStatVci }
                  ::= { pdnAtmVclStatTable 1 }
 
              PdnAtmVclStatEntry ::=
                  SEQUENCE {
                      pdnAtmVclStatIfIndex           Integer32,
                      pdnAtmVclStatVpi               Integer32,
                      pdnAtmVclStatVci               Integer32,
                      pdnAtmVclStatTotalCellIns      Counter32,
                      pdnAtmVclStatClp0CellIns       Counter32,
                      pdnAtmVclStatTotalDiscards     Counter32,
                      pdnAtmVclStatClp0Discards      Counter32,
                      pdnAtmVclStatTotalCellOuts     Counter32,
                      pdnAtmVclStatClp0CellOuts      Counter32,
                      pdnAtmVclStatTaggedOuts        Counter32,
                      pdnAtmVclStatRowStatus       	 RowStatus
                  }
 
              pdnAtmVclStatIfIndex OBJECT-TYPE
                  SYNTAX  Integer32
                  MAX-ACCESS  read-only
                  STATUS current
                  DESCRIPTION
                      "A unique value for each interface.  Its value
                      ranges between 1 and the value of ifNumber.  The
                      value for each interface must remain constant at
                      least from one re-initialization of the entity's
                      network management system to the next re-
                      initialization."
                  ::= { pdnAtmVclStatEntry 1 }
 
              pdnAtmVclStatVpi OBJECT-TYPE
                  SYNTAX     Integer32
                  MAX-ACCESS     read-only
                  STATUS     current
                  DESCRIPTION
                      "The VPI value of the VCL."
                  ::= { pdnAtmVclStatEntry 2 }

              pdnAtmVclStatVci OBJECT-TYPE
                  SYNTAX     Integer32
                  MAX-ACCESS     read-only
                  STATUS     current
                  DESCRIPTION
                      "The VCI value of the VCL."
                  ::= { pdnAtmVclStatEntry 3 }
 
              pdnAtmVclStatTotalCellIns OBJECT-TYPE
                  SYNTAX   Counter32
                  MAX-ACCESS   read-only
                  STATUS   current
                  DESCRIPTION
                      "The total number of valid ATM cells received by
                      this VCL including both CLP=0 and CLP=1 cells.
                      The cells are counted prior to the application of
                      the traffic policing."
                  ::= { pdnAtmVclStatEntry 4 }
 
              pdnAtmVclStatClp0CellIns OBJECT-TYPE
			      SYNTAX   Counter32
                  MAX-ACCESS   read-only
                  STATUS   current
                  DESCRIPTION
                      "The number of valid ATM cells received by this
                      VCL with CLP=0.  The cells are counted prior to
                      the application of the traffic policing."
                  ::= { pdnAtmVclStatEntry 5 }
 
              pdnAtmVclStatTotalDiscards OBJECT-TYPE
                  SYNTAX   Counter32
                  MAX-ACCESS   read-only
                  STATUS   current
                  DESCRIPTION
                      "The total number of valid ATM cells discarded by
                      the traffic policing entity.  This includes cells
                      originally received with CLP=0 and CLP=1."
                  ::= { pdnAtmVclStatEntry 6 }
 
              pdnAtmVclStatClp0Discards OBJECT-TYPE
                  SYNTAX   Counter32
                  MAX-ACCESS   read-only
                  STATUS   current
                  DESCRIPTION
                      "The total number of valid ATM cells received with
                      CLP=0 an  discarded by the traffic policing
                      entity."
                  ::= { pdnAtmVclStatEntry 7 }
 
              pdnAtmVclStatTotalCellOuts OBJECT-TYPE
                  SYNTAX   Counter32
                  MAX-ACCESS   read-only
                  STATUS   current
                  DESCRIPTION
                      "The total number of valid ATM cells transmitted
                      by this VCL.  This includes both CLP=0 and CLP=1
                      cells."
                  ::= { pdnAtmVclStatEntry 8 }
 
              pdnAtmVclStatClp0CellOuts OBJECT-TYPE
                  SYNTAX   Counter32
                  MAX-ACCESS   read-only
                  STATUS   current
                  DESCRIPTION
                      "The total number of valid ATM cells transmitted
                      with CLP=0 by this VCL."
                  ::= { pdnAtmVclStatEntry 9 }
 
              pdnAtmVclStatTaggedOuts OBJECT-TYPE
                  SYNTAX   Counter32
                  MAX-ACCESS   read-only
                  STATUS   current
                  DESCRIPTION
                      "The total number of valid ATM cells tagged by the
                      traffic policing entity from CLP=0 to CLP=1 and
                      transmitted by this VCL."
                  ::= { pdnAtmVclStatEntry 10 }

			pdnAtmVclStatRowStatus OBJECT-TYPE
				    SYNTAX  RowStatus
				    MAX-ACCESS  read-write
				    STATUS current
				    DESCRIPTION
			           "This object is used to create a new row
						 or delete an existing row in this table. When a new
						row is added, statistics are collected for the
						VCL. Statistics collection is terminated by deletion of the
						row."
				    ::= { pdnAtmVclStatEntry  11 }

-- ===============================================================
--
-- ATM VCL current and historical fifteen-minute interval statistics 
-- pdnAtmfVclCurrTable and pdnAtmVclHistTable
--  ZPan.

-- Current fifteen-minute interval statistics per VCL

pdnAtmVclCurrTable OBJECT-TYPE
     SYNTAX    SEQUENCE OF    PdnAtmVclCurrEntry
     MAX-ACCESS     not-accessible
     STATUS    current
     DESCRIPTION
          "This table maintains per-TP statistics for the
          fifteen-minute interval currently being collected."
     ::= { pdnAtmVclStat 3 }

pdnAtmVclCurrEntry OBJECT-TYPE
     SYNTAX    PdnAtmVclCurrEntry
     MAX-ACCESS     not-accessible
     STATUS    current
     DESCRIPTION
          "An entry in this table for VCL termination points.
          Each VCL Termination Point automatically has
          an entry in this table associated with it."
     INDEX     { ifIndex, 
		 atmVclVpi,
		 atmVclVci }
     ::= { pdnAtmVclCurrTable 1 }

PdnAtmVclCurrEntry ::= SEQUENCE {
     pdnAtmVclCurrElapsedTime 	     TimeInterval,
     pdnAtmVclCurrTotalCellIns       Gauge32,
     pdnAtmVclCurrTotalInDiscards    Gauge32,
     pdnAtmVclCurrTotalCellOuts      Gauge32,
     pdnAtmVclCurrTotalOutDiscards   Gauge32
          }

pdnAtmVclCurrElapsedTime OBJECT-TYPE
     SYNTAX TimeInterval
     MAX-ACCESS read-only
     STATUS current
     DESCRIPTION
          "Amount of time, measured in seconds, that statistics
          for this entry (the current interval) have been counted."
     ::= { pdnAtmVclCurrEntry 1 }

pdnAtmVclCurrTotalCellIns OBJECT-TYPE
     SYNTAX    Gauge32
     MAX-ACCESS     read-only
     STATUS    current
     DESCRIPTION
          "The total number of valid ATM cells received by this VCL.
	       This number corresponds to that of toal cells recieved
           from CPE if this interface is a DSL ATM interface" 
     ::= { pdnAtmVclCurrEntry 2 }

pdnAtmVclCurrTotalInDiscards OBJECT-TYPE
     SYNTAX    Gauge32
     MAX-ACCESS     read-only
     STATUS    current
     DESCRIPTION
          "The number of discarded received cells."
     ::= { pdnAtmVclCurrEntry 3 }

pdnAtmVclCurrTotalCellOuts OBJECT-TYPE
     SYNTAX    Gauge32
     MAX-ACCESS     read-only
     STATUS    current
     DESCRIPTION
          "The number of cells that have been successfully sent.
	       This number corresponds to that of toal cells transmitted
           to CPE if this interface is a DSL ATM interface" 
     ::= { pdnAtmVclCurrEntry 4 }

pdnAtmVclCurrTotalOutDiscards OBJECT-TYPE
     SYNTAX    Gauge32
     MAX-ACCESS     read-only
     STATUS    current
     DESCRIPTION
          "The number of discarded transmitted cells since this interval."
     ::= { pdnAtmVclCurrEntry 5 }


-- History fifteen-minute interval statistics per VCL and time interval
-- These data are only recorded for permanent connections.

pdnAtmVclHistTable OBJECT-TYPE
     SYNTAX    SEQUENCE OF    PdnAtmVclHistEntry
     MAX-ACCESS     not-accessible
     STATUS    current
     DESCRIPTION
          "This table maintains per-interface statistics for previous
          fifteen-minute intervals."
     ::= { pdnAtmVclStat 4 }

pdnAtmVclHistEntry OBJECT-TYPE
     SYNTAX    PdnAtmVclHistEntry
     MAX-ACCESS     not-accessible
     STATUS    current
     DESCRIPTION
          "An entry in History Data table for VCL termination points.
          Each VCL Termination Point automatically has
          an entry in this table associated with it."
     INDEX     { ifIndex,
		     atmVclVpi,
		     atmVclVci,
	         pdnAtmVclHistIndex }
     ::= { pdnAtmVclHistTable 1 }

PdnAtmVclHistEntry ::= SEQUENCE {
     pdnAtmVclHistIndex            Integer32,
     pdnAtmVclHistElapsedTime      TimeInterval,
     pdnAtmVclHistTotalCellIns     Gauge32,
     pdnAtmVclHistTotalInDiscards  Gauge32,
     pdnAtmVclHistTotalCellOuts    Gauge32,
     pdnAtmVclHistTotalOutDiscards Gauge32
          }

pdnAtmVclHistIndex OBJECT-TYPE
     SYNTAX    Integer32 (1..96)
     MAX-ACCESS     not-accessible
     STATUS    current
     DESCRIPTION
          "A number between 1 and 96, which identifies the interval
          for which the set of statistics in this entry was
          collected.
          The interval identified by 1 is the most recently completed
          15 minute interval, and the interval identified by N is the
          interval immediately preceding the one identified by N-1."
     ::= { pdnAtmVclHistEntry 1 }

pdnAtmVclHistElapsedTime OBJECT-TYPE
     SYNTAX    TimeInterval
     MAX-ACCESS     read-only
     STATUS    current
     DESCRIPTION
          "Amount of Time, measured in units of 0.01 second, that
 	   statistics for this entry(the current interval) have been
	   counted."
     ::= { pdnAtmVclHistEntry 2 }

pdnAtmVclHistTotalCellIns OBJECT-TYPE
     SYNTAX    Gauge32
     MAX-ACCESS     read-only
     STATUS    current
     DESCRIPTION
          "The total number of valid ATM cells received by this VCL
	   during this interval.
	   This number corresponds to that of toal cells recieved
           from CPE if this interface is a DSL ATM interface" 
     ::= { pdnAtmVclHistEntry 3 }

pdnAtmVclHistTotalInDiscards OBJECT-TYPE
     SYNTAX    Gauge32
     MAX-ACCESS     read-only
     STATUS    current
     DESCRIPTION
          "The number of discarded received cells during this interval."
     ::= { pdnAtmVclHistEntry 4 }

pdnAtmVclHistTotalCellOuts OBJECT-TYPE
     SYNTAX    Gauge32
     MAX-ACCESS     read-only
     STATUS    current
     DESCRIPTION
          "The number of cells that have been successfully sent during
	       this interval.
	       This number corresponds to that of toal cells transmitted
           to CPE if this interface is a DSL ATM interface" 
     ::= { pdnAtmVclHistEntry 5 }

pdnAtmVclHistTotalOutDiscards OBJECT-TYPE
     SYNTAX    Gauge32
     MAX-ACCESS     read-only
     STATUS    current
     DESCRIPTION
          "The number of discarded transmitted cells during this interval."
     ::= { pdnAtmVclHistEntry 6 }

END

-- ===============================================================
-- Copyright (C) 2000 Paradyne Corporation.
--  ATM Extension Group
