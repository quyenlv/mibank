-- *****************************************************************
-- RBN-SMI.my:	RedBack Networks Structure of Management Information
--
-- Copyright (c) 1998 RedBack Networks, Inc.
-- All rights reserved.
-- 
-- *****************************************************************

RBN-SMI DEFINITIONS ::= BEGIN

IMPORTS
	MODULE-IDENTITY,
	OBJECT-IDENTITY,
	enterprises
		FROM SNMPv2-SMI;

redBackNetworks MODULE-IDENTITY
	LAST-UPDATED	"9803242300Z"
	ORGANIZATION	"RedBack Networks, Inc."
	CONTACT-INFO
		"	RedBack Networks, Inc.

		Postal:	1389 Moffett Park Drive
			Sunnyvale, CA  94089-1134
			USA

		 Phone:	+1 408 548 3500
		   Fax: +1 408 548 3599

		E-mail:	mib-info@RedBackNetworks.com"
	DESCRIPTION
		"The Structure of Management Information for
		RedBack Networks"
	::= { enterprises 2352 }

rbnProducts OBJECT-IDENTITY
	STATUS	current
	DESCRIPTION
		""
	::= { redBackNetworks 1 }

rbnMgmt OBJECT-IDENTITY
	STATUS current
	DESCRIPTION
		""
	::= { redBackNetworks 2 }

rbnExperiment OBJECT-IDENTITY
	STATUS current
	DESCRIPTION
		""
	::= { redBackNetworks 3 }

rbnCapabilities OBJECT-IDENTITY
	STATUS current
	DESCRIPTION
		""
	::= { redBackNetworks 4 }

rbnModules OBJECT-IDENTITY
	STATUS current
	DESCRIPTION
		""
	::= { redBackNetworks 5 }

rbnEntities OBJECT-IDENTITY
	STATUS current
	DESCRIPTION
		""
	::= { redBackNetworks 6 }

END
