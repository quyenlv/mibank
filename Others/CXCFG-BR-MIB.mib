-- Definitions

   CXCFG-BR-MIB DEFINITIONS ::= BEGIN

--#CURRENT-VERSION 1

   IMPORTS
       OBJECT-TYPE
           FROM RFC-1212
       Alias, cxCfgDot1dBase, cxCfgSrBase  
           FROM CXProduct-SMI;

-- Following objects: cxCfgDot1dBaseNumOfDBFilterEntries
-- and cxCfgDot1dBaseNumOfStaticDBFilterEntries only apply to STP bridge.

   cxCfgDot1dBaseNumOfDBFilterEntries OBJECT-TYPE
       SYNTAX  INTEGER
       ACCESS  read-write
       STATUS  mandatory
       DESCRIPTION
"Determines the number of entries in the filtering database. Available RAM
is the parameter.

Range of Values: None

Default Value: None

Configuration Changed: Administrative"

       ::= { cxCfgDot1dBase 1 }

   cxCfgDot1dBaseNumOfStaticDBFilterEntries OBJECT-TYPE
       SYNTAX  INTEGER
       ACCESS  read-write
       STATUS  mandatory
       DESCRIPTION
"Determines the number of static entries in the filtering database.
Available RAM is the parameter.

Range of Values:  None

Default Value:  None

Configuration Changed:  Administrative"

       ::= { cxCfgDot1dBase 2 }


-- The Configuration Base Port Table for STP 

   cxCfgDot1dBasePortTable OBJECT-TYPE
       SYNTAX  SEQUENCE OF CxCfgDot1dBasePortEntry
       ACCESS  not-accessible
       STATUS  mandatory
       DESCRIPTION
"A table that contains basic information about every port that is associated 
with this bridge."

       ::= { cxCfgDot1dBase 3 }

   cxCfgDot1dBasePortEntry OBJECT-TYPE
       SYNTAX  CxCfgDot1dBasePortEntry
       ACCESS  not-accessible
       STATUS  mandatory
       DESCRIPTION
"Contains configuration information for each port of the bridge."

       INDEX  { cxCfgDot1dBasePort }
       ::= { cxCfgDot1dBasePortTable 1 }

   CxCfgDot1dBasePortEntry ::=
       SEQUENCE {
       cxCfgDot1dBasePort
           INTEGER,
       cxCfgDot1dBasePortIfIndex
           INTEGER,
       cxCfgDot1dBasePortSubnetworkSapAlias
           Alias,
       cxCfgDot1dBasePortRowStatus
           INTEGER,
       cxCfgDot1dBasePortState  
           INTEGER,
       cxCfgDot1dBasePortPriority  
           INTEGER
       }

   cxCfgDot1dBasePort OBJECT-TYPE
       SYNTAX  INTEGER (1..65535)
       ACCESS  read-only
       STATUS  mandatory
       DESCRIPTION
"Displays the port number.

Options:
The acceptable values depend on the type of device that you are configuring.

In the CX900 architecture:
11, 21, 31, 41, 51, 61 or 71. The first digit identifies the slot number
the I/O board resides in, the second digit identifies the number of the port
on the I/O board.

In the CX1000 architecture:
Accepts only the value '1'. The LAN module only supports 1 port per I/O 
board. You distinguish between multiple I/O boards by specifying the slot 
number of the I/O board using another object.

Default Value: 1"

       ::= { cxCfgDot1dBasePortEntry 1 }

   cxCfgDot1dBasePortIfIndex OBJECT-TYPE
       SYNTAX  INTEGER
       ACCESS  read-only
       STATUS  mandatory
       DESCRIPTION
"Displays the table row that contains configuration or monitoring objects
for a specific type of physical interface.

Range of Values: From 1 to the total number of entries in the 
Interface Table.

Default Value: '0' indicates there is no corresponding entry in the
Interface Table for this port. "

       ::= { cxCfgDot1dBasePortEntry 2 }

   cxCfgDot1dBasePortSubnetworkSapAlias OBJECT-TYPE
       SYNTAX  Alias
       ACCESS  read-write
       STATUS  mandatory
       DESCRIPTION
"Specifies a name (alias) for the physical or convergence port to which this
port binds in order to establish a circuit for transmission. This value must
match a physical or convergence port's alias, as defined by the
cxLanIoPortAlias object in the cxLanIoPortTable or by the object 
cxConvPortAlias in the cxConvTable.

Range of Values: From 1 to 32 alphanumeric characters. You can use any 
combination of letters and numbers however, you cannot use blank spaces. 
Use a dash or underscore as a delimiter.

Default Value: LAN-PORT1

Configuration Changed: Administrative"

       ::= { cxCfgDot1dBasePortEntry 3 }

   cxCfgDot1dBasePortRowStatus  OBJECT-TYPE
        SYNTAX  INTEGER {
                     invalid (1),
                     valid   (2)
                  }
        ACCESS  read-write
        STATUS  mandatory
        DESCRIPTION
"Determines the status of the objects in a table row.

Options:
invalid (1): Row is flagged; after the next reset the values will be
disabled and the row will be deleted from the table).

valid (2): Values are enabled.

Default value:  valid (2)

Configuration Changed: Administrative"
        DEFVAL { valid }
       ::= { cxCfgDot1dBasePortEntry 4 }

       
   cxCfgDot1dBasePortState   OBJECT-TYPE
       SYNTAX  INTEGER {
                on (1),
                off (2),
                onether (3),
                ontoken (4)
               }
       ACCESS  read-write
       STATUS  mandatory
          
       DESCRIPTION
"Determines the state of the STP port. 

Options: 
On (1): The STP port is set to on.

Off (2): The STP port is set to off.

OnEther (3): The Ethernet STP port will bind to IP.

OnToken (4): The Token Ring STP port will bind to IP.

Default value:  On (1)

Configuration Changed: Administrative"
        DEFVAL { on }
       ::= {cxCfgDot1dBasePortEntry  5 }


     cxCfgDot1dBasePortPriority  OBJECT-TYPE
          SYNTAX  INTEGER {
                     discard(1),
                     forward(2),
                     priority-low(3),
                     priority-high(4)
                    
                  }
          ACCESS  read-write
          STATUS  mandatory
          DESCRIPTION 
"Determines the filtering/forwarding action and the forwarding priority
for data sent from the STP bridge.
 
Options:
discard (1): Do not forward the data.

forward (2): Forward the data.

priority-low (3): Forward with a low priority (Frame Relay only).

priority-high (4): Forward with a high priority (Frame Relay only).
 
Default Value:  forward (2)

Configuration Changed:  Administrative"
        DEFVAL { forward }
     ::= { cxCfgDot1dBasePortEntry 6 }


-- The Configuration Base Port Table for SR

   cxCfgSrBasePortTable OBJECT-TYPE
       SYNTAX  SEQUENCE OF CxCfgSrBasePortEntry
       ACCESS  not-accessible
       STATUS  mandatory
       DESCRIPTION
"A table that contains basic information about every port that is associated
with this SR bridge."

       ::= { cxCfgSrBase 1 }

   cxCfgSrBasePortEntry OBJECT-TYPE
       SYNTAX  CxCfgSrBasePortEntry
       ACCESS  not-accessible
       STATUS  mandatory
       DESCRIPTION
"Configuration information for each port of the SR bridge."

       INDEX  { cxCfgSrBasePort }
       ::= { cxCfgSrBasePortTable 1 }

   CxCfgSrBasePortEntry ::=
       SEQUENCE {
       cxCfgSrBasePort
           INTEGER,
       cxCfgSrBasePortIfIndex
           INTEGER,
       cxCfgSrBasePortSubnetworkSapAlias
           Alias,
       cxCfgSrBasePortRowStatus
           INTEGER,
       cxCfgSrBasePortState  
           INTEGER,
       cxCfgSrBasePortPriority
           INTEGER
       }

   cxCfgSrBasePort OBJECT-TYPE
       SYNTAX  INTEGER (1..65535)
       ACCESS  read-only
       STATUS  mandatory
       DESCRIPTION
"Displays the port number.

Options:
The acceptable values depend on the type of device that you are configuring.

In the CX 900 architecture:
11, 21, 31, 41, 51, 61 or 71. The first digit identifies the slot number 
the I/O board resides in, the second digit identifies the number of the port
on the I/O board.

In the CX 1000 architecture:
Accepts only the value '1'. The LAN module only supports 1 port per I/O
board. You distinguish between multiple I/O boards by specifying the slot 
number of the I/O board using another object.

Default Value: 1 "

       ::= { cxCfgSrBasePortEntry 1 }

   cxCfgSrBasePortIfIndex OBJECT-TYPE
       SYNTAX  INTEGER
       ACCESS  read-only
       STATUS  mandatory
       DESCRIPTION
"Displays the table row that contains configuration or monitoring objects 
for a specific type of physical interface.

Range of Values: From 1 to the total number of entries in the 
Interface Table.

Default Value: '0' indicates there is no corresponding entry in the 
Interface Table for this port."

       ::= { cxCfgSrBasePortEntry 2 }

   cxCfgSrBasePortSubnetworkSapAlias OBJECT-TYPE
       SYNTAX  Alias
       ACCESS  read-write
       STATUS  mandatory
       DESCRIPTION
"Specifies a name (alias) for the physical or convergence port to which this
SR port binds in order to establish a circuit for transmission.  This value 
must match a physical or convergence port's alias as defined by the object
cxLanIoPortAlias of the cxLanIoPortTable or by the object cxConvPortAlias of 
the cxConvTable.

Range of Values: From 1 to 32 alphanumeric characters. You can use any 
combination of letters and numbers however, you cannot use blank spaces.  
Use a dash or underscore as a delimiter.

Default Value: LAN-PORT1

Configuration Changed: Administrative"

       ::= { cxCfgSrBasePortEntry 3 }

       
   cxCfgSrBasePortRowStatus  OBJECT-TYPE
        SYNTAX  INTEGER {
                     invalid (1),
                     valid   (2)
                  }
        ACCESS  read-write
        STATUS  mandatory
        DESCRIPTION
"Determines the status of the objects in a table row.

Options:
invalid (1): Row is flagged. After the next reset the values will be
disabled and the row will be deleted from the table.

valid (2): Values are enabled.

Default Value: (2)

Configuration Changed: Administrative"
        DEFVAL { valid }
       ::= { cxCfgSrBasePortEntry 4 }

   cxCfgSrBasePortState   OBJECT-TYPE
       SYNTAX  INTEGER {
                on (1),
                off (2),
                ontoken (3)
               }
       ACCESS  read-write
       STATUS  mandatory
          
       DESCRIPTION
"Determines the state of the SR port. You can control activity at the port
by changing this value.

Options: 
on (1): The SR port is set to on.

off (2): The SR port is set to off.

OnToken (4): The Token Ring SR port will bind to IP.

Default Value: (1)

Configuration Changed: Administrative"
          DEFVAL { on }  
       ::= {cxCfgSrBasePortEntry 5 }

     cxCfgSrBasePortPriority  OBJECT-TYPE
          SYNTAX  INTEGER {
                     discard(1),
                     forward(2),
                     priority-low(3),
                     priority-high(4)
                     
                  }
          ACCESS  read-write
          STATUS  mandatory
          DESCRIPTION 
"Determines the filtering/forwarding action and the forwarding priority
for data sent from the SR bridge.
 
Options:
discard (1): Do not forward the data.

forward (2): Forward the data.

priority-low (3): Forward with a low priority (Frame Relay only).

priority-high (4): Forward with a high priority (Frame Relay only).
 
Default value:  (2)

Configuration Changed: Administrative"
        DEFVAL { forward }
     ::= { cxCfgSrBasePortEntry 6 }


cxCfgDot1dBaseMibLevel OBJECT-TYPE
   SYNTAX   INTEGER
   ACCESS   read-only
   STATUS   mandatory
   DESCRIPTION
"Used to determine current MIB module release supported
by the agent. Object is in decimal."
   DEFVAL { 0 }
   --#STARTING-VERSION 1
   ::= { cxCfgDot1dBase 4 }

   END
