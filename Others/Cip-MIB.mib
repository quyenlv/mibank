Cip-MIB DEFINITIONS ::= BEGIN
	IMPORTS
          MODULE-IDENTITY, OBJECT-TYPE, Integer32,
	  Counter32, Gauge32 , IpAddress
                FROM SNMPv2-SMI
          DisplayString, DateAndTime
                FROM SNMPv2-TC
          UsrLongString, common
                FROM USR-DEFINITIONS-MIB;
    usrCip   MODULE-IDENTITY
         LAST-UPDATED "200208012020Z"
         ORGANIZATION "CommWorks Corporation, a 3Com Company"
         CONTACT-INFO "Customer Support"
         DESCRIPTION
                 "The commWorks enterprise defined MIB objects
                   for CIP"
--      REVISION "200202182020Z"
--      DESCRIPTION
--              "Converted to SNMPv2"
         ::= { common 10 }
   -- textual conventions
   -- 
   -- textual conventions are like pre-processor macro in 'C'
   --        (i.e. #define statements)
   -- Use them to define your own 'datatypes'
   NetNumber ::= OCTET STRING (SIZE(4))
   -- Begin managed object definitions here...
    usrCipPortParamTable OBJECT-TYPE
         SYNTAX  SEQUENCE OF USRCIPPortParamEntry
         MAX-ACCESS  not-accessible
         STATUS  current
         DESCRIPTION
            "This table contains the serial port parameters."
	::= { usrCip 1 }
    usrCipPortParamEntry OBJECT-TYPE
        SYNTAX      USRCIPPortParamEntry
        MAX-ACCESS  not-accessible
        STATUS      current
        DESCRIPTION "Each entry corresponds to a serial interface."
        INDEX   {
                usrCipPortIndex
               }
     ::= {usrCipPortParamTable 1}
     USRCIPPortParamEntry ::= 
          SEQUENCE {
               usrCipPortIndex
                    Integer32,
               usrCipPortType
                    INTEGER,
               usrCipPortAccess
                    INTEGER,
               usrCipPortHostType
                    INTEGER,
               usrCipPortLoginService
                    INTEGER,
               usrCipPortTcpPortNumber
                    Integer32,
               usrCipPortLoginMsg
                    OCTET STRING,
               usrCipPortLoginPrompt
                    OCTET STRING,
               usrCipPortIpAddress
                    IpAddress,
               usrCipPortHostIpAddress
                    IpAddress,
               usrCipPortNetMask
                    Integer32,
               usrCipPortProtocol
                    INTEGER,
               usrCipPortMtu
                    Integer32,
               usrCipPortIdleTimeOut
                    Integer32,
               usrCipPortState
                    INTEGER,
               usrCipPortNumConns
                    Counter32,
               usrCipPortConnType
                    INTEGER,
               usrCipUserName
                    OCTET STRING,
               usrCipConnStartTime
                    Integer32,
               usrCipDataLinkConn
                    INTEGER,
               usrCipInitScriptName
                    DisplayString,
               usrCipIfConnType
                    INTEGER,
               usrCipPromptUserName
                    OCTET STRING,
               usrCipUserPasswd
                    OCTET STRING,
               usrCipPortIfName
                    OCTET STRING,
               usrCipPortDialPrefix
                    OCTET STRING,
               usrCipPortCfgScript
                    DisplayString,
               usrCipPortCfgScriptResult
                    UsrLongString,
               usrCipPortPromptingStyle
                    INTEGER,
               usrCipPortLoginProcessing
                    INTEGER,
               usrCipPortCallType
                   INTEGER,
	       usrCipPortDNISAuthentication
		   INTEGER,
	       usrCipPortDNISAuthTime
		   INTEGER,
	       usrCipPortDNISAuthType
		   INTEGER,
	       usrCipPortDNISPassword
		   OCTET STRING, 
	       usrCipPortDNISTimeout
		   Integer32,
	       usrCipPortParity
		   INTEGER,
               usrCipPortDomainName
                    OCTET STRING,
               usrCipPortDelimiter 
                    OCTET STRING,
               usrCipPromptDelay 
                   Integer32,
	       usrCipPromptTimeout
		   Integer32,
	       usrCipSpecialXonXoffFlow
                   INTEGER,
               usrCipCalledPhoneNumber
                   OCTET STRING,
	       usrCipCallingPhoneNumber
                   OCTET STRING,
	       usrCipPortGlobalConnId
		   Integer32,
	       usrCipPortUseDnisPool
		   INTEGER,
	       usrCipPortLoginTable
		   OCTET STRING,
     		usrCipPortMobileType
		   INTEGER
               }
     usrCipPortIndex OBJECT-TYPE
          SYNTAX      Integer32
          MAX-ACCESS  not-accessible
          STATUS      current
          DESCRIPTION "The identifier of the physical interface."
     ::= {usrCipPortParamEntry 1}
     usrCipPortType OBJECT-TYPE
          SYNTAX      INTEGER {
                         login (1),
                         network (2),
                         login-network (3)
                         }
          MAX-ACCESS  read-write
          STATUS      current
          DESCRIPTION "The type of the physical port."
        --CONFIGURABLE
     ::= {usrCipPortParamEntry 2}
     usrCipPortAccess OBJECT-TYPE
          SYNTAX      INTEGER {
                         dial-in(1),
                         dial-out(2),
                         two-way(3)
                       }
          MAX-ACCESS  read-write
          STATUS      current
          DESCRIPTION "This field specifies the direction of the calls
                         that could be made on a specific interface. 
                         Ports could be configured to be dial-in, dial-out
                         or two-way ports."
       --CONFIGURABLE
     ::= {usrCipPortParamEntry 3}
     usrCipPortHostType OBJECT-TYPE
          SYNTAX      INTEGER {
                         undefined (0),
                         default (1),
                         prompt (2),
                         specified (3)
                         }
          MAX-ACCESS  read-write
          STATUS      current
          DESCRIPTION "The host type that the dial-in user 
                       will be connected to."
        --CONFIGURABLE
     ::= {usrCipPortParamEntry 4}
     usrCipPortLoginService OBJECT-TYPE
          SYNTAX      INTEGER {
                         telnet (1),
                         rlogin (2),
                         cleartcp (3),
                         ping (4)
                         }
          MAX-ACCESS  read-write
          STATUS      current
          DESCRIPTION "The Service type that the dial-in user will 
                       be connected to."
        --CONFIGURABLE
     ::= {usrCipPortParamEntry 5}
     usrCipPortTcpPortNumber OBJECT-TYPE
          SYNTAX      Integer32
          MAX-ACCESS  read-write
          STATUS      current
          DESCRIPTION "The tcp port number associated with the service type."
        --CONFIGURABLE
     ::= {usrCipPortParamEntry 6}
     usrCipPortLoginMsg OBJECT-TYPE
          SYNTAX      OCTET STRING (SIZE(0..800))
          MAX-ACCESS  read-write
          STATUS      current
          DESCRIPTION "The salutation message associated with a specific port."
        --CONFIGURABLE
     ::= {usrCipPortParamEntry 7}
     usrCipPortLoginPrompt OBJECT-TYPE
   	  SYNTAX      OCTET STRING (SIZE(0..64))
   	  MAX-ACCESS  read-write
   	  STATUS      current
   	  DESCRIPTION "The login prompt associated with a specific port."
        --CONFIGURABLE
     ::= {usrCipPortParamEntry 8}
     usrCipPortIpAddress OBJECT-TYPE
   	  SYNTAX      IpAddress
   	  MAX-ACCESS  read-write
   	  STATUS      current
	  DESCRIPTION "The IP address for a specific serial port."
        --CONFIGURABLE
      ::= {usrCipPortParamEntry 9}
     usrCipPortHostIpAddress OBJECT-TYPE
   	  SYNTAX      IpAddress
   	  MAX-ACCESS  read-write
   	  STATUS      current
	  DESCRIPTION "A host IP address specified for this interface."
        --CONFIGURABLE
   	::= {usrCipPortParamEntry 10}
     usrCipPortNetMask OBJECT-TYPE
   	  SYNTAX      Integer32
   	  MAX-ACCESS  read-write
   	  STATUS      current
   	  DESCRIPTION "The netmask associated with a specific 
                       serial interface."
        --CONFIGURABLE
     ::= {usrCipPortParamEntry 11}
     usrCipPortProtocol OBJECT-TYPE
   	  SYNTAX      INTEGER {
                         ppp (1),
                         slip (2),
                         arap (3)
                    	   }
   	  MAX-ACCESS  read-write
   	  STATUS      current
   	  DESCRIPTION "The protocol type configured for a specific interface."
        --CONFIGURABLE
     ::= {usrCipPortParamEntry 12}
     usrCipPortMtu OBJECT-TYPE
   	  SYNTAX      Integer32
   	  MAX-ACCESS  read-write
   	  STATUS      current
   	  DESCRIPTION "The mtu value associated with a specific interface."
        --CONFIGURABLE
     ::= {usrCipPortParamEntry 13}
     usrCipPortIdleTimeOut OBJECT-TYPE
   	  SYNTAX      Integer32
   	  MAX-ACCESS  read-write
   	  STATUS      current
   	  DESCRIPTION "The maximum idle time specified for an interface."
        --CONFIGURABLE
     ::= {usrCipPortParamEntry 14}
     usrCipPortState OBJECT-TYPE
          SYNTAX        INTEGER {
                          port-disabled (0),
                          port-initializing(1),
                          port-available(2),
                          port-connecting(3),
                          port-connected(4),
                          port-disconnecting(5),
                          port-disconnected(6)
                           }
          MAX-ACCESS    read-only
          STATUS        current
          DESCRIPTION  "The state of the serial line."
     ::= {usrCipPortParamEntry 15}
     usrCipPortNumConns OBJECT-TYPE
   	  SYNTAX      Counter32
   	  MAX-ACCESS  read-only
   	  STATUS      current
   	  DESCRIPTION "The total number of connections made on this if."
     ::= {usrCipPortParamEntry 16}
     usrCipPortConnType OBJECT-TYPE
          SYNTAX        INTEGER {
                          undefined-conn(0),
                          on-demand-conn(1),
                          dial-back-conn(2),
                          continuous-conn(3),
                          manual-conn(4),
                          timed-conn(5),
                          shared-modem-conn(6),
                          dial-in-conn(7),
                          bond-conn(8),
                          dedicated-conn (9)
                           }
          MAX-ACCESS    read-only
          STATUS        current
          DESCRIPTION  "The connection type on this interface."
     ::= {usrCipPortParamEntry 17}
     usrCipUserName OBJECT-TYPE
          SYNTAX      OCTET STRING (SIZE(0..32))
   	  MAX-ACCESS  read-only
   	  STATUS      current
   	  DESCRIPTION "The name user connected to this interface. "
     ::= {usrCipPortParamEntry 18}
     usrCipConnStartTime OBJECT-TYPE
          SYNTAX      Integer32
          MAX-ACCESS  read-only
          STATUS      current
          DESCRIPTION "The start time of a connection specified 
                       on an interface."
     ::= {usrCipPortParamEntry 19}
     usrCipDataLinkConn OBJECT-TYPE
          SYNTAX        INTEGER {
                           undefined(0),
                           telnet (1),
                           rlogin (2),
                           clear-tcp (3),
                           ppp (4),
                           arap (5),
                           slip (6),
                           admin(7),
                           ping(8),
                           none(9),
                           lt2p(10),
                           pptp(11),
                           tap(12),
                           cliNas(13),
                           shell(14),
                           pingIp (15),
                           vtp (16),
                           sipRpt7111a (17),    -- wireline only
                           sipRpt7111m (18),    -- wireline only
                           sipRpt729 (19)       -- wireline only
                           }
          MAX-ACCESS    read-only
          STATUS        current
          DESCRIPTION  "The data link layer that a specific dial-in session is
                        connected to."
     ::= {usrCipPortParamEntry 20}
     usrCipInitScriptName OBJECT-TYPE
          SYNTAX      DisplayString  (SIZE(0..7))
          MAX-ACCESS  read-write
          STATUS      current
          DESCRIPTION "The name of the script"
        --CONFIGURABLE
     ::= { usrCipPortParamEntry 21 }
     usrCipIfConnType OBJECT-TYPE
          SYNTAX      INTEGER {
                        if-direct-conn (1),
                        if-direct-network-conn (2),
                        if-normal-conn (3),
                        if-prompt-passwd (4),
                        if-prompt-none (5),
						if-ppp-only(6)
                        }
          MAX-ACCESS  read-write
          STATUS      current
          DESCRIPTION "The type of the connection that i/f is configured for."
        --CONFIGURABLE
     ::= { usrCipPortParamEntry 22 }
     usrCipPromptUserName OBJECT-TYPE
          SYNTAX        OCTET STRING (SIZE(0..32))
          MAX-ACCESS    read-write
          STATUS        current
          DESCRIPTION   "This could only be set if the port is
                        configured not to prompt for username."
     --CONFIGURABLE
     ::= {usrCipPortParamEntry 23}
     usrCipUserPasswd OBJECT-TYPE
          SYNTAX      OCTET STRING (SIZE(0..15))
   	  MAX-ACCESS  read-write
   	  STATUS      current
   	  DESCRIPTION "This could only be set if the port is 
                       configured to not prompt for password."
        --CONFIGURABLE
     ::= { usrCipPortParamEntry 24 }
     usrCipPortIfName OBJECT-TYPE
          SYNTAX      OCTET STRING (SIZE(0..32))
   	  MAX-ACCESS  read-only
   	  STATUS      current
   	  DESCRIPTION "The name of the serial line interface."
     ::= { usrCipPortParamEntry 25 }
     usrCipPortDialPrefix OBJECT-TYPE
         SYNTAX         OCTET STRING (SIZE(0..64))
         MAX-ACCESS     read-write
         STATUS         current
         DESCRIPTION    "This string defines the prefix to the phone number."
       --CONFIGURABLE
    ::= {usrCipPortParamEntry 26}
    usrCipPortCfgScript OBJECT-TYPE
         SYNTAX         DisplayString (SIZE(0..32))
         MAX-ACCESS     read-write
         STATUS         current
         DESCRIPTION    "This string defines an I-modem or V.34 AT command
            			 a value of RESET will cause the modem to be reset 
                         and reinitialized with the string found in 
                         usrInitScriptCommands.
                         A value of zero indicates no command exists. It
                         cannot be SET to NULL."
    ::= { usrCipPortParamEntry 27 }
    usrCipPortCfgScriptResult OBJECT-TYPE
         SYNTAX         UsrLongString (SIZE(0..1350))
         MAX-ACCESS     read-only
         STATUS         current
         DESCRIPTION    "This string defines the result of the AT command.
                         NVT ASCII characters."
    ::= { usrCipPortParamEntry 28 }
    usrCipPortPromptingStyle OBJECT-TYPE
         SYNTAX        INTEGER {
                           local-prompting(1),
                           remote-prompting(2)
                       }                                                  
         MAX-ACCESS    read-write
         STATUS        current 
         DESCRIPTION   "This value specifies whether the NAS will provide
                       username and password prompting locally or if the  
                       prompting will be handled by a remote security server."
       --CONFIGURABLE 
    ::= { usrCipPortParamEntry 29 }
    usrCipPortLoginProcessing OBJECT-TYPE
        SYNTAX INTEGER {
                       disable-auth-for-none (1),
                       disable-auth-for-async-ppp (2),
                       disable-auth-for-sync-ppp (3),
                       disable-auth-for-ppp (4)
                       }
        MAX-ACCESS read-write
        STATUS current
        DESCRIPTION
            "This variable controls login processing.  This value can be set
             for controlling user authentication for different types of 
	     autodetected PPP calls. Default is authentication is done for 
	     all types of PPP calls.."
        --CONFIGURABLE
        ::= {usrCipPortParamEntry 30}
     usrCipPortDomainName OBJECT-TYPE
          SYNTAX      OCTET STRING (SIZE(0..240))
          MAX-ACCESS  read-write
          STATUS      current
          DESCRIPTION "The Domain Name associated with this port "
       --CONFIGURABLE
     ::= { usrCipPortParamEntry 31 }
     usrCipPortDelimiter  OBJECT-TYPE
          SYNTAX  OCTET STRING    (SIZE (0..1))
          MAX-ACCESS  read-write
          STATUS  current
          DESCRIPTION      
              "The delimiter string port domain configuration"
          --CONFIGURABLE   
          ::= { usrCipPortParamEntry 32 } 
usrCipPortCallType OBJECT-TYPE
        SYNTAX INTEGER {
                       call-type-pptp(1),
                       call-type-l2tp(2),
                       call-type-none(3)
                       }
        MAX-ACCESS read-write
        STATUS current
        DESCRIPTION
            "This variable call type associated with the interface."
        --CONFIGURABLE
        ::= {usrCipPortParamEntry 33}
	usrCipPortDNISAuthentication  OBJECT-TYPE
         SYNTAX INTEGER 
		 {
                 dnis-auth-disabled (1),
                 dnis-auth-preferred (2),
                 dnis-auth-required (3)
                 }
         MAX-ACCESS  read-write
         STATUS  current
         DESCRIPTION
             "DNIS Authentication type"
         --CONFIGURABLE
         ::= { usrCipPortParamEntry 34 }
	usrCipPortDNISAuthTime  OBJECT-TYPE
         SYNTAX INTEGER 
                         {
                         before-answer (1),
                         after-answer (2)
                         }
         MAX-ACCESS  read-write
         STATUS  current
         DESCRIPTION
             "DNIS Authentication Time"
         --CONFIGURABLE
         ::= { usrCipPortParamEntry 35 }
	usrCipPortDNISAuthType  OBJECT-TYPE
         SYNTAX INTEGER 
		 {
                 dnis (1),
                 ani (2)
                 }
         MAX-ACCESS  read-write
         STATUS  current
         DESCRIPTION
             "DNIS Authentication type"
         --CONFIGURABLE
         ::= { usrCipPortParamEntry 36 }
     usrCipPortDNISPassword OBJECT-TYPE
          SYNTAX      OCTET STRING (SIZE(0..15))
   	  MAX-ACCESS  read-write
   	  STATUS      current
   	  DESCRIPTION "The DNIS  password."
        --CONFIGURABLE
     ::= { usrCipPortParamEntry 37 }
     usrCipPortDNISTimeout OBJECT-TYPE
          SYNTAX      Integer32
          MAX-ACCESS  read-write
          STATUS      current
          DESCRIPTION "Timeout if no auth within this time"
        --CONFIGURABLE
     ::= {usrCipPortParamEntry 38}
    usrCipPortParity  OBJECT-TYPE
         SYNTAX INTEGER   
         {
             no-parity-eight-bit (1),
             even-seven-bit (2),
             odd-seven-bit (3),
             no-parity-seven-bit (4)
         }
         MAX-ACCESS  read-write      
         STATUS  current     
         DESCRIPTION
             "Port Parity"
         --CONFIGURABLE
         ::= { usrCipPortParamEntry 39 }
    usrCipPromptDelay  OBJECT-TYPE
         SYNTAX Integer32 (0..100)
         MAX-ACCESS  read-write
         STATUS  current
         DESCRIPTION
             "If user does not enter any key after banner mesg, authenticate
              user based on interface user name after this delay"
         --CONFIGURABLE
         ::= { usrCipPortParamEntry 40 }
    usrCipPromptTimeout  OBJECT-TYPE
         SYNTAX Integer32 (5..600)
         MAX-ACCESS  read-write
         STATUS  current
         DESCRIPTION
             " This is the maximum timeout while prompting for 
		username password. If nothing is typed, the session will
		be terminated. Default is 300 secs"
         --CONFIGURABLE
         ::= { usrCipPortParamEntry 41 }
    usrCipSpecialXonXoffFlow  OBJECT-TYPE
         SYNTAX INTEGER   
         {
             disabled (0),
             enabled (1)
         }
         MAX-ACCESS  read-write      
         STATUS  current     
         DESCRIPTION
             "Special Xon Xoff flow control in modem control receive side"
         --CONFIGURABLE
         ::= { usrCipPortParamEntry 42 }
	 usrCipCallingPhoneNumber OBJECT-TYPE
      SYNTAX      OCTET STRING (SIZE(0..64))
   	  MAX-ACCESS  read-only
   	  STATUS      current
   	  DESCRIPTION "Calling phone number"
     ::= { usrCipPortParamEntry 43 }
	 usrCipCalledPhoneNumber OBJECT-TYPE
      SYNTAX      OCTET STRING (SIZE(0..64))
   	  MAX-ACCESS  read-only
   	  STATUS      current
   	  DESCRIPTION "Called phone number"
     ::= { usrCipPortParamEntry 44 }
	usrCipPortGlobalConnId OBJECT-TYPE
      SYNTAX      Integer32
      MAX-ACCESS  read-only
      STATUS      current
      DESCRIPTION "Global Connection Id"
     ::= { usrCipPortParamEntry 45 }
	 usrCipPortUseDnisPool OBJECT-TYPE
         SYNTAX INTEGER 
		 {
             dnis-pool-disabled (1),
             dnis-pool-preferred (2),
             dnis-pool-required (3)
         }
         MAX-ACCESS  read-write
         STATUS  current
         DESCRIPTION
             "User DNIS pool"
         --CONFIGURABLE
     ::= { usrCipPortParamEntry 46 }
     usrCipPortLoginTable OBJECT-TYPE
         SYNTAX OCTET STRING (SIZE(0..32))
         MAX-ACCESS  read-write
         STATUS  current
         DESCRIPTION
             "Login Host Table "
         --CONFIGURABLE 
     ::= { usrCipPortParamEntry 47 }
     usrCipPortMobileType OBJECT-TYPE
          SYNTAX        INTEGER {
                          undefined-conn(0),
                          mobile-ip(1),
                          simple-ip(2)
                           }
          MAX-ACCESS    read-only
          STATUS        current
          DESCRIPTION  "The Mobile Node connected"
     ::= {usrCipPortParamEntry 48}
-- Modem Group Table 
      usrCipModemGroupTable OBJECT-TYPE
         SYNTAX  SEQUENCE OF USRCIPModemGroupEntry 
         MAX-ACCESS  not-accessible
         STATUS  current
         DESCRIPTION
            "This table contains the serial port parameters."
      ::= { usrCip 2 }
     usrCipModemGroupEntry OBJECT-TYPE
        SYNTAX      USRCIPModemGroupEntry
        MAX-ACCESS  not-accessible
        STATUS      current
        DESCRIPTION "Each entry corresponds to a serial interface.
                     All objects required for row creation."
        INDEX   {
                usrCipModemGroupName
               }
     ::= {usrCipModemGroupTable 1}
     USRCIPModemGroupEntry ::= 
          SEQUENCE {
               usrCipModemGroupName
                    DisplayString,
               usrCipModemGroupStatus
                    INTEGER,
               usrCipModemGroupCount
                    Integer32
          }
     usrCipModemGroupName OBJECT-TYPE
          SYNTAX        DisplayString (SIZE (0..32))
          MAX-ACCESS    not-accessible
          STATUS        current
          DESCRIPTION   "The identifier of a modem group."
     ::= { usrCipModemGroupEntry 1 }
     usrCipModemGroupStatus  OBJECT-TYPE
        SYNTAX          INTEGER {
                                add(0),
                                delete(1)
                                }
        MAX-ACCESS     	read-write
        STATUS          current
        DESCRIPTION     "The status could be add or delete the group member
                         specified in the usrCipGroupMembers MIB."
      --CONFIGURABLE
    ::= { usrCipModemGroupEntry 2 }
     usrCipModemGroupCount OBJECT-TYPE
          SYNTAX      Integer32
          MAX-ACCESS  read-only
          STATUS      current
          DESCRIPTION "The number of modem ports in a specific group."
     ::= { usrCipModemGroupEntry 3 }
-- The Global Host Table
      usrCipGlblHostTable OBJECT-TYPE
         SYNTAX  SEQUENCE OF USRCIPGlblHostEntry
         MAX-ACCESS  not-accessible
         STATUS  current
         DESCRIPTION
            "This table contains the global host addresses."
      ::= { usrCip 3 }
     usrCipGlblHostEntry OBJECT-TYPE
        SYNTAX      USRCIPGlblHostEntry
        MAX-ACCESS  not-accessible
        STATUS      current
        DESCRIPTION "Each entry contains a host address with tcp port numbers."
        INDEX   {
                usrCipGlblHostIndex
                }
     ::= {usrCipGlblHostTable 1}
     USRCIPGlblHostEntry ::= 
         SEQUENCE {
               usrCipGlblHostIndex
                    Integer32,
               usrCipGlblHostAddress
                    IpAddress,
               usrCipGlblHostRloginPort
                    Integer32,
               usrCipGlblHostTelnetPort
                    Integer32,
               usrCipGlblHostTcpClearPort
                    Integer32,
               usrCipGlblHostName
                    OCTET STRING,
               usrCipGlblHostState 
                    INTEGER
          }
     usrCipGlblHostIndex OBJECT-TYPE
          SYNTAX      Integer32
          MAX-ACCESS  read-write
          STATUS      current
          DESCRIPTION "The identifier of a default host table."
     ::= { usrCipGlblHostEntry 1 }
     usrCipGlblHostAddress OBJECT-TYPE
        SYNTAX  IpAddress
        MAX-ACCESS  read-write
        STATUS  current
        DESCRIPTION     
                "The global host IP address."
        --CONFIGURABLE                
     ::= { usrCipGlblHostEntry 2 }
     usrCipGlblHostRloginPort   OBJECT-TYPE
        SYNTAX  Integer32
        MAX-ACCESS  read-write
        STATUS  current
        DESCRIPTION
                "The host rlogin tcp port number."
        --CONFIGURABLE        
     ::= { usrCipGlblHostEntry 3 }        
     usrCipGlblHostTelnetPort   OBJECT-TYPE
        SYNTAX  Integer32
        MAX-ACCESS  read-write
        STATUS  current
        DESCRIPTION
                "The host telnet port number."
        --CONFIGURABLE
     ::= { usrCipGlblHostEntry 4 }
     usrCipGlblHostTcpClearPort OBJECT-TYPE
        SYNTAX  Integer32
        MAX-ACCESS  read-write
        STATUS  current
        DESCRIPTION     
                "The host tcp clear port number."
        --CONFIGURABLE
     ::= { usrCipGlblHostEntry 5 }
     usrCipGlblHostName OBJECT-TYPE
        SYNTAX  OCTET STRING (SIZE(0..32))
        MAX-ACCESS  read-write
        STATUS  current
        DESCRIPTION
                "The global host name."
        --CONFIGURABLE
     ::= { usrCipGlblHostEntry 6 }
     usrCipGlblHostState OBJECT-TYPE
        SYNTAX  INTEGER {
                        host-undefined (0),
                        host-valid (1),
                        host-invalid (2),
                        host-pending (3)
                        }
        MAX-ACCESS  read-write
        STATUS  current
        DESCRIPTION     
                "The state of a default host entry."
     ::= { usrCipGlblHostEntry 7 }
-- The Global Parameters
     usrCipGlblHostSelectionMethod      OBJECT-TYPE
        SYNTAX  INTEGER {
                        round-robin(0),
                        random(1)
                        }
        MAX-ACCESS  read-write
        STATUS  current
        DESCRIPTION
                "The method that will be used to select the 
                 default host."
        --CONFIGURABLE
        ::= {usrCip 4}	     
     usrCipGlblHostType OBJECT-TYPE
        SYNTAX  INTEGER {
                        undefined-host(0),
                        default-host(1),
                        prompt(2)
                        }
        MAX-ACCESS  read-write
        STATUS  current
        DESCRIPTION
            "The default host type."
        --CONFIGURABLE
        ::= { usrCip 5 }
     usrCipGlblLoginMsg OBJECT-TYPE
        SYNTAX  OCTET STRING (SIZE(0..255))
        MAX-ACCESS  read-write
        STATUS  current
        DESCRIPTION
                "The user login message"
        --CONFIGURABLE
        ::= { usrCip 6 }
     usrCipGlblUsrCommandPrompt OBJECT-TYPE
        SYNTAX  OCTET STRING (SIZE(0..64))
        MAX-ACCESS  read-write
        STATUS  current
        DESCRIPTION
                "The user command prompt."
        --CONFIGURABLE
        ::= { usrCip 7 }
      usrCipGlblLogNetUserPrompt OBJECT-TYPE
        SYNTAX  OCTET STRING (SIZE(0..64))
        MAX-ACCESS  read-write
        STATUS  current
        DESCRIPTION
                "The login/network command prompt."
        --CONFIGURABLE
        ::= { usrCip 8 }
     usrCipGlblMgPrompt OBJECT-TYPE
        SYNTAX  OCTET STRING (SIZE(0..64))
        MAX-ACCESS  read-write
        STATUS  current
        DESCRIPTION
                "The manage prompt."
        --CONFIGURABLE
        ::= { usrCip 9 }
     usrCipGlblUserName OBJECT-TYPE
        SYNTAX  OCTET STRING (SIZE(0..32))
        MAX-ACCESS  read-write
        STATUS  current
        DESCRIPTION
                "The default user name used in case the dial-in users don't
                 get prompted for the user name and no user name is configured
                 for the i/f."
        --CONFIGURABLE
        ::= { usrCip 10 }
     usrCipGlblNumCalls OBJECT-TYPE
        SYNTAX  Counter32
        MAX-ACCESS  read-only
        STATUS  current
        DESCRIPTION
                "The total number of calls received since the boot up time."
        ::= { usrCip 11 }
     usrCipAllowManageOnDialups OBJECT-TYPE
        SYNTAX  INTEGER {
                        manage-off(0),
                        manage-on (1)
                        }
        MAX-ACCESS  read-write
        STATUS  current
        DESCRIPTION
                "This variable turns on/off the ability to manage the system
                 through the dialup ports."
        --CONFIGURABLE
        ::= { usrCip 12 }
     usrCipHangUp OBJECT-TYPE
        SYNTAX  Integer32
        MAX-ACCESS  read-write
        STATUS  current
        DESCRIPTION
                "This variable is set only if a hangup message is sent out.
                 The value of this variable is the interface index."
        ::= {usrCip 13 }
     usrCipDialOut OBJECT-TYPE
        SYNTAX  OCTET STRING (SIZE(0..32))
        MAX-ACCESS  read-write
        STATUS  current
        DESCRIPTION
                "This variable is set through the CLI when the user
                 manually issues a dial-out."
        ::= { usrCip 14 }
     usrCipBusyOut   OBJECT-TYPE
        SYNTAX  Integer32
        MAX-ACCESS  read-write
        STATUS  current
        DESCRIPTION     
                "This variable is set only in case the user wants to 
                take the phone off hook."
        ::= {usrCip 15}
     usrInitScriptTable OBJECT-TYPE
         SYNTAX  SEQUENCE OF USRInitScriptEntry
         MAX-ACCESS  not-accessible
         STATUS  current
         DESCRIPTION
            "This table contains the global host addresses."
      ::= { usrCip 16}
     usrInitScriptEntry OBJECT-TYPE
        SYNTAX      USRInitScriptEntry
        MAX-ACCESS  not-accessible
        STATUS      current
        DESCRIPTION "Each entry contains a host address with tcp port numbers."
        INDEX   {
                usrInitScriptName
                }
     ::= {usrInitScriptTable 1}
     USRInitScriptEntry ::= 
         SEQUENCE {
               usrInitScriptName
                    DisplayString,
               usrInitScriptCommands
                    DisplayString,
	       usrInitScriptStatus
		    INTEGER
                }
     usrInitScriptName OBJECT-TYPE
          SYNTAX      DisplayString  (SIZE(0..7))
          MAX-ACCESS  not-accessible
          STATUS      current
          DESCRIPTION "The name of the script"
     ::= { usrInitScriptEntry 1 }
     usrInitScriptCommands OBJECT-TYPE
          SYNTAX        DisplayString (SIZE(0..56))
          MAX-ACCESS    read-write
          STATUS        current
          DESCRIPTION   "The AT commands that will be sent to the serial line
                         driver every time a connection goes away."
        --CONFIGURABLE
     ::= { usrInitScriptEntry 2 }
     usrInitScriptStatus  OBJECT-TYPE
        SYNTAX          INTEGER {
                                normal-status(0),
                                delete-script(1)
                                }
        MAX-ACCESS     	read-write
        STATUS          current
        DESCRIPTION     "This variable is used to delete a script from the init
                         script list."
    ::= { usrInitScriptEntry 3 }
-- MIB Variables defined for CFM purposes
     usrCipCfmPortIndexTable OBJECT-TYPE
         SYNTAX  SEQUENCE OF USRCIPCfmPortIndexEntry
         MAX-ACCESS  not-accessible
         STATUS  current
         DESCRIPTION
            "This table contains CIP port indices. It is defined 
             so that CFM process would be able to save a specific
             row of portal table."
	::= { usrCip 17 }
     usrCipCfmPortIndexEntry OBJECT-TYPE
        SYNTAX      USRCIPCfmPortIndexEntry
        MAX-ACCESS  not-accessible
        STATUS      current
        DESCRIPTION "Each entry corresponds to a serial interface."
        INDEX   {
                usrCipCfmPortIndex
               }
     ::= {usrCipCfmPortIndexTable 1}
     USRCIPCfmPortIndexEntry ::= 
          SEQUENCE {
               usrCipCfmPortIndex
                    Integer32,
               usrCipCfmPortFlag
                    Integer32
                }
     usrCipCfmPortIndex OBJECT-TYPE
          SYNTAX      Integer32
          MAX-ACCESS  read-only
          STATUS      current
          DESCRIPTION "The identifier of the physical interface."
     ::= {usrCipCfmPortIndexEntry 1}
     usrCipCfmPortFlag OBJECT-TYPE
          SYNTAX       Integer32
          MAX-ACCESS   read-write
          STATUS       current
          DESCRIPTION   "The flag that triggers a cfm operation on each
                         interface."
     ::= {usrCipCfmPortIndexEntry 2 }
-- Scalar Flags
    usrCipCfmAllPortsFlag  OBJECT-TYPE
         SYNTAX         Integer32
         MAX-ACCESS     read-write
         STATUS         current
         DESCRIPTION    "This flag triggers a CFM action."
    ::= { usrCip 18 }
    usrCipCfmModemGroupFlag OBJECT-TYPE
        SYNTAX          Integer32
        MAX-ACCESS      read-write
        STATUS          current
        DESCRIPTION     "This flag triggers a save of modem group table."
    ::= { usrCip 19 }
    usrCipCfmGlblHostTableFlag OBJECT-TYPE
        SYNTAX          Integer32
        MAX-ACCESS      read-write
        STATUS          current
        DESCRIPTION     "This flag triggers a save of global host table."
    ::= { usrCip 20 }        
    usrCipCfmInitScriptFlag OBJECT-TYPE
        SYNTAX          Integer32
        MAX-ACCESS      read-write
        STATUS          current
        DESCRIPTION     "This flag triggers a save of init script table."
    ::= { usrCip 21 }
    usrCipCfmGlblVarFlag OBJECT-TYPE
        SYNTAX          Integer32
        MAX-ACCESS      read-write
        STATUS          current
        DESCRIPTION     "This flag triggers a save of global variables."
    ::= { usrCip 22 }
   usrCipCfmSaveAllFlag OBJECT-TYPE
        SYNTAX          Integer32
        MAX-ACCESS      read-write
        STATUS          current
        DESCRIPTION     "This flag triggers a save for all of CIP tables."
    ::= { usrCip 23 }
-- Port Parameters Grouped in a Modem Group 
    usrCipModemPortParamTable OBJECT-TYPE
         SYNTAX  SEQUENCE OF USRCIPModemPortParamEntry
         MAX-ACCESS  not-accessible
         STATUS  current
         DESCRIPTION
            "This table contains the serial port parameters."
	::= { usrCip 24 }
    usrCipModemPortParamEntry OBJECT-TYPE
        SYNTAX      USRCIPModemPortParamEntry
        MAX-ACCESS  not-accessible
        STATUS      current
        DESCRIPTION "Each entry corresponds to a serial interface."
        INDEX   {
                usrCipModemPortName
               }
     ::= {usrCipModemPortParamTable 1}
     USRCIPModemPortParamEntry ::= 
          SEQUENCE {
               usrCipModemPortName
                    OCTET STRING,
               usrCipModemPortType
                    INTEGER,
               usrCipModemPortAccess
                    INTEGER,
               usrCipModemPortHostType
                    INTEGER,
               usrCipModemPortLoginService
                    INTEGER,
               usrCipModemPortTcpPortNumber
                    Integer32,
               usrCipModemPortLoginMsg
                    OCTET STRING,
               usrCipModemPortLoginPrompt
                    OCTET STRING,
               usrCipModemPortIpAddress
                    IpAddress,
               usrCipModemPortHostIpAddress
                    IpAddress,
               usrCipModemPortNetMask
                    Integer32,
               usrCipModemPortProtocol
                    INTEGER,
               usrCipModemPortMtu
                    Integer32,
               usrCipModemPortIdleTimeOut
                    Integer32,
               usrCipModemInitScriptName
                    DisplayString,
               usrCipModemIfConnType
                    INTEGER,
               usrCipModemPromptUserName
                    OCTET STRING,
               usrCipModemUserPasswd
                    OCTET STRING,
               usrCipModemDialPrefix
                    OCTET STRING,
               usrCipModemPortPromptingStyle
                    INTEGER,
               usrCipModemPortLoginProcessing
                    INTEGER,
               usrCipModemPortDNISAuthentication
                   INTEGER,
               usrCipModemPortDNISAuthTime
                   INTEGER,
               usrCipModemPortDNISAuthType 
                   INTEGER,
               usrCipModemPortDNISPassword
                   OCTET STRING,
               usrCipModemPortDNISTimeout
                   Integer32,
              usrCipModemPortParity
                    INTEGER,
              usrCipModemPromptDelay
                   Integer32,
	      usrCipModemPromptTimeout
		   Integer32,
  	      usrCipModemSpecialXonXoffFlow 
		   INTEGER,
  	      usrCipModemUseDnisPool 
		   INTEGER,
	      usrCipModemLoginTable
		   OCTET STRING
               }
     usrCipModemPortName OBJECT-TYPE
          SYNTAX        OCTET STRING (SIZE (0..32))
          MAX-ACCESS    not-accessible
          STATUS        current
          DESCRIPTION   "The identifier of a modem group."
     ::= {usrCipModemPortParamEntry 1}
     usrCipModemPortType OBJECT-TYPE
          SYNTAX      INTEGER {
                         login (1),
                         network (2),
                         login-network (3)
                         }
          MAX-ACCESS  read-write
          STATUS      current
          DESCRIPTION "The type of the physical port."
     ::= {usrCipModemPortParamEntry 2}
     usrCipModemPortAccess OBJECT-TYPE
          SYNTAX      INTEGER {
                         dial-in(1),
                         dial-out(2),
                         two-way(3)
                       }
          MAX-ACCESS  read-write
          STATUS      current
          DESCRIPTION "This field specifies the direction of the calls
                         that could be made on a specific interface. 
                         Ports could be configured to be dial-in, dial-out
                         or two-way ports."
     ::= {usrCipModemPortParamEntry 3}
     usrCipModemPortHostType OBJECT-TYPE
          SYNTAX      INTEGER {
                         default (1),
                         prompt (2),
                         specified (3)
                         }
          MAX-ACCESS  read-write
          STATUS      current
          DESCRIPTION "The host type that the dial-in user 
                       will be connected to."
     ::= {usrCipModemPortParamEntry 4}
     usrCipModemPortLoginService OBJECT-TYPE
          SYNTAX      INTEGER {
                         telnet (1),
                         rlogin (2),
                         netdata (3)
                         }
          MAX-ACCESS  read-write
          STATUS      current
          DESCRIPTION "The Service type that the dial-in user will 
                       be connected to."
     ::= {usrCipModemPortParamEntry 5}
     usrCipModemPortTcpPortNumber OBJECT-TYPE
          SYNTAX      Integer32
          MAX-ACCESS  read-write
          STATUS      current
          DESCRIPTION "The tcp port number associated with the service type."
     ::= {usrCipModemPortParamEntry 6}
     usrCipModemPortLoginMsg OBJECT-TYPE
          SYNTAX      OCTET STRING (SIZE(0..255))
          MAX-ACCESS  read-write
          STATUS      current
          DESCRIPTION "The salutation message associated with a specific port."
     ::= {usrCipModemPortParamEntry 7}
     usrCipModemPortLoginPrompt OBJECT-TYPE
   	  SYNTAX      OCTET STRING (SIZE(0..64))
   	  MAX-ACCESS  read-write
   	  STATUS      current
   	  DESCRIPTION "The login prompt associated with a specific port."
     ::= {usrCipModemPortParamEntry 8}
     usrCipModemPortIpAddress OBJECT-TYPE
   	  SYNTAX      IpAddress
   	  MAX-ACCESS  read-write
   	  STATUS      current
	  DESCRIPTION "The IP address for a specific serial port."
      ::= {usrCipModemPortParamEntry 9}
     usrCipModemPortHostIpAddress OBJECT-TYPE
   	  SYNTAX      IpAddress
   	  MAX-ACCESS  read-write
   	  STATUS      current
	  DESCRIPTION "A host IP address specified for this interface."
   	::= {usrCipModemPortParamEntry 10}
     usrCipModemPortNetMask OBJECT-TYPE
   	  SYNTAX      Integer32
   	  MAX-ACCESS  read-write
   	  STATUS      current
   	  DESCRIPTION "The netmask associated with a specific 
                       serial interface."
     ::= {usrCipModemPortParamEntry 11}
     usrCipModemPortProtocol OBJECT-TYPE
   	  SYNTAX      INTEGER {
                         ppp (1),
                         slip (2),
                         arap (3)
                    	   }
   	  MAX-ACCESS  read-write
   	  STATUS      current
   	  DESCRIPTION "The protocol type configured for a specific interface."
     ::= {usrCipModemPortParamEntry 12}
     usrCipModemPortMtu OBJECT-TYPE
   	  SYNTAX      Integer32
   	  MAX-ACCESS  read-write
   	  STATUS      current
   	  DESCRIPTION "The mtu value associated with a specific interface."
     ::= {usrCipModemPortParamEntry 13}
     usrCipModemPortIdleTimeOut OBJECT-TYPE
   	  SYNTAX      Integer32
   	  MAX-ACCESS  read-write
   	  STATUS      current
   	  DESCRIPTION "The maximum idle time specified for an interface."
     ::= {usrCipModemPortParamEntry 14}
     usrCipModemInitScriptName OBJECT-TYPE
          SYNTAX      DisplayString  (SIZE(0..7))
          MAX-ACCESS  read-write
          STATUS      current
          DESCRIPTION "The name of the script"
     ::= { usrCipModemPortParamEntry 15 }
     usrCipModemIfConnType OBJECT-TYPE
          SYNTAX      INTEGER {
                        if-direct-conn (1),
                        if-direct-network-conn (2),
                        if-normal-conn (3),
                        if-prompt-passwd (4),
                        if-prompt-none (5),
						if-ppp-only(6)
                        }
          MAX-ACCESS  read-write
          STATUS      current
          DESCRIPTION "The type of the connection that i/f is configured for."
     ::= { usrCipModemPortParamEntry 16 }
     usrCipModemPromptUserName OBJECT-TYPE
          SYNTAX        OCTET STRING (SIZE(0..32))
          MAX-ACCESS    read-write
          STATUS        current
          DESCRIPTION   "This could only be set if the port is
                        configured not to prompt for username."
     ::= { usrCipModemPortParamEntry 17 }
     usrCipModemUserPasswd OBJECT-TYPE
          SYNTAX      OCTET STRING (SIZE(0..15))
   	  MAX-ACCESS  read-write
   	  STATUS      current
   	  DESCRIPTION "This could only be set if the port is 
                       configured to not prompt for password."
     ::= { usrCipModemPortParamEntry 18 }
     usrCipModemDialPrefix OBJECT-TYPE
         SYNTAX         OCTET STRING (SIZE(0..64))
         MAX-ACCESS     read-write
         STATUS         current
         DESCRIPTION    "This string defines the prefix to the phone number."
    ::= { usrCipModemPortParamEntry 19 }
    usrCipModemPortPromptingStyle OBJECT-TYPE
         SYNTAX        INTEGER {
                           local-prompting(1),
                           remote-prompting(2)
                       }
         MAX-ACCESS    read-write
         STATUS        current
         DESCRIPTION   "This value specifies whether the NAS will provide
                       username and password prompting locally or if the
                       prompting will be handled by a remote security server."
       --CONFIGURABLE
    ::= { usrCipModemPortParamEntry 20 }
    usrCipModemPortLoginProcessing OBJECT-TYPE
        SYNTAX INTEGER {
                       enable (1),
                       disable (2)
                       }
        MAX-ACCESS read-write
        STATUS current
        DESCRIPTION
            "This variable controls login processing.  Setting the value to disable
             will cause the box to not prompt a user for login name or password.  Enabling
             this value will cause the box to perform normal login name and password prompting."
        --CONFIGURABLE
        ::= {usrCipModemPortParamEntry 21}
    usrCipModemPortDNISAuthentication  OBJECT-TYPE
         SYNTAX INTEGER    
         {     
             dnis-auth-disabled (1),
             dnis-auth-preferred (2), 
             dnis-auth-required (3)
         }      
         MAX-ACCESS  read-write
         STATUS  current       
         DESCRIPTION  
             "DNIS Authentication type"
         --CONFIGURABLE
         ::= { usrCipModemPortParamEntry 22 }
    usrCipModemPortDNISAuthTime  OBJECT-TYPE
         SYNTAX INTEGER
         {
             before-answer (1),
             after-answer (2)
         }
         MAX-ACCESS read-write
         STATUS  current
         DESCRIPTION
             "DNIS Authentication Time"
         --CONFIGURABLE
         ::= { usrCipModemPortParamEntry 23 }
    usrCipModemPortDNISAuthType  OBJECT-TYPE
         SYNTAX INTEGER
         {
             dnis (1),
             ani (2)
         }
         MAX-ACCESS read-write
         STATUS  current
         DESCRIPTION
             "DNIS Authentication type"
         --CONFIGURABLE
         ::= { usrCipModemPortParamEntry 24 }
     usrCipModemPortDNISPassword OBJECT-TYPE
          SYNTAX      OCTET STRING (SIZE(0..15))
  	  MAX-ACCESS  read-write
   	  STATUS      current
   	  DESCRIPTION "The DNIS  password."
        --CONFIGURABLE
         ::= { usrCipModemPortParamEntry 25 }
     usrCipModemPortDNISTimeout OBJECT-TYPE
          SYNTAX      Integer32
          MAX-ACCESS  read-write
          STATUS      current
          DESCRIPTION "Timeout if no auth within this time"
        --CONFIGURABLE
     ::= {usrCipModemPortParamEntry 26}
    usrCipModemPortParity  OBJECT-TYPE
         SYNTAX INTEGER       
         {      
			no-parity-eight-bit (1),
			even-seven-bit (2),  
			odd-seven-bit (3),  
			no-parity-seven-bit (4)
         }
         MAX-ACCESS  read-write
         STATUS  current
         DESCRIPTION
             "Port Parity"
         --CONFIGURABLE
         ::= { usrCipModemPortParamEntry 27 }
    usrCipModemPromptDelay  OBJECT-TYPE
         SYNTAX Integer32 (0..100)
         MAX-ACCESS   read-write
         STATUS  current
         DESCRIPTION
             "If user does not enter any key after banner mesg, authenticate
              user based on interface user name after this delay"
         --CONFIGURABLE 
         ::= { usrCipModemPortParamEntry 28 }
    usrCipModemPromptTimeout  OBJECT-TYPE
         SYNTAX Integer32 (5..600)
         MAX-ACCESS read-write
         STATUS  current
         DESCRIPTION
             " This is the maximum timeout while prompting for 
		username password. If nothing is typed, the session will
		be terminated. Default is 300 secs"
         --CONFIGURABLE
         ::= { usrCipModemPortParamEntry 29 }
      usrCipModemSpecialXonXoffFlow  OBJECT-TYPE
         SYNTAX INTEGER       
         {      
             disbaled (0),
             enabled (1)
         }
         MAX-ACCESS read-write
         STATUS  current
         DESCRIPTION
             "Special Xon Xoff flow control in modem control receive side"
         --CONFIGURABLE
         ::= { usrCipModemPortParamEntry 30 }
	 usrCipModemUseDnisPool OBJECT-TYPE
         SYNTAX INTEGER 
		 {
             dnis-pool-disabled (1),
             dnis-pool-preferred (2),
             dnis-pool-required (3)
         }
         MAX-ACCESS read-write
         STATUS  current
         DESCRIPTION
             "User DNIS pool"
         --CONFIGURABLE
     ::= { usrCipModemPortParamEntry 31 }
	 usrCipModemLoginTable OBJECT-TYPE
         SYNTAX OCTET STRING (SIZE(0..32))
         MAX-ACCESS  read-write
         STATUS  current
         DESCRIPTION
             "Login Host Table "
         --CONFIGURABLE
     ::= { usrCipModemPortParamEntry 32 }
     usrCipConfigFileName OBJECT-TYPE
         SYNTAX OCTET STRING (SIZE(0..64))
         MAX-ACCESS read-only
         STATUS current
         DESCRIPTION
           "The name of a ConfigFile to read/write permanent database
            records. If the value of this object is an empty string,
            then the default name `@file://CallInitProcess.cfg' is
            used."
     ::= { usrCip 25 }
-- Modem Group Interface Table
      usrCipModemGroupInterfaceTable OBJECT-TYPE
         SYNTAX  SEQUENCE OF USRCIPModemGroupInterfaceEntry 
         MAX-ACCESS  not-accessible
         STATUS  current
         DESCRIPTION
            "This table contains the list of interfaces that belong to 
             a particular modem group."
      ::= { usrCip 26 }
     usrCipModemGroupInterfaceEntry OBJECT-TYPE
        SYNTAX      USRCIPModemGroupInterfaceEntry
        MAX-ACCESS  not-accessible
        STATUS      current
        DESCRIPTION "Each entry corresponds to a serial interface."
        INDEX   {
                usrCipModemGroupInterfaceGroupName,
                usrCipModemGroupInterfaceName
               }
     ::= {usrCipModemGroupInterfaceTable 1}
     USRCIPModemGroupInterfaceEntry ::= 
          SEQUENCE {
               usrCipModemGroupInterfaceName
                    DisplayString,
               usrCipModemGroupInterfaceStatus
                    INTEGER,
               usrCipModemGroupInterfaceGroupName
                    DisplayString
          }
     usrCipModemGroupInterfaceGroupName OBJECT-TYPE
          SYNTAX        DisplayString
          MAX-ACCESS    not-accessible
          STATUS        current
          DESCRIPTION   "Group name that this interface belongs to."
     ::= { usrCipModemGroupInterfaceEntry 1 }
     usrCipModemGroupInterfaceName OBJECT-TYPE
          SYNTAX        DisplayString 
          MAX-ACCESS    not-accessible
          STATUS        current
          DESCRIPTION   "The identifier of a modem group."
     --CONFIGURABLE
     ::= { usrCipModemGroupInterfaceEntry 2 }
     usrCipModemGroupInterfaceStatus  OBJECT-TYPE
        SYNTAX          INTEGER {
                                add(0),
                                delete(1),
                                active(2),
                                inactive(3)
                                }
        MAX-ACCESS     	read-write
        STATUS          current
        DESCRIPTION     "The status could be add or delete the group member
                         specified in the usrCipGroupMembers MIB."
      --CONFIGURABLE
     ::= { usrCipModemGroupInterfaceEntry 3 }
     usrCipGlobalCallType  OBJECT-TYPE
           SYNTAX          INTEGER { pptp(1),l2tp(3),none(2) }
           MAX-ACCESS      read-write
           STATUS          current
           DESCRIPTION
              " Global Call Type determiner . "
           --CONFIGURABLE
           ::= { usrCip 27 }
     usrCipSingleLevelPrompting OBJECT-TYPE
        SYNTAX  INTEGER {
            disabled(0),
            enabled(1)
        }
        MAX-ACCESS  read-write
        STATUS current
        DESCRIPTION
           "If enabled, Login/Network users are presented with the HiPer
           prompt, by-passing the initial Login/Network prompt (def: disabled)."
        --CONFIGURABLE
     ::= { usrCip 28 }
   usrCipCfmChatScriptFlag OBJECT-TYPE
        SYNTAX          Integer32
        MAX-ACCESS      read-write
        STATUS          current
        DESCRIPTION     "This flag triggers a save of chat script table."
    ::= { usrCip 29 }
    usrCipChatScriptTable OBJECT-TYPE
         SYNTAX  SEQUENCE OF USRCIPChatScriptEntry
         MAX-ACCESS  not-accessible
         STATUS  current
         DESCRIPTION
            "This table contains the chatscript names."
    ::= { usrCip 30 }
    usrCIPChatScriptEntry OBJECT-TYPE
        SYNTAX      USRCIPChatScriptEntry
        MAX-ACCESS  not-accessible
        STATUS      current
        DESCRIPTION "Each entry corresponds to a chat script."
        INDEX   { usrCipChatScriptName }
     ::= {usrCipChatScriptTable 1}
    USRCIPChatScriptEntry ::=
          SEQUENCE {
               usrCipChatScriptName
                    OCTET STRING,
               usrCipChatScriptStatus
                    INTEGER,
               usrCipChatScriptString
                    OCTET STRING
    }
   usrCipChatScriptName OBJECT-TYPE
         SYNTAX  OCTET STRING (SIZE(0..64))
         MAX-ACCESS  not-accessible
         STATUS  current
         DESCRIPTION
            "The character name for this chatscript."
    ::= { usrCIPChatScriptEntry 1 }
    usrCipChatScriptStatus OBJECT-TYPE
         SYNTAX  INTEGER {
                         add(1),
                         delete(2),
                         verify(3),
                         normal(4),       -- Chat Script reading in progress
                         reading(5),     -- Chat Script reading in progress
                         verifyFailed(6),  -- Chat Script verification failed
                         starting(7),       -- Chat Script operation starting
                         verifying(8)       -- Chat script verification in progress
                         }
         MAX-ACCESS  read-write
         STATUS  current
         DESCRIPTION
            "The status of this chatscript entry. Valid row entries in this
             table have the status field set to normal. The settable values
             are normal and delete. If the instance is in the table and the
             status is starting/reading, this will be an add operation."
         --CONFIGURABLE
     ::= { usrCIPChatScriptEntry 2 }
    usrCipChatScriptString OBJECT-TYPE
         SYNTAX  OCTET STRING
         MAX-ACCESS  read-only
         STATUS  current
         DESCRIPTION
            "Chat script buffer"
    ::= { usrCIPChatScriptEntry 3 }
    usrCipDNISAuthFlag  OBJECT-TYPE
         SYNTAX  INTEGER {
                 disabled(0),
                 enabled(1)
             }
         MAX-ACCESS  read-write
         STATUS  current
         DESCRIPTION
             "This is the switch to enable/disable DNIS based
              call-authorization"
         --CONFIGURABLE
         ::= { usrCip 31 }
    usrCipDNISAuthPassword  OBJECT-TYPE
         SYNTAX  OCTET STRING (SIZE(0..127))
         MAX-ACCESS  read-write
         STATUS  current
         DESCRIPTION
             "This is the Password for the DNIS authorization request being sent out"
         --CONFIGURABLE
         ::= { usrCip 32 }
    usrCipBannerFileName  OBJECT-TYPE
         SYNTAX  OCTET STRING (SIZE(0..64))
         MAX-ACCESS  read-write
         STATUS  current
         DESCRIPTION
             "This is file name for port banner file, value zero if none."
         --CONFIGURABLE
         ::= { usrCip 33 }
    usrCipAutoAnswerFlag  OBJECT-TYPE
         SYNTAX  INTEGER {
                 disabled(0),
                 enabled(1)
             }
         MAX-ACCESS  read-write
         STATUS  current
         DESCRIPTION
             "This is the switch to enable/disable the Auto Answering of
              Modem-Sharing-Dialout Calls"
         --CONFIGURABLE
         ::= { usrCip 34 }
    usrSlotUtilizationTable OBJECT-TYPE
         SYNTAX  SEQUENCE OF USRSlotUtilizationEntry
         MAX-ACCESS  not-accessible
         STATUS  current
         DESCRIPTION
            "This table contains the chatscript names."
    ::= { usrCip 35 }
    usrSlotUtilizationEntry OBJECT-TYPE
        SYNTAX      USRSlotUtilizationEntry
        MAX-ACCESS  not-accessible
        STATUS      current
        DESCRIPTION "Each entry corresponds to a chat script."
        INDEX   { usrSlotIndex }
     ::= {usrSlotUtilizationTable 1}
    USRSlotUtilizationEntry ::=
          SEQUENCE {
               usrSlotIndex
                    Integer32,
               usrSlotId
                    Integer32,
               usrSlotActiveCalls
                    Integer32,
               usrSlotNumberOfPorts
                    Integer32,
               usrSlotUtilization
                    Integer32
    }
   usrSlotIndex OBJECT-TYPE
         SYNTAX  Integer32
         MAX-ACCESS  not-accessible
         STATUS  current
         DESCRIPTION
            "The slot index."
    ::= { usrSlotUtilizationEntry 1 }
   usrSlotId OBJECT-TYPE
         SYNTAX  Integer32
         MAX-ACCESS  read-only
         STATUS  current
         DESCRIPTION
            "The slot number in human readable format where proper offset is computed." 
    ::= { usrSlotUtilizationEntry 2 }
   usrSlotActiveCalls OBJECT-TYPE
         SYNTAX  Integer32
         MAX-ACCESS  read-only
         STATUS  current
         DESCRIPTION
            "The number of active calls on that slot at that instant." 
    ::= { usrSlotUtilizationEntry 3 }
   usrSlotNumberOfPorts OBJECT-TYPE
         SYNTAX  Integer32
         MAX-ACCESS  read-only
         STATUS  current
         DESCRIPTION
            "The number of ports on that slot."
    ::= { usrSlotUtilizationEntry 4 }
   usrSlotUtilization OBJECT-TYPE
         SYNTAX  Integer32
         MAX-ACCESS  read-only
         STATUS  current
         DESCRIPTION
            "The percent utilization of that slot. This is computed as number of active calls on that slot divided by the number of ports on that slot."
    ::= { usrSlotUtilizationEntry 5 }
    usrCipTotalCalls  OBJECT-TYPE
         SYNTAX  Integer32 
         MAX-ACCESS  read-only
         STATUS  current
         DESCRIPTION
             "Total number of calls on the chassis."
         ::= { usrCip 36 }
    usrCipTotalAvailablePorts  OBJECT-TYPE
         SYNTAX  Integer32 
         MAX-ACCESS  read-only
         STATUS  current
         DESCRIPTION
             "Total number of ports on the chassis."
         ::= { usrCip 37 }
    usrCipTotalChassisUtilization  OBJECT-TYPE
         SYNTAX  Integer32 
         MAX-ACCESS  read-only
         STATUS  current
         DESCRIPTION
             "Percent utilization of all ports on the chassis."
         ::= { usrCip 38 }
    usrCipCallsInLast24Hours  OBJECT-TYPE
         SYNTAX  Integer32 
         MAX-ACCESS  read-only
         STATUS  current
         DESCRIPTION
             "The number of calls in last 24 hours."
         ::= { usrCip 39 }
    usrCipDialinAccessManageUser  OBJECT-TYPE
         SYNTAX  INTEGER {
            disabled(2),
            enabled(1)
         }
         MAX-ACCESS  read-write
         STATUS  current
         DESCRIPTION
             "No Manage user dialin access"
		--CONFIGURABLE
         ::= { usrCip 40 }
-- CIP login table definition. An interface pointing to this table
-- use the login host ip address and login port from the table.
   usrCipCfmLoginTableFlag OBJECT-TYPE
        SYNTAX          Integer32
        MAX-ACCESS      read-write
        STATUS          current
        DESCRIPTION     "This flag triggers a save of cip login table."  
    ::= { usrCip 69 }
    usrCipLoginTable OBJECT-TYPE
    SYNTAX SEQUENCE OF UsrCipLoginEntry
    MAX-ACCESS  not-accessible
    STATUS  current
    DESCRIPTION
        ""
    ::= { usrCip 70 }
    usrCipLoginEntry    OBJECT-TYPE
    SYNTAX  UsrCipLoginEntry
    MAX-ACCESS  not-accessible
    STATUS  current
    DESCRIPTION
        ""
   INDEX  { usrCipLoginListName, usrCipLoginPref }
	   ::= { usrCipLoginTable 1 }
    UsrCipLoginEntry ::=
	SEQUENCE {
		usrCipLoginListName     OCTET STRING,
		usrCipLoginPref		Integer32,
		usrCipLoginIpAddress	IpAddress,
		usrCipLoginPort		Integer32,
		usrCipLoginListNameForPrint
                        		OCTET STRING,
		usrCipLoginEntryDelete  Integer32
	} 
    usrCipLoginListName  OBJECT-TYPE
         SYNTAX  OCTET STRING (SIZE(0..9))
         MAX-ACCESS  not-accessible
         STATUS  current
         DESCRIPTION
             "This is the cip login list name"
    ::= { usrCipLoginEntry 1 }
    usrCipLoginPref  OBJECT-TYPE
        SYNTAX  Integer32
        MAX-ACCESS  not-accessible 
        STATUS  current
        DESCRIPTION
            "login preference index"
    ::= { usrCipLoginEntry 2 }
    usrCipLoginIpAddress  OBJECT-TYPE
         SYNTAX  IpAddress
         MAX-ACCESS  read-write
         STATUS  current
         DESCRIPTION
             "This is the cip login host ip address"
     --CONFIGURABLE
     ::= { usrCipLoginEntry 3 }
    usrCipLoginPort  OBJECT-TYPE
         SYNTAX  Integer32
         MAX-ACCESS  read-write
         STATUS  current
         DESCRIPTION
             "This is the cip login host port"
     --CONFIGURABLE
     ::= { usrCipLoginEntry 4 }
    usrCipLoginListNameForPrint  OBJECT-TYPE
         SYNTAX  OCTET STRING (SIZE(0..9))
         MAX-ACCESS  read-write
         STATUS  current
         DESCRIPTION
             "This is the cip login list name. Added the second mib to print
	      the login table name. The first mib is an index to table"
     --CONFIGURABLE
     ::= { usrCipLoginEntry 5 }
    usrCipLoginEntryDelete  OBJECT-TYPE
         SYNTAX  Integer32
         MAX-ACCESS  read-write
         STATUS  current
         DESCRIPTION
             "Setting this entry will delete the particular table"
     ::= { usrCipLoginEntry 6 }
    usrCipModemUtilizationStatisticsTable OBJECT-TYPE  
           SYNTAX     SEQUENCE OF USRCIPModemUtilizationStatisticsEntry
           MAX-ACCESS not-accessible
           STATUS     current
           DESCRIPTION
             "The active calls during every hour gives 24 samples."
    ::= { usrCip 41 }
    usrCipModemUtilizationStatisticsEntry OBJECT-TYPE  
           SYNTAX     USRCIPModemUtilizationStatisticsEntry
           MAX-ACCESS not-accessible
           STATUS     current
           DESCRIPTION
                "CIP PPP Modem Utilizationstatistics"
           INDEX      { usrCipModemUtilizationStatisticsIndex }
    ::= { usrCipModemUtilizationStatisticsTable 1 }
    USRCIPModemUtilizationStatisticsEntry ::= SEQUENCE {
           usrCipModemUtilizationStatisticsIndex
                    Integer32,
           usrCipModemUtilization
                    Counter32,
           usrCipCallsPerHour
                    Counter32,
           usrCipPacketsForwadedPerHour
                    Counter32
        }
    usrCipModemUtilizationStatisticsIndex OBJECT-TYPE
           SYNTAX     Integer32
           MAX-ACCESS not-accessible
           STATUS     current
           DESCRIPTION
                 "The index for the call duration samples."
           ::= { usrCipModemUtilizationStatisticsEntry 1 }
    usrCipModemUtilization OBJECT-TYPE
           SYNTAX     Counter32   
           MAX-ACCESS read-only
           STATUS     current 
           DESCRIPTION
                 "The  percentage utilization of the modems per hour."
           ::= { usrCipModemUtilizationStatisticsEntry 2 }
    usrCipCallsPerHour OBJECT-TYPE
           SYNTAX     Counter32   
           MAX-ACCESS read-only
           STATUS     current 
           DESCRIPTION
                 "The  number of calls per hour."
           ::= { usrCipModemUtilizationStatisticsEntry 3 }
    usrCipPacketsForwadedPerHour OBJECT-TYPE
           SYNTAX     Counter32   
           MAX-ACCESS read-only
           STATUS     current 
           DESCRIPTION
                 "The  number of packets forwarded per hour."
           ::= { usrCipModemUtilizationStatisticsEntry 4 }
	usrCipCallStatisticsTable OBJECT-TYPE
           SYNTAX     SEQUENCE OF USRCIPCallStatisticsEntry
           MAX-ACCESS  not-accessible
           STATUS     current
           DESCRIPTION
                 "The  table listing the Cip Call statistics
                  for all the calls coming in."
           ::= { usrCip 42 }
    usrCipCallStatisticsEntry OBJECT-TYPE
           SYNTAX     USRCIPCallStatisticsEntry
           MAX-ACCESS not-accessible
           STATUS     current
           DESCRIPTION
				"CIP Call statistics"
           INDEX      { usrCipCallStatisticsIndex }
           ::= { usrCipCallStatisticsTable 1 }
    USRCIPCallStatisticsEntry ::= SEQUENCE {
           usrCipCallStatisticsIndex                        Integer32,
           usrCipCallStatisticsOnDemandConns                Counter32,
           usrCipCallStatisticsContinuousConns              Counter32,
           usrCipCallStatisticsDialBackConns                Counter32,
           usrCipCallStatisticsManualConns                  Counter32,
           usrCipCallStatisticsTimedConns                   Counter32,
           usrCipCallStatisticsSharedConns                  Counter32,
           usrCipCallStatisticsDialInConns                  Counter32,
           usrCipCallStatisticsBondConns                    Counter32,
           usrCipCallStatisticsDedicatedConns               Counter32,
           usrCipCallStatisticsAnalogCalls                  Counter32,
           usrCipCallStatisticsIsdnCalls                    Counter32,
           usrCipCallStatisticsDialInUsers                  Counter32,
           usrCipCallStatisticsNetworkUsers                 Counter32,
           usrCipCallStatisticsCounterResetTime             DateAndTime,
           usrCipCallStatisticsIs95cPppConns                Counter32,
           usrCipCallStatisticsEvdoPppConns                 Counter32
     }
    usrCipCallStatisticsIndex OBJECT-TYPE
           SYNTAX     Integer32
           MAX-ACCESS not-accessible
           STATUS     current
           DESCRIPTION
                 "The index for the call statistics display.
                  they are 0-now, 1-max, 2-today & 3-total."
           ::= { usrCipCallStatisticsEntry 1 }
	usrCipCallStatisticsOnDemandConns OBJECT-TYPE
           SYNTAX     Counter32
           MAX-ACCESS read-only
           STATUS     current
           DESCRIPTION
                 "The number of On Demand connections."
           ::= { usrCipCallStatisticsEntry 2 }
	usrCipCallStatisticsContinuousConns OBJECT-TYPE
           SYNTAX     Counter32
           MAX-ACCESS read-only
           STATUS     current
           DESCRIPTION
                 "The number of Continuous  connections."
           ::= { usrCipCallStatisticsEntry 3 }
	usrCipCallStatisticsDialBackConns OBJECT-TYPE
           SYNTAX     Counter32
           MAX-ACCESS read-only
           STATUS     current
           DESCRIPTION
                 "The number of Dial back connections."
           ::= { usrCipCallStatisticsEntry 4 }
	usrCipCallStatisticsManualConns OBJECT-TYPE
           SYNTAX     Counter32
           MAX-ACCESS read-only
           STATUS     current
           DESCRIPTION
                 "The number of manual connections."
           ::= { usrCipCallStatisticsEntry 5 }
	usrCipCallStatisticsTimedConns OBJECT-TYPE
           SYNTAX     Counter32
           MAX-ACCESS read-only
           STATUS     current
           DESCRIPTION
                 "The number of Timed connections."
           ::= { usrCipCallStatisticsEntry 6 }
	usrCipCallStatisticsSharedConns OBJECT-TYPE
           SYNTAX     Counter32
           MAX-ACCESS read-only
           STATUS     current
           DESCRIPTION
                 "The number of Shared connections."
           ::= { usrCipCallStatisticsEntry 7 }
	usrCipCallStatisticsDialInConns OBJECT-TYPE
           SYNTAX     Counter32
           MAX-ACCESS read-only
           STATUS     current
           DESCRIPTION
                 "The number of Dial-In connections."
           ::= { usrCipCallStatisticsEntry 8 }
	usrCipCallStatisticsBondConns OBJECT-TYPE
           SYNTAX     Counter32
           MAX-ACCESS read-only
           STATUS     current
           DESCRIPTION
                 "The number of Bond connections."
           ::= { usrCipCallStatisticsEntry 9 }
	usrCipCallStatisticsDedicatedConns OBJECT-TYPE
           SYNTAX     Counter32
           MAX-ACCESS read-only
           STATUS     current
           DESCRIPTION
                 "The number of Dedicated connections."
           ::= { usrCipCallStatisticsEntry 10 }
	usrCipCallStatisticsAnalogCalls OBJECT-TYPE
           SYNTAX     Counter32
           MAX-ACCESS read-only
           STATUS     current
           DESCRIPTION
                 "The number of analog calls."
           ::= { usrCipCallStatisticsEntry 11 }
	usrCipCallStatisticsIsdnCalls OBJECT-TYPE
           SYNTAX     Counter32
           MAX-ACCESS read-only
           STATUS     current
           DESCRIPTION
                 "The number of digital calls."
           ::= { usrCipCallStatisticsEntry 12 }
	usrCipCallStatisticsDialInUsers OBJECT-TYPE
           SYNTAX     Counter32
           MAX-ACCESS read-only
           STATUS     current
           DESCRIPTION
                 "The number of login users."
           ::= { usrCipCallStatisticsEntry 13 }
	 usrCipCallStatisticsNetworkUsers OBJECT-TYPE
           SYNTAX     Counter32
           MAX-ACCESS read-only
           STATUS     current
           DESCRIPTION
                 "The number of  Network users."
           ::= { usrCipCallStatisticsEntry 14 }
    usrCipCallStatisticsCounterResetTime	OBJECT-TYPE
      SYNTAX        DateAndTime
	  MAX-ACCESS	read-write
	  STATUS	current
	  DESCRIPTION
	    "Time the call statistics counters were last reset to value zero."
    ::= { usrCipCallStatisticsEntry 15 }
        usrCipCallStatisticsIs95cPppConns OBJECT-TYPE
           SYNTAX     Counter32
           MAX-ACCESS read-only
           STATUS     current
           DESCRIPTION
                 "Counter of IS-95C PPP Connections."
           ::= { usrCipCallStatisticsEntry 16 }
        usrCipCallStatisticsEvdoPppConns OBJECT-TYPE
           SYNTAX     Counter32
           MAX-ACCESS read-only
           STATUS     current
           DESCRIPTION
                 "Counter of EVDO PPP Connections."
           ::= { usrCipCallStatisticsEntry 17 }
	usrCipCallDurationStatisticsTable OBJECT-TYPE
           SYNTAX     SEQUENCE OF USRCIPCallDurationStatisticsEntry
           MAX-ACCESS not-accessible
           STATUS     current
           DESCRIPTION
			 "Number of calls which lasted 1, 2, 5, 10, 20, 60, 
			  120, 360, 720, 1440, 2160 and 3600 minutes & over. 
			  This gives 12 samples."
           ::= { usrCip 43 }
    usrCipCallDurationStatisticsEntry OBJECT-TYPE
           SYNTAX     USRCIPCallDurationStatisticsEntry
           MAX-ACCESS not-accessible
           STATUS     current
           DESCRIPTION
                "CIP Call Duration statistics"
           INDEX      { usrCipCallDurationStatisticsIndex }
           ::= { usrCipCallDurationStatisticsTable 1 }
    USRCIPCallDurationStatisticsEntry ::= SEQUENCE {
           usrCipCallDurationStatisticsIndex            Integer32,
           usrCipCallDurations                          Counter32
        }
    usrCipCallDurationStatisticsIndex OBJECT-TYPE
           SYNTAX     Integer32
           MAX-ACCESS not-accessible
           STATUS     current
           DESCRIPTION
                 "The index for the call duration samples."
           ::= { usrCipCallDurationStatisticsEntry 1 }
    usrCipCallDurations OBJECT-TYPE
           SYNTAX     Counter32 
           MAX-ACCESS read-only
           STATUS     current 
           DESCRIPTION
                 "The  number of calls for each samples."
           ::= { usrCipCallDurationStatisticsEntry 2 }
	usrCipPPPCompressionStatisticsTable OBJECT-TYPE
           SYNTAX     SEQUENCE OF USRCIPPPPCompressionStatisticsEntry
           MAX-ACCESS not-accessible
           STATUS     current
           DESCRIPTION
                 "The  table listing the Cip PPP Compression statistics
                  for all the calls coming in."
           ::= { usrCip 44 }
    usrCipPPPCompressionStatisticsEntry OBJECT-TYPE
           SYNTAX     USRCIPPPPCompressionStatisticsEntry
           MAX-ACCESS not-accessible
           STATUS     current
           DESCRIPTION
                "CIP PPPCompression statistics"
           INDEX      { usrCipPPPCompressionStatisticsIndex }
           ::= { usrCipPPPCompressionStatisticsTable 1 }
    USRCIPPPPCompressionStatisticsEntry ::= SEQUENCE {
           usrCipPPPCompressionStatisticsIndex                Integer32,
           usrCipPPPCompressionStatisticsMicrosoftComp        Counter32,
           usrCipPPPCompressionStatisticsAscendComp           Counter32,
           usrCipPPPCompressionStatisticsStackComp            Counter32,
           usrCipPPPCompressionStatisticsPPPUsers             Counter32,
           usrCipPPPCompressionStatisticsPPPBundlesFormed     Counter32,
           usrCipPPPCompressionStatisticsMrruNegotiated       Counter32,
           usrCipPPPCompressionStatisticsIPXNegotiated        Counter32,
           usrCipPPPCompressionStatisticsIPNegotiated         Counter32,
           usrCipPPPCompressionStatisticsVJCompression        Counter32,
           usrCipPPPCompressionStatisticsBACPNegotiated       Counter32,
           usrCipPPPCompressionStatisticsCHAPAuthenticated    Counter32,
           usrCipPPPCompressionStatisticsPAPAuthenticated     Counter32,
           usrCipPPPCompressionStatisticsMSCHAPAuthenticated  Counter32,
           usrCipPPPCompressionStatisticsEAPAuthenticated     Counter32,
           usrCipPPPCompressionStatisticsResetTime            DateAndTime,
           usrCipPPPCompressionStatisticsDeflateComp          Counter32,
    	   usrCipPPPStatisticsConnInitiated                   Counter32,
           usrCipPPPStatisticsConnRenegotiated                Counter32,
           usrCipPPPStatisticsConnSuccess                     Counter32,
           usrCipPPPStatisticsConnFailed                      Counter32,
           usrCipPPPStatisticsConnRelease                     Counter32,
           usrCipPPPStatisticsConnMobileRelease               Counter32,
           usrCipPPPStatisticsConnPDSNRelease                 Counter32,
           usrCipPPPStatisticsConnLCPFailed                   Counter32,
           usrCipPPPStatisticsConnAuthFailed                  Counter32,
           usrCipPPPStatisticsConnIPCPFailed                  Counter32,
           usrCipPPPStatisticsConnRenegPDSN                   Counter32,
           usrCipPPPStatisticsConnRenegMobile                 Counter32,
           usrCipPPPStatisticsConnRenegIPMismatch             Counter32,
           usrCipPPPStatisticsConnRenegOtherReasons           Counter32,
           usrCipPPPStatisticsConnCHAPAuthSuccess             Counter32,
           usrCipPPPStatisticsConnCHAPAuthFailed              Counter32,
           usrCipPPPStatisticsConnPAPAuthSuccess              Counter32,
           usrCipPPPStatisticsConnPAPAuthFailed               Counter32,
           usrCipPPPStatisticsConnMSCHAPAuthSuccess           Counter32,
           usrCipPPPStatisticsConnMSCHAPAuthFailed            Counter32,
           usrCipPPPStatisticsConnEAPAuthSuccess              Counter32,
           usrCipPPPStatisticsConnEAPAuthFailed               Counter32,
           usrCipPPPStatisticsNumLCPFailMaxRetx               Counter32,
           usrCipPPPStatisticsNumLCPFailUnsupport             Counter32,
           usrCipPPPStatisticsNumLCPFailUnknown               Counter32,
           usrCipPPPStatisticsNumIPCPFailMaxRetx              Counter32,
           usrCipPPPStatisticsNumIPCPFailUnsupport            Counter32,
           usrCipPPPStatisticsNumIPCPFailUnknown              Counter32,
           usrCipPPPStatisticsConnLCPEntered                  Counter32,
           usrCipPPPStatisticsConnAuthEntered                 Counter32,
           usrCipPPPStatisticsConnIPCPEntered                 Counter32,
           usrCipPPPStatisticsTotalCallsWithCompression       Counter32,
           usrCipPPPStatisticsConnsFailedBeforeLcp   	      Counter32,
           usrCipPPPStatisticsConnsReachedLcpOpen   	      Counter32,
           usrCipPPPStatisticsConnsAuthSkipped                Counter32,
           usrCipPPPStatisticsConnsCHAPAuthAborted            Counter32,
           usrCipPPPStatisticsConnsPAPAuthAborted             Counter32,
           usrCipPPPStatisticsConnsMSCHAPAuthAborted          Counter32,
           usrCipPPPStatisticsConnsEAPAuthAborted             Counter32,
           usrCipPPPStatisticsConnsAuthPassed                 Counter32,
           usrCipPPPStatisticsConnsRenegotiatedAfterSetup     Counter32
	}
	usrCipPPPCompressionStatisticsIndex OBJECT-TYPE
           SYNTAX     Integer32
           MAX-ACCESS not-accessible
           STATUS     current
           DESCRIPTION
                 "The index for the PPPCompression statistics display."
           ::= { usrCipPPPCompressionStatisticsEntry 1 }
    usrCipPPPCompressionStatisticsMicrosoftComp OBJECT-TYPE
           SYNTAX     Counter32
           MAX-ACCESS read-only
           STATUS     current
           DESCRIPTION
                 "The number of calls uses microsoft compression."
           ::= { usrCipPPPCompressionStatisticsEntry 2 }
    usrCipPPPCompressionStatisticsAscendComp OBJECT-TYPE
           SYNTAX     Counter32
           MAX-ACCESS read-only
           STATUS     current
           DESCRIPTION
                 "The number of calls uses ascend compression.."
           ::= { usrCipPPPCompressionStatisticsEntry 3 }
    usrCipPPPCompressionStatisticsStackComp OBJECT-TYPE
           SYNTAX     Counter32
           MAX-ACCESS read-only
           STATUS     current
           DESCRIPTION
                 "The number of calls uses stack compression.."
           ::= { usrCipPPPCompressionStatisticsEntry 4 }
    usrCipPPPCompressionStatisticsPPPUsers OBJECT-TYPE
           SYNTAX     Counter32
           MAX-ACCESS read-only
           STATUS     current
           DESCRIPTION
                 "The number of PPP users.."
           ::= { usrCipPPPCompressionStatisticsEntry 5 }
    usrCipPPPCompressionStatisticsPPPBundlesFormed OBJECT-TYPE
           SYNTAX     Counter32
           MAX-ACCESS read-only
           STATUS     current
           DESCRIPTION
                 "The number of PPP Bundles formed.."
           ::= { usrCipPPPCompressionStatisticsEntry 6 }
    usrCipPPPCompressionStatisticsMrruNegotiated OBJECT-TYPE
           SYNTAX     Counter32
           MAX-ACCESS read-only
           STATUS     current
           DESCRIPTION
                 "The number of calls negotiated MRRU for making a multi-link.."
           ::= { usrCipPPPCompressionStatisticsEntry 7 }
    usrCipPPPCompressionStatisticsIPXNegotiated OBJECT-TYPE
           SYNTAX     Counter32
           MAX-ACCESS read-only
           STATUS     current
           DESCRIPTION
                 "The number of calls negotiated IPX."
           ::= { usrCipPPPCompressionStatisticsEntry 8 }
    usrCipPPPCompressionStatisticsIPNegotiated OBJECT-TYPE
           SYNTAX     Counter32
           MAX-ACCESS read-only
           STATUS     current
           DESCRIPTION
                 "The number of calls negotiated IP."
           ::= { usrCipPPPCompressionStatisticsEntry 9 }
    usrCipPPPCompressionStatisticsVJCompression OBJECT-TYPE
           SYNTAX     Counter32
           MAX-ACCESS read-only
           STATUS     current
           DESCRIPTION
                 "The number of calls negotiated VJ Compression"
           ::= { usrCipPPPCompressionStatisticsEntry 10 }
    usrCipPPPCompressionStatisticsBACPNegotiated OBJECT-TYPE
           SYNTAX     Counter32
           MAX-ACCESS read-only
           STATUS     current
           DESCRIPTION
                 "The number of calls negotiated BAP."
           ::= { usrCipPPPCompressionStatisticsEntry 11 }
    usrCipPPPCompressionStatisticsCHAPAuthenticated OBJECT-TYPE
           SYNTAX     Counter32
           MAX-ACCESS read-only
           STATUS     current
           DESCRIPTION
                 "The number of calls attempted authentication using CHAP."
           ::= { usrCipPPPCompressionStatisticsEntry 12 }
    usrCipPPPCompressionStatisticsPAPAuthenticated OBJECT-TYPE
           SYNTAX     Counter32
           MAX-ACCESS read-only
           STATUS     current
           DESCRIPTION
                 "The number of calls attempted authentication using PAP."
           ::= { usrCipPPPCompressionStatisticsEntry 13 }
    usrCipPPPCompressionStatisticsMSCHAPAuthenticated OBJECT-TYPE
           SYNTAX     Counter32
           MAX-ACCESS read-only
           STATUS     current
           DESCRIPTION
                 "The number of calls attempted authentication using MSCHAP."
           ::= { usrCipPPPCompressionStatisticsEntry 14 }
    usrCipPPPCompressionStatisticsEAPAuthenticated OBJECT-TYPE
           SYNTAX     Counter32
           MAX-ACCESS read-only
           STATUS     current
           DESCRIPTION
                 "The number of calls attempted authentication using EAP."
           ::= { usrCipPPPCompressionStatisticsEntry 15 }
    usrCipPPPCompressionStatisticsResetTime	OBJECT-TYPE
           SYNTAX	DateAndTime
           MAX-ACCESS	read-write
           STATUS	current
	   DESCRIPTION
		"Time the PPP statistics counters were last reset to value zero."
    ::= { usrCipPPPCompressionStatisticsEntry 16 }
    usrCipPPPCompressionStatisticsDeflateComp OBJECT-TYPE
           SYNTAX     Counter32
           MAX-ACCESS read-only
           STATUS     current
           DESCRIPTION
                 "The number of calls uses Deflate compression.."
           ::= { usrCipPPPCompressionStatisticsEntry 17 }
    usrCipPPPStatisticsConnInitiated OBJECT-TYPE
           SYNTAX     Counter32
           MAX-ACCESS read-only
           STATUS     current
           DESCRIPTION
                 "The number of PPP calls initiated."
           ::= { usrCipPPPCompressionStatisticsEntry 18 }
    usrCipPPPStatisticsConnRenegotiated OBJECT-TYPE
           SYNTAX     Counter32
           MAX-ACCESS read-only
           STATUS     current
           DESCRIPTION
                 "The number of PPP calls renegotiated."
           ::= { usrCipPPPCompressionStatisticsEntry 19 }
    usrCipPPPStatisticsConnSuccess OBJECT-TYPE
           SYNTAX     Counter32
           MAX-ACCESS read-only
           STATUS     current
           DESCRIPTION
                 "The number of PPP calls succeeded."
           ::= { usrCipPPPCompressionStatisticsEntry 20 }
    usrCipPPPStatisticsConnFailed OBJECT-TYPE
           SYNTAX     Counter32
           MAX-ACCESS read-only
           STATUS     current
           DESCRIPTION
                 "The number of PPP calls failed."
           ::= { usrCipPPPCompressionStatisticsEntry 21 }
    usrCipPPPStatisticsConnRelease OBJECT-TYPE
           SYNTAX     Counter32
           MAX-ACCESS read-only
           STATUS     current
           DESCRIPTION
                 "The number of PPP calls released."
           ::= { usrCipPPPCompressionStatisticsEntry 22 }
    usrCipPPPStatisticsConnMobileRelease OBJECT-TYPE
           SYNTAX     Counter32
           MAX-ACCESS read-only
           STATUS     current
           DESCRIPTION
                 "The number of PPP calls released by Mobile."
           ::= { usrCipPPPCompressionStatisticsEntry 23 }
    usrCipPPPStatisticsConnPDSNRelease OBJECT-TYPE
           SYNTAX     Counter32
           MAX-ACCESS read-only
           STATUS     current
           DESCRIPTION
                 "The number of PPP calls released by PDSN."
           ::= { usrCipPPPCompressionStatisticsEntry 24 }
    usrCipPPPStatisticsConnLCPFailed   OBJECT-TYPE
           SYNTAX     Counter32
           MAX-ACCESS read-only
           STATUS     current
           DESCRIPTION
                 "The number of PPP calls failed at LCP state."
           ::= { usrCipPPPCompressionStatisticsEntry 25 }
    usrCipPPPStatisticsConnAuthFailed   OBJECT-TYPE
           SYNTAX     Counter32
           MAX-ACCESS read-only
           STATUS     current
           DESCRIPTION
                 "The number of PPP calls failed at authentication state."
           ::= { usrCipPPPCompressionStatisticsEntry 26 }
    usrCipPPPStatisticsConnIPCPFailed   OBJECT-TYPE
           SYNTAX     Counter32
           MAX-ACCESS read-only
           STATUS     current
           DESCRIPTION
                 "The number of PPP calls failed at IPCP state."
           ::= { usrCipPPPCompressionStatisticsEntry 27 }
    usrCipPPPStatisticsConnRenegPDSN   OBJECT-TYPE
           SYNTAX     Counter32
           MAX-ACCESS read-only
           STATUS     current
           DESCRIPTION
                 "The number of PPP calls renegotiated by PDSN."
           ::= { usrCipPPPCompressionStatisticsEntry 28 }
    usrCipPPPStatisticsConnRenegMobile   OBJECT-TYPE
           SYNTAX     Counter32
           MAX-ACCESS read-only
           STATUS     current
           DESCRIPTION
                 "The number of PPP calls renegotiated by Mobile."
           ::= { usrCipPPPCompressionStatisticsEntry 29 }
    usrCipPPPStatisticsConnRenegIPMismatch   OBJECT-TYPE
           SYNTAX     Counter32
           MAX-ACCESS read-only
           STATUS     current
           DESCRIPTION
                 "The number of PPP calls renegotiated due to IP mismatch."
           ::= { usrCipPPPCompressionStatisticsEntry 30 }
    usrCipPPPStatisticsConnRenegOtherReasons   OBJECT-TYPE
           SYNTAX     Counter32
           MAX-ACCESS read-only
           STATUS     current
           DESCRIPTION
                 "The number of PPP calls renegotiated due to some reason."
           ::= { usrCipPPPCompressionStatisticsEntry 31 }
    usrCipPPPStatisticsConnCHAPAuthSuccess   OBJECT-TYPE
           SYNTAX     Counter32
           MAX-ACCESS read-only
           STATUS     current
           DESCRIPTION
                 "The number of PPP calls successfully authenticated with CHAP."
           ::= { usrCipPPPCompressionStatisticsEntry 32 }
    usrCipPPPStatisticsConnCHAPAuthFailed   OBJECT-TYPE
           SYNTAX     Counter32
           MAX-ACCESS read-only
           STATUS     current
           DESCRIPTION
                 "The number of PPP calls failed in CHAP authentication."
           ::= { usrCipPPPCompressionStatisticsEntry 33 }
    usrCipPPPStatisticsConnPAPAuthSuccess   OBJECT-TYPE
           SYNTAX     Counter32
           MAX-ACCESS read-only
           STATUS     current
           DESCRIPTION
                 "The number of PPP calls successfully authenticated with PAP."
           ::= { usrCipPPPCompressionStatisticsEntry 34 }
    usrCipPPPStatisticsConnPAPAuthFailed   OBJECT-TYPE
           SYNTAX     Counter32
           MAX-ACCESS read-only
           STATUS     current
           DESCRIPTION
                 "The number of PPP calls failed in PAP authentication."
           ::= { usrCipPPPCompressionStatisticsEntry 35 }
    usrCipPPPStatisticsConnMSCHAPAuthSuccess   OBJECT-TYPE
           SYNTAX     Counter32
           MAX-ACCESS read-only
           STATUS     current
           DESCRIPTION
                 "The number of PPP calls successfully authenticated with MSCHAP."
           ::= { usrCipPPPCompressionStatisticsEntry 36 }
    usrCipPPPStatisticsConnMSCHAPAuthFailed   OBJECT-TYPE
           SYNTAX     Counter32
           MAX-ACCESS read-only
           STATUS     current
           DESCRIPTION
                 "The number of PPP calls failed in MSCHAP authentication."
           ::= { usrCipPPPCompressionStatisticsEntry 37 }
    usrCipPPPStatisticsConnEAPAuthSuccess   OBJECT-TYPE
           SYNTAX     Counter32
           MAX-ACCESS read-only
           STATUS     current
           DESCRIPTION
                 "The number of PPP calls successfully authenticated with EAP."
           ::= { usrCipPPPCompressionStatisticsEntry 38 }
    usrCipPPPStatisticsConnEAPAuthFailed   OBJECT-TYPE
           SYNTAX     Counter32
           MAX-ACCESS read-only
           STATUS     current
           DESCRIPTION
                 "The number of PPP calls failed in EAP authentication."
           ::= { usrCipPPPCompressionStatisticsEntry 39 }
    usrCipPPPStatisticsNumLCPFailMaxRetx   OBJECT-TYPE
           SYNTAX     Counter32
           MAX-ACCESS read-only
           STATUS     current
           DESCRIPTION
                 "The number of PPP calls failed after maximum retries while negotiating LCP."
           ::= { usrCipPPPCompressionStatisticsEntry 40 }
    usrCipPPPStatisticsNumLCPFailUnsupport   OBJECT-TYPE
           SYNTAX     Counter32
           MAX-ACCESS read-only
           STATUS     current
           DESCRIPTION
                 "The number of PPP calls failed due to unsupported attribute while negotiating LCP."
           ::= { usrCipPPPCompressionStatisticsEntry 41 }
    usrCipPPPStatisticsNumLCPFailUnknown   OBJECT-TYPE
           SYNTAX     Counter32
           MAX-ACCESS read-only
           STATUS     current
           DESCRIPTION
                 "The number of PPP calls failed due to unknown reason while negotiating LCP."
           ::= { usrCipPPPCompressionStatisticsEntry 42 }
    usrCipPPPStatisticsNumIPCPFailMaxRetx   OBJECT-TYPE
           SYNTAX     Counter32
           MAX-ACCESS read-only
           STATUS     current
           DESCRIPTION
                 "The number of PPP calls failed after maximum retries while negotiating IPCP."
           ::= { usrCipPPPCompressionStatisticsEntry 43 }
    usrCipPPPStatisticsNumIPCPFailUnsupport   OBJECT-TYPE
           SYNTAX     Counter32
           MAX-ACCESS read-only
           STATUS     current
           DESCRIPTION
                 "The number of PPP calls failed due to unsupported attribute while negotiating IPCP."
           ::= { usrCipPPPCompressionStatisticsEntry 44 }
    usrCipPPPStatisticsNumIPCPFailUnknown   OBJECT-TYPE
           SYNTAX     Counter32
           MAX-ACCESS read-only
           STATUS     current
           DESCRIPTION
                 "The number of PPP calls failed due to unknown reason while negotiating IPCP."
           ::= { usrCipPPPCompressionStatisticsEntry 45 }
    usrCipPPPStatisticsConnLCPEntered   OBJECT-TYPE
           SYNTAX     Counter32
           MAX-ACCESS read-only
           STATUS     current
           DESCRIPTION
                 "The number of PPP calls which entered LCP state."
           ::= { usrCipPPPCompressionStatisticsEntry 46 }
    usrCipPPPStatisticsConnAuthEntered   OBJECT-TYPE
           SYNTAX     Counter32
           MAX-ACCESS read-only
           STATUS     current
           DESCRIPTION
                 "The number of PPP calls which entered authentication state."
           ::= { usrCipPPPCompressionStatisticsEntry 47 }
    usrCipPPPStatisticsConnIPCPEntered   OBJECT-TYPE
           SYNTAX     Counter32
           MAX-ACCESS read-only
           STATUS     current
           DESCRIPTION
                 "The number of PPP calls which entered IPCP state."
           ::= { usrCipPPPCompressionStatisticsEntry 48 }
    usrCipPPPStatisticsTotalCallsWithCompression   OBJECT-TYPE
           SYNTAX     Counter32
           MAX-ACCESS read-only
           STATUS     current
           DESCRIPTION
                 "The total number of PPP calls which used compression."
           ::= { usrCipPPPCompressionStatisticsEntry 49 }
    usrCipPPPStatisticsConnsFailedBeforeLcp   OBJECT-TYPE
           SYNTAX     Counter32
           MAX-ACCESS read-only
           STATUS     current
           DESCRIPTION
                 "The number of PPP calls failed before LCP negotiated
		  even started.  An example is running out of memmory or
		  some other internal failure before LCP begins."
           ::= { usrCipPPPCompressionStatisticsEntry 50 }
    usrCipPPPStatisticsConnsReachedLcpOpen   OBJECT-TYPE
           SYNTAX     Counter32
           MAX-ACCESS read-only
           STATUS     current
           DESCRIPTION
                 "The number of PPP calls that have successfully negotiated
		  the LCP options, have reached the LCP Open stane, and have
		  proceeded to the next PPP phase (usually Authentication)."
           ::= { usrCipPPPCompressionStatisticsEntry 51 }
    usrCipPPPStatisticsConnsAuthSkipped   OBJECT-TYPE
           SYNTAX     Counter32
           MAX-ACCESS read-only
           STATUS     current
           DESCRIPTION
                 "The number of PPP calls that have negotiated to have no
		  authentication protocol, have reached the LCP Open state,
		  and therefore have skipped the PPP Authentication phase,
		  and proceeded directly to the PPP Network phase."
           ::= { usrCipPPPCompressionStatisticsEntry 52 }
    usrCipPPPStatisticsConnsCHAPAuthAborted   OBJECT-TYPE
           SYNTAX     Counter32
           MAX-ACCESS read-only
           STATUS     current
           DESCRIPTION
                 "The number of PPP calls failed during CHAP authentication
		  at a different layer than CHAP authentication
		  prior to CHAP authentication reaching a pass/fail verdict.
		  Examples are receiving a LCP Term Req or physical layer down
		  while waiting for the auth reply from a RADIUS server."
           ::= { usrCipPPPCompressionStatisticsEntry 53 }
    usrCipPPPStatisticsConnsPAPAuthAborted   OBJECT-TYPE
           SYNTAX     Counter32
           MAX-ACCESS read-only
           STATUS     current
           DESCRIPTION
                 "The number of PPP calls failed during PAP authentication
		  at a different layer than PAP authentication
		  prior to PAP authentication reaching a pass/fail verdict.
		  Examples are receiving a LCP Term Req or physical layer down
		  while waiting for the auth reply from a RADIUS server."
           ::= { usrCipPPPCompressionStatisticsEntry 54 }
    usrCipPPPStatisticsConnsMSCHAPAuthAborted   OBJECT-TYPE
           SYNTAX     Counter32
           MAX-ACCESS read-only
           STATUS     current
           DESCRIPTION
                 "The number of PPP calls failed during MSCHAP authentication
		  at a different layer than MSCHAP authentication
		  prior to MSCHAP authentication reaching a pass/fail verdict.
		  Examples are receiving a LCP Term Req or physical layer down
		  while waiting for the auth reply from a RADIUS server."
           ::= { usrCipPPPCompressionStatisticsEntry 55 }
    usrCipPPPStatisticsConnsEAPAuthAborted   OBJECT-TYPE
           SYNTAX     Counter32
           MAX-ACCESS read-only
           STATUS     current
           DESCRIPTION
                 "The number of PPP calls failed during EAP authentication
		  at a different layer than EAP authentication
		  prior to EAP authentication reaching a pass/fail verdict.
		  Examples are receiving a LCP Term Req or physical layer down
		  while waiting for the auth reply from a RADIUS server."
           ::= { usrCipPPPCompressionStatisticsEntry 56 }
    usrCipPPPStatisticsConnsAuthPassed   OBJECT-TYPE
           SYNTAX     Counter32
           MAX-ACCESS read-only
           STATUS     current
           DESCRIPTION
                 "The number of PPP calls that have successfully passed the
		  authentication phase, and have proceeded to the PPP Network
		  phase."
           ::= { usrCipPPPCompressionStatisticsEntry 57 }
    usrCipPPPStatisticsConnsRenegotiatedAfterSetup  OBJECT-TYPE
           SYNTAX     Counter32
           MAX-ACCESS read-only
           STATUS     current
           DESCRIPTION
                 "The number of PPP calls that have initiated renegotiation
		  after PPP link reached the fully setup state."
           ::= { usrCipPPPCompressionStatisticsEntry 58 }
	usrCipSpeedStatisticsTable OBJECT-TYPE
           SYNTAX     SEQUENCE OF USRCIPSpeedStatisticsEntry
           MAX-ACCESS not-accessible
           STATUS     current
           DESCRIPTION
                 "The  table listing the CIP Speed statistics
                  for all the calls coming in."
           ::= { usrCip 45 }
    usrCipSpeedStatisticsEntry OBJECT-TYPE
           SYNTAX     USRCIPSpeedStatisticsEntry
           MAX-ACCESS not-accessible
           STATUS     current
           DESCRIPTION
                "CIP Speed statistics of the incoming calls."
           INDEX      { usrCipSpeedStatisticsIndex }
           ::= { usrCipSpeedStatisticsTable 1 }
    USRCIPSpeedStatisticsEntry ::= SEQUENCE {
           usrCipSpeedStatisticsIndex                      Integer32,
           usrCipSpeedStatisticsSpeed300                   Counter32,
           usrCipSpeedStatisticsSpeed1200                  Counter32,
           usrCipSpeedStatisticsSpeed2400                  Counter32,
           usrCipSpeedStatisticsSpeed4800                  Counter32,
           usrCipSpeedStatisticsSpeed7200                  Counter32,
           usrCipSpeedStatisticsSpeed9600                  Counter32,
           usrCipSpeedStatisticsSpeed12000                 Counter32,
           usrCipSpeedStatisticsSpeed14400                 Counter32,
           usrCipSpeedStatisticsSpeed16800                 Counter32,
           usrCipSpeedStatisticsSpeed19200                 Counter32,
           usrCipSpeedStatisticsSpeed21600                 Counter32,
           usrCipSpeedStatisticsSpeed28800                 Counter32,
           usrCipSpeedStatisticsSpeed38400                 Counter32,
           usrCipSpeedStatisticsSpeed57600                 Counter32,
           usrCipSpeedStatisticsSpeed115200                Counter32,
           usrCipSpeedStatisticsSpeed288000                Counter32,
           usrCipSpeedStatisticsSpeed751200                Counter32,
           usrCipSpeedStatisticsSpeed120075                Counter32,
           usrCipSpeedStatisticsSpeed24000                 Counter32,
           usrCipSpeedStatisticsSpeed26400                 Counter32,
           usrCipSpeedStatisticsSpeed31200                 Counter32,
           usrCipSpeedStatisticsSpeed33600                 Counter32,
           usrCipSpeedStatisticsSpeed32000                 Counter32,
           usrCipSpeedStatisticsSpeed36000                 Counter32,
           usrCipSpeedStatisticsSpeed40000                 Counter32,
           usrCipSpeedStatisticsSpeed44000                 Counter32,
           usrCipSpeedStatisticsSpeed48000                 Counter32,
           usrCipSpeedStatisticsSpeed49333                 Counter32,
           usrCipSpeedStatisticsSpeed50666                 Counter32,
           usrCipSpeedStatisticsSpeed52000                 Counter32,
           usrCipSpeedStatisticsSpeed53333                 Counter32,
           usrCipSpeedStatisticsSpeed54666                 Counter32,
           usrCipSpeedStatisticsSpeed56000                 Counter32,
           usrCipSpeedStatisticsSpeed57333                 Counter32,
           usrCipSpeedStatisticsSpeed58666                 Counter32,
           usrCipSpeedStatisticsSpeed60000                 Counter32,
           usrCipSpeedStatisticsSpeed61333                 Counter32,
           usrCipSpeedStatisticsSpeed64000                 Counter32,
           usrCipSpeedStatisticsResetTime                  DateAndTime
    }
    usrCipSpeedStatisticsIndex OBJECT-TYPE
           SYNTAX     Integer32
           MAX-ACCESS not-accessible
           STATUS     current
           DESCRIPTION
                 "The index for the speed statistics display.
                  they are 0-now & 1-total."
           ::= { usrCipSpeedStatisticsEntry 1 }
    usrCipSpeedStatisticsSpeed300 OBJECT-TYPE
           SYNTAX     Counter32
           MAX-ACCESS read-only
           STATUS     current
           DESCRIPTION
                 "The number of calls with speed of 300."
           ::= { usrCipSpeedStatisticsEntry 2 }
    usrCipSpeedStatisticsSpeed1200 OBJECT-TYPE
           SYNTAX     Counter32
           MAX-ACCESS read-only
           STATUS     current
           DESCRIPTION
                 "The number of calls with speed of 1200."
           ::= { usrCipSpeedStatisticsEntry 3 }
    usrCipSpeedStatisticsSpeed2400 OBJECT-TYPE
           SYNTAX     Counter32
           MAX-ACCESS read-only
           STATUS     current
           DESCRIPTION
                 "The number of calls with speed of 2400."
           ::= { usrCipSpeedStatisticsEntry 4 }
    usrCipSpeedStatisticsSpeed4800 OBJECT-TYPE
           SYNTAX     Counter32
           MAX-ACCESS read-only
           STATUS     current
           DESCRIPTION
                 "The number of calls with speed of 4800."
           ::= { usrCipSpeedStatisticsEntry 5 }
    usrCipSpeedStatisticsSpeed7200 OBJECT-TYPE
           SYNTAX     Counter32
           MAX-ACCESS read-only
           STATUS     current
           DESCRIPTION
                 "The number of calls with speed of 7200."
           ::= { usrCipSpeedStatisticsEntry 6 }
    usrCipSpeedStatisticsSpeed9600 OBJECT-TYPE
           SYNTAX     Counter32
           MAX-ACCESS read-only
           STATUS     current
           DESCRIPTION
                 "The number of calls with speed of 9600."
           ::= { usrCipSpeedStatisticsEntry 7 }
    usrCipSpeedStatisticsSpeed12000 OBJECT-TYPE
           SYNTAX     Counter32
           MAX-ACCESS read-only
           STATUS     current
           DESCRIPTION
                 "The number of calls with speed of 12000."
           ::= { usrCipSpeedStatisticsEntry 8 }
    usrCipSpeedStatisticsSpeed14400 OBJECT-TYPE
           SYNTAX     Counter32
           MAX-ACCESS read-only
           STATUS     current
           DESCRIPTION
                 "The number of calls with speed of 14400."
           ::= { usrCipSpeedStatisticsEntry 9 }
    usrCipSpeedStatisticsSpeed16800 OBJECT-TYPE
           SYNTAX     Counter32
           MAX-ACCESS read-only
           STATUS     current
           DESCRIPTION
                 "The number of calls with speed of 16800."
           ::= { usrCipSpeedStatisticsEntry 10 }
    usrCipSpeedStatisticsSpeed19200 OBJECT-TYPE
           SYNTAX     Counter32
           MAX-ACCESS read-only
           STATUS     current
           DESCRIPTION
                 "The number of calls with speed of 19200."
           ::= { usrCipSpeedStatisticsEntry 11 }
    usrCipSpeedStatisticsSpeed21600 OBJECT-TYPE
           SYNTAX     Counter32
           MAX-ACCESS read-only
           STATUS     current
           DESCRIPTION
                 "The number of calls with speed of 21600."
           ::= { usrCipSpeedStatisticsEntry 12 }
    usrCipSpeedStatisticsSpeed28800 OBJECT-TYPE
           SYNTAX     Counter32
           MAX-ACCESS read-only
           STATUS     current
           DESCRIPTION
                 "The number of calls with speed of 28800."
           ::= { usrCipSpeedStatisticsEntry 13 }
    usrCipSpeedStatisticsSpeed38400 OBJECT-TYPE
           SYNTAX     Counter32
           MAX-ACCESS read-only
           STATUS     current
           DESCRIPTION
                 "The number of calls with speed of 38400."
           ::= { usrCipSpeedStatisticsEntry 14 }
    usrCipSpeedStatisticsSpeed57600 OBJECT-TYPE
           SYNTAX     Counter32
           MAX-ACCESS read-only
           STATUS     current
           DESCRIPTION
                 "The number of calls with speed of 57600."
           ::= { usrCipSpeedStatisticsEntry 15 }
    usrCipSpeedStatisticsSpeed115200 OBJECT-TYPE
           SYNTAX     Counter32
           MAX-ACCESS read-only
           STATUS     current
           DESCRIPTION
                 "The number of calls with speed of 115200."
           ::= { usrCipSpeedStatisticsEntry 16 }
    usrCipSpeedStatisticsSpeed288000 OBJECT-TYPE
           SYNTAX     Counter32
           MAX-ACCESS read-only
           STATUS     current
           DESCRIPTION
                 "The number of calls with speed of 288000."
           ::= { usrCipSpeedStatisticsEntry 17 }
    usrCipSpeedStatisticsSpeed751200 OBJECT-TYPE
           SYNTAX     Counter32
           MAX-ACCESS read-only
           STATUS     current
           DESCRIPTION
                 "The number of calls with speed of 75_1200."
           ::= { usrCipSpeedStatisticsEntry 18 }
    usrCipSpeedStatisticsSpeed120075 OBJECT-TYPE
           SYNTAX     Counter32
           MAX-ACCESS read-only
           STATUS     current
           DESCRIPTION
                 "The number of calls with speed of 1200_75."
           ::= { usrCipSpeedStatisticsEntry 19 }
    usrCipSpeedStatisticsSpeed24000 OBJECT-TYPE
           SYNTAX     Counter32
           MAX-ACCESS read-only
           STATUS     current
           DESCRIPTION
                 "The number of calls with speed of 24000."
           ::= { usrCipSpeedStatisticsEntry 20 }
    usrCipSpeedStatisticsSpeed26400 OBJECT-TYPE
           SYNTAX     Counter32
           MAX-ACCESS read-only
           STATUS     current
           DESCRIPTION
                 "The number of calls with a speed of 26400."
           ::= { usrCipSpeedStatisticsEntry 21 }
    usrCipSpeedStatisticsSpeed31200 OBJECT-TYPE
           SYNTAX     Counter32
           MAX-ACCESS read-only
           STATUS     current
           DESCRIPTION
                 "The number of calls with a speed of 31200."
           ::= { usrCipSpeedStatisticsEntry 22 }
    usrCipSpeedStatisticsSpeed33600 OBJECT-TYPE
           SYNTAX     Counter32
           MAX-ACCESS read-only
           STATUS     current
           DESCRIPTION
                 "The number of calls with a speed of 33600."
           ::= { usrCipSpeedStatisticsEntry 23 }
    usrCipSpeedStatisticsSpeed32000 OBJECT-TYPE
           SYNTAX     Counter32
           MAX-ACCESS read-only
           STATUS     current
           DESCRIPTION
                 "The number of calls with a speed of 32000."
           ::= { usrCipSpeedStatisticsEntry 24 }
    usrCipSpeedStatisticsSpeed36000 OBJECT-TYPE
           SYNTAX     Counter32
           MAX-ACCESS read-only
           STATUS     current
           DESCRIPTION
                 "The number of calls with a speed of 36000."
           ::= { usrCipSpeedStatisticsEntry 25 }
    usrCipSpeedStatisticsSpeed40000 OBJECT-TYPE
           SYNTAX     Counter32
           MAX-ACCESS read-only
           STATUS     current
           DESCRIPTION
                 "The number of calls with a speed of 40000."
           ::= { usrCipSpeedStatisticsEntry 26 }
    usrCipSpeedStatisticsSpeed44000 OBJECT-TYPE
           SYNTAX     Counter32
           MAX-ACCESS read-only
           STATUS     current
           DESCRIPTION
                 "The number of calls with a speed of 44000."
           ::= { usrCipSpeedStatisticsEntry 27 }
    usrCipSpeedStatisticsSpeed48000 OBJECT-TYPE
           SYNTAX     Counter32
           MAX-ACCESS read-only
           STATUS     current
           DESCRIPTION
                 "The number of calls with a speed of 48000."
           ::= { usrCipSpeedStatisticsEntry 28 }
    usrCipSpeedStatisticsSpeed49333 OBJECT-TYPE
           SYNTAX     Counter32
           MAX-ACCESS read-only
           STATUS     current
           DESCRIPTION
                 "The number of calls with a speed of 49333."
           ::= { usrCipSpeedStatisticsEntry 29 }
    usrCipSpeedStatisticsSpeed50666 OBJECT-TYPE
           SYNTAX     Counter32
           MAX-ACCESS read-only
           STATUS     current
           DESCRIPTION
                 "The number of calls with a speed of 50666."
           ::= { usrCipSpeedStatisticsEntry 30 }
    usrCipSpeedStatisticsSpeed52000 OBJECT-TYPE
           SYNTAX     Counter32
           MAX-ACCESS read-only
           STATUS     current
           DESCRIPTION
                 "The number of calls with a speed of 52000."
           ::= { usrCipSpeedStatisticsEntry 31 }
    usrCipSpeedStatisticsSpeed53333 OBJECT-TYPE
           SYNTAX     Counter32
           MAX-ACCESS read-only
           STATUS     current
           DESCRIPTION
                 "The number of calls with a speed of 53333."
           ::= { usrCipSpeedStatisticsEntry 32 }
    usrCipSpeedStatisticsSpeed54666 OBJECT-TYPE
           SYNTAX     Counter32
           MAX-ACCESS read-only
           STATUS     current
           DESCRIPTION
                 "The number of calls with a speed of 54666."
           ::= { usrCipSpeedStatisticsEntry 33 }
    usrCipSpeedStatisticsSpeed56000 OBJECT-TYPE
           SYNTAX     Counter32
           MAX-ACCESS read-only
           STATUS     current
           DESCRIPTION
                 "The number of calls with a speed of 56000."
           ::= { usrCipSpeedStatisticsEntry 34 }
    usrCipSpeedStatisticsSpeed57333 OBJECT-TYPE
           SYNTAX     Counter32
           MAX-ACCESS read-only
           STATUS     current
           DESCRIPTION
                 "The number of calls with a speed of 57333."
           ::= { usrCipSpeedStatisticsEntry 35 }
    usrCipSpeedStatisticsSpeed58666 OBJECT-TYPE
           SYNTAX     Counter32
           MAX-ACCESS read-only
           STATUS     current
           DESCRIPTION
                 "The number of calls with a speed of 58666."
           ::= { usrCipSpeedStatisticsEntry 36 }
    usrCipSpeedStatisticsSpeed60000 OBJECT-TYPE
           SYNTAX     Counter32
           MAX-ACCESS read-only
           STATUS     current
           DESCRIPTION
                 "The number of calls with a speed of 60000."
           ::= { usrCipSpeedStatisticsEntry 37 }
    usrCipSpeedStatisticsSpeed61333 OBJECT-TYPE
           SYNTAX     Counter32
           MAX-ACCESS read-only
           STATUS     current
           DESCRIPTION
                 "The number of calls with a speed of 61333."
           ::= { usrCipSpeedStatisticsEntry 38 }
    usrCipSpeedStatisticsSpeed64000 OBJECT-TYPE
           SYNTAX     Counter32
           MAX-ACCESS read-only
           STATUS     current
           DESCRIPTION
                 "The number of calls with speed of 64000."
           ::= { usrCipSpeedStatisticsEntry 39 }
    usrCipSpeedStatisticsResetTime	OBJECT-TYPE
			SYNTAX	    DateAndTime
			MAX-ACCESS	read-write
			STATUS	current
			DESCRIPTION
				"Time the Speed statistics counters were last reset to value zero."
    ::= { usrCipSpeedStatisticsEntry 40 }
    usrCipPacketSizeStatisticsTable OBJECT-TYPE
           SYNTAX     SEQUENCE OF USRCIPPacketSizeStatisticsEntry
           MAX-ACCESS not-accessible
           STATUS     current
           DESCRIPTION
	           "Size of the PPP packets in each direction.
		    packet size of every 64 bytes. ie 0-64, 64-128,
 	            128-192,, 2048. Which gives 32 samples."
           ::= { usrCip 46 }
    usrCipPacketSizeStatisticsEntry OBJECT-TYPE
           SYNTAX     USRCIPPacketSizeStatisticsEntry
           MAX-ACCESS not-accessible
           STATUS     current
           DESCRIPTION
                "CIP PPP packet size statistics"
           INDEX      { usrCipPacketSizeStatisticsIndex }
           ::= { usrCipPacketSizeStatisticsTable 1 }
    USRCIPPacketSizeStatisticsEntry ::= SEQUENCE {
           usrCipPacketSizeStatisticsIndex      Integer32,
           usrCipPacketUpLoadSizes              Counter32,
           usrCipPacketDownLoadSizes            Counter32
		}
	usrCipPacketSizeStatisticsIndex OBJECT-TYPE
           SYNTAX     Integer32
           MAX-ACCESS not-accessible
           STATUS     current
           DESCRIPTION
                 "The index for the PPP packet size samples."
           ::= { usrCipPacketSizeStatisticsEntry 1 }
    usrCipPacketUpLoadSizes OBJECT-TYPE
           SYNTAX     Counter32
           MAX-ACCESS read-only
           STATUS     current
           DESCRIPTION
                 "The PPP Upload packet size samples."
           ::= { usrCipPacketSizeStatisticsEntry 2 }
    usrCipPacketDownLoadSizes OBJECT-TYPE
           SYNTAX     Counter32
           MAX-ACCESS read-only
           STATUS     current
           DESCRIPTION
                 "The PPP Download packet size samples."
           ::= { usrCipPacketSizeStatisticsEntry 3 }
	usrCipModemDisconectReasonNoError  OBJECT-TYPE
         SYNTAX  Counter32
         MAX-ACCESS  read-only
         STATUS  current
         DESCRIPTION
             "Number of calls with disconnect reason no_error."
         ::= { usrCip 47 }
	usrCipModemDisconectReasonNoCarrier  OBJECT-TYPE
         SYNTAX  Counter32
         MAX-ACCESS  read-only
         STATUS  current
         DESCRIPTION
             "Number of calls with disconnect reason no_carrier."
         ::= { usrCip 48 }
	usrCipModemDisconectReasonNoDsr  OBJECT-TYPE
         SYNTAX  Counter32
         MAX-ACCESS  read-only
         STATUS  current
         DESCRIPTION
             "Number of calls with disconnect reason no_dsr."
         ::= { usrCip 49 }
	usrCipModemDisconectReasonTimeout  OBJECT-TYPE
         SYNTAX  Counter32
         MAX-ACCESS  read-only
         STATUS  current
         DESCRIPTION
             "Number of calls with disconnect reason timeout."
         ::= { usrCip 50 }
	usrCipModemDisconectReasonReset  OBJECT-TYPE
         SYNTAX  Counter32
         MAX-ACCESS  read-only
         STATUS  current
         DESCRIPTION
             "Number of calls with disconnect reason reset."
         ::= { usrCip 51 }
	usrCipModemDisconectReasonCallDropReq  OBJECT-TYPE
         SYNTAX  Counter32
         MAX-ACCESS  read-only
         STATUS  current
         DESCRIPTION
             "Number of calls with disconnect reason call_drop_req."
         ::= { usrCip 52 }
	usrCipModemDisconectReasonIdleTimeout  OBJECT-TYPE
         SYNTAX  Counter32
         MAX-ACCESS  read-only
         STATUS  current
         DESCRIPTION
             "Number of calls with disconnect reason idle_timeout."
         ::= { usrCip 53 }
	usrCipModemDisconectReasonSessionTimeout  OBJECT-TYPE
         SYNTAX  Counter32
         MAX-ACCESS  read-only
         STATUS  current
         DESCRIPTION
             "Number of calls with disconnect reason session_timeout."
         ::= { usrCip 54 }
	usrCipModemDisconectReasonUserReqDrop  OBJECT-TYPE
         SYNTAX  Counter32
         MAX-ACCESS  read-only
         STATUS  current
         DESCRIPTION
             "Number of calls with disconnect reason user_req_drop."
         ::= { usrCip 55 }
	usrCipModemDisconectReasonHostReqDrop  OBJECT-TYPE
         SYNTAX  Counter32
         MAX-ACCESS  read-only
         STATUS  current
         DESCRIPTION
             "Number of calls with disconnect reason host_req_drop."
         ::= { usrCip 56 }
	usrCipModemDisconectReasonServiceInterruption  OBJECT-TYPE
         SYNTAX  Counter32
         MAX-ACCESS  read-only
         STATUS  current
         DESCRIPTION
             "Number of calls with disconnect reason service_interruption."
         ::= { usrCip 57 }
	usrCipModemDisconectReasonServiceUnavailable  OBJECT-TYPE
         SYNTAX  Counter32
         MAX-ACCESS  read-only
         STATUS  current
         DESCRIPTION
             "Number of calls with disconnect reason service_unavailable."
         ::= { usrCip 58 }
	usrCipModemDisconectReasonUserInputError  OBJECT-TYPE
         SYNTAX  Counter32
         MAX-ACCESS  read-only
         STATUS  current
         DESCRIPTION
             "Number of calls with disconnect reason user_input_error."
         ::= { usrCip 59 }
	usrCipModemDisconectReasonNasDropForCallback  OBJECT-TYPE
         SYNTAX  Counter32
         MAX-ACCESS  read-only
         STATUS  current
         DESCRIPTION
             "Number of calls with disconnect reason nas_drop_for_callback."
         ::= { usrCip 60 }
        usrCipModemDisconectReasonnasDropMiscNonError  OBJECT-TYPE
         SYNTAX  Counter32
         MAX-ACCESS  read-only
         STATUS  current
         DESCRIPTION
             "Number of calls with disconnect reason nas_drop_misc_non_error."
         ::= { usrCip 61 }
	usrCipModemDisconectReasonNasInternalError  OBJECT-TYPE
         SYNTAX  Counter32
         MAX-ACCESS  read-only
         STATUS  current
         DESCRIPTION
             "Number of calls with disconnect reason nas_internal_error."
         ::= { usrCip 62 }
	usrCipStatisticsResetCallDuration    OBJECT-TYPE
         SYNTAX  DateAndTime
         MAX-ACCESS  read-write
	 STATUS  current
	 DESCRIPTION
		"Daily time we reset all the call statistics counters."
         ::= { usrCip 63 }
	usrCipStatisticsResetPPPUploadPackets    OBJECT-TYPE
	 SYNTAX  DateAndTime
	 MAX-ACCESS  read-write
	 STATUS  current
	 DESCRIPTION
		"Daily time we reset all the ppp upload packets counters."
         ::= { usrCip 64 }
	usrCipStatisticsResetPPPDownloadPackets    OBJECT-TYPE
	 SYNTAX  DateAndTime
	 MAX-ACCESS  read-write
	 STATUS  current
	 DESCRIPTION
		"Daily time we reset all the PPP download packets counters."
         ::= { usrCip 65 }
	usrCipStatisticsResetCallDisconnectReasons    OBJECT-TYPE
     SYNTAX      DateAndTime
	 MAX-ACCESS  read-write
	 STATUS  current
	 DESCRIPTION
		"Daily time we reset all the call disconnect reason counters."
         ::= { usrCip 66 }
	usrCipStatistics100PercentModemUtilization    OBJECT-TYPE
	 SYNTAX  Counter32
	 MAX-ACCESS  read-only
	 STATUS  current
	 DESCRIPTION
		" Number of minutes at modems 100 % utilization."
         ::= { usrCip 67 }
	usrCipModemCompressionStatisticsTable OBJECT-TYPE
           SYNTAX     SEQUENCE OF USRCIPModemCompressionStatisticsEntry
           MAX-ACCESS not-accessible
           STATUS     current
           DESCRIPTION
                 "The  table listing the Modem Compression statistics
                  for all the calls coming in."
           ::= { usrCip 68 }
    usrCipModemCompressionStatisticsEntry OBJECT-TYPE
           SYNTAX     USRCIPModemCompressionStatisticsEntry
           MAX-ACCESS not-accessible
           STATUS     current
           DESCRIPTION
                "CIP Modem Compression statistics"
           INDEX      { usrCipModemCompressionStatisticsIndex }
           ::= { usrCipModemCompressionStatisticsTable 1 }
    USRCIPModemCompressionStatisticsEntry ::= SEQUENCE {
           usrCipModemCompressionStatisticsIndex              Integer32,
           usrCipModemCompressionStatisticsModemCompNone      Counter32,
           usrCipModemCompressionStatisticsModemCompV42Bis    Counter32,
           usrCipModemCompressionStatisticsModemCompMnp5      Counter32,
           usrCipModemCompressionStatisticsResetTime          DateAndTime
		}
	 usrCipModemCompressionStatisticsIndex OBJECT-TYPE
           SYNTAX     Integer32
           MAX-ACCESS not-accessible
           STATUS     current
           DESCRIPTION
                 "The index for the Modem Compression statistics display.
                  they are 0-now& 1-total."
           ::= { usrCipModemCompressionStatisticsEntry 1 }
	usrCipModemCompressionStatisticsModemCompNone OBJECT-TYPE
           SYNTAX     Counter32
           MAX-ACCESS read-only
           STATUS     current
           DESCRIPTION
                 "The number of calls that has No Modem Compression."
           ::= { usrCipModemCompressionStatisticsEntry 2 }
	usrCipModemCompressionStatisticsModemCompV42Bis OBJECT-TYPE
           SYNTAX     Counter32
           MAX-ACCESS read-only
           STATUS     current
           DESCRIPTION
                 "The number of calls that has V_42Bis modem compression."
           ::= { usrCipModemCompressionStatisticsEntry 3 }
	usrCipModemCompressionStatisticsModemCompMnp5 OBJECT-TYPE
           SYNTAX     Counter32
           MAX-ACCESS read-only
           STATUS     current
           DESCRIPTION
                 "The number of calls that has mnp5 modem compression."
           ::= { usrCipModemCompressionStatisticsEntry 4 }
    usrCipModemCompressionStatisticsResetTime	OBJECT-TYPE
       SYNTAX	DateAndTime
	   MAX-ACCESS	read-write
	   STATUS	current
	   DESCRIPTION
		"Time the Speed statistics counters were last reset to value zero."
    ::= { usrCipModemCompressionStatisticsEntry 5 }
	usrCipTelnetConnectionTimeout  OBJECT-TYPE
         SYNTAX  Integer32
         MAX-ACCESS  read-write
         STATUS  current
         DESCRIPTION
             "For host rotation a configurable connection timeout"
     --CONFIGURABLE
         ::= { usrCip 71 }
    usrCipTelnetBuffering  OBJECT-TYPE
         SYNTAX  Integer32
         MAX-ACCESS  read-write
         STATUS  current
         DESCRIPTION
             "For a login user, whether CIP to TELNET buffering           
             should be turned on or off flag"
     --CONFIGURABLE
         ::= { usrCip 72 }
    usrCipPDSNAcctStyle OBJECT-TYPE
         SYNTAX  INTEGER {
		defaultPDSNStyle(1),
		emulateIWUStyle(2)
	 }
         MAX-ACCESS  read-write
         STATUS  current
         DESCRIPTION
             "This flag determines whether the PDSN emulates the IWU      
             while sending the interim accounting packets."
	 DEFVAL { defaultPDSNStyle }
     --CONFIGURABLE
         ::= { usrCip 77 }
    usrCipPppTotalReleases OBJECT-TYPE
         SYNTAX  Counter32
         MAX-ACCESS  read-only
         STATUS  current
         DESCRIPTION
	     "Count of PPP sessions which got released for any reason
	      after the PPP session was fully set up, i.e. has successfully
	      exited the IPCP stage and was in the operations stage and
	      then got released.  This counter was added for
	      Wireless IP to monitor PPP over the A10 R-P (Radio Node - PDSN)
	      link over which runs multiple PPP over GRE over IP."
         ::= { usrCip 78 }
    usrCipPppUserReleases OBJECT-TYPE
         SYNTAX  Counter32
         MAX-ACCESS  read-only
         STATUS  current
         DESCRIPTION
 	     "Count of PPP sessions which got released by the user
	      (LCP Term Req).  This counter was added for Wireless IP
	      to track the number of Mobile initiated releases  	
	      which occured after connection was fully setup, i.e. has
	      successfully exited the IPCP stage and was in the
	      operations stage, then was released."
         ::= { usrCip 79 }
    usrCipPppRpReleases OBJECT-TYPE
         SYNTAX  Counter32
         MAX-ACCESS  read-only
         STATUS  current
         DESCRIPTION
 	     "Count of PPP sessions which got released via the 3G R-P 
	      interface.
	      This counter was added for Wireless IP to track the number of 
	      RAN initiated releases which occured after the PPP connection
              was fully setup (after IPCP).  The RAN (Radio Access Node) aka
	      RN (Radio Node) aka RNN (Radio Network Node) aka PCF (Packet
     	      Communication Facility) initiates the release by de-registering
	      that mobile PPP connection by sending a Mobile-IP-like 
	      Registration Request with a lifetime of zero for that mobile
	      over the 3GPP2 A11 R-P interface.  Note that the PPP session
	      itself is carried over a GRE tunnel that forms the A10 portion 
	      of the 3GPP2 R-P interface."
         ::= { usrCip 80 }
    usrCipPppFaReleases OBJECT-TYPE
         SYNTAX  Counter32
         MAX-ACCESS  read-only
         STATUS  current
         DESCRIPTION
 	     "Count of PPP sessions which got released by request of
	      the FA (Mobile IP Foreign Agent) process in this PDSN.
	      This is only counted when the PPP session is fully setup,
	      i.e. has successfully exited the IPCP stage and was in the
	      operations stage, then was released."
         ::= { usrCip 81 }
    usrCipPppFacnReleases OBJECT-TYPE
         SYNTAX  Counter32
         MAX-ACCESS  read-only
         STATUS  current
         DESCRIPTION
 	     "Count of PPP sessions which got released by request of
	      the FACN (Foreign Agent Control Node).
	      This typically occurs when a handoff has occured for a
	      Mobile Station to another PDSN, and the FACN notifies us of
	      this fact so that the PPP resources can be released faster.
	      This is only counted when the PPP session is fully setup,
	      i.e. has successfully exited the IPCP stage and was in the
	      operations stage, then was released."
         ::= { usrCip 82 }
    usrCipPppLocalAdminReleases OBJECT-TYPE
         SYNTAX  Counter32
         MAX-ACCESS  read-only
         STATUS  current
         DESCRIPTION
 	     "Count of PPP sessions which got released by
	      a local administrative command.
	      This counter was added for Wireless IP to track the number of
	      PDSN initiated releases (Admin Command) which occured after the
	      PPP connection was fully setup (after successful IPCP)." 
         ::= { usrCip 83 }
    usrCipPppIdleTimeoutReleases OBJECT-TYPE
         SYNTAX  Counter32
         MAX-ACCESS  read-only
         STATUS  current
         DESCRIPTION
 	     "Count of PPP sessions which got released due to local Idle
	      Timeout.
	      This counter was added for Wireless IP to track the number of
	      PDSN initiated releases (Idle Timeout) which occured after the
	      PPP connection was fully setup (after successful IPCP)." 
         ::= { usrCip 84 }
    usrCipPppL2tpTunnelReleases OBJECT-TYPE
         SYNTAX  Counter32
         MAX-ACCESS  read-only
         STATUS  current
         DESCRIPTION
 	     "Count of PPP sessions which got released locally due to
	      attached an L2TP tunnel being released.
	      This counter was added for Wireless IP to track the number of
	      PDSN initiated releases (L2TP tunnel release) which occured 
	      after the L2TP connection was fully setup."
         ::= { usrCip 85 }
    usrCipPppInsufResourceReleases OBJECT-TYPE
         SYNTAX  Counter32
         MAX-ACCESS  read-only
         STATUS  obsolete
         DESCRIPTION
 	     "Count of PPP sessions which got released locally due to
	      insufficient resources.
	      This counter was added for Wireless IP to track the number of
	      PDSN initiated releases (Insufficient resources) which occured 
	      after the PPP connection was fully setup (successful IPCP).
          This unnecessary counter has been removed." 
         ::= { usrCip 86 }
    usrCipPppIngressFilteringReleases OBJECT-TYPE
         SYNTAX  Counter32
         MAX-ACCESS  read-only
         STATUS  current
         DESCRIPTION
 	     "Count of PPP sessions which got released locally due to
	      PPP renegotiations triggered by Ingress Filtering.
	      This counter was added for Wireless IP to track the number of
	      PDSN initiated releases (Ingress Filtering) which occured 
	      after the PPP connection was fully setup (successful IPCP)." 
         ::= { usrCip 87 }
    usrCipPppLocalMiscReleases OBJECT-TYPE
         SYNTAX  Counter32
         MAX-ACCESS  read-only
         STATUS  current
         DESCRIPTION
 	     "Count of PPP sessions which got released locally due to
	      miscellaneous other reasons not otherwise covered.
	      This counter was added for Wireless IP to track the number of
	      PDSN initiated releases (Miscellaneous Reason) which occured 
	      after the PPP connection was fully setup (successful IPCP)." 
         ::= { usrCip 88 }
     usrCipCallCurrentIs95cPppConns OBJECT-TYPE
         SYNTAX  Gauge32
         MAX-ACCESS  read-only
         STATUS  current
         DESCRIPTION
 	     "Number of Current Active IS-95C PPP Connections."
         ::= { usrCip 89 }
     usrCipCallActivePppConns OBJECT-TYPE
         SYNTAX  Gauge32
         MAX-ACCESS  read-only
         STATUS  current
         DESCRIPTION
 	     "Number of Active PPP Connections."
         ::= { usrCip 90 }
    usrCipShortTimeBillingSolnEnabled  OBJECT-TYPE
         SYNTAX  INTEGER {
                 enabled(1),
                 disabled(2)
             }
         MAX-ACCESS  read-write
         STATUS  current
         DESCRIPTION
             "This is the switch to enable/disable the Solution
              to Short Time Billing feature"
	 DEFVAL { disabled }
         --CONFIGURABLE
         ::= { usrCip 91 }
    usrCipShortTimeBillingSolnTimer  OBJECT-TYPE
         SYNTAX Integer32 (1..255)
         MAX-ACCESS  read-write
         STATUS  current
         DESCRIPTION
             "The value of the Short Term Billing Solution Timer"
	 DEFVAL { 5 }
         --CONFIGURABLE
         ::= { usrCip 92 }
END         -- End CIP-MIB definitions
-- ************************************************************************
--
--
--    usr_pppml.mib - The CommWorks PPP Mult-Link MIB module
--
-- Author:         <Joe Kralowetz>
--
