ACC-RIP DEFINITIONS ::= BEGIN

    IMPORTS
		OBJECT-TYPE, IpAddress, TimeTicks, Gauge, Counter FROM RFC1155-SMI
		TRAP-TYPE FROM RFC-1215
		ifIndex FROM RFC1213-MIB
       accTrapLogSeqNum FROM ACC-SYSTEM
accBRG, DisplayString, RowStatus, IfIndex, SmdsAddress
             FROM ACC-MIB;
    -- ACC RIP branch
    accRip      OBJECT IDENTIFIER ::= { accBRG 16 }
    accRipGeneral   OBJECT IDENTIFIER ::= { accRip 11 }
    accRipAdminStatus OBJECT-TYPE
        SYNTAX	INTEGER {
                    on(1),
                    off(2)
                }
        ACCESS  read-write
        STATUS  mandatory
        DESCRIPTION
             "Adminstrative status of RIP protocol.
              Extended causes subnet mask information to be included in
              RIP packets, permitting variable-length subnet masking."
        ::= { accRip 1 }
    accRipUpdateTimer OBJECT-TYPE
        SYNTAX  TimeTicks
        ACCESS  read-write
        STATUS  obsolete
        DESCRIPTION
             "This unit will send updates to its neighbors at the interval
              established by this timer.  Note that all other RIP timers
              are scaled off this value."
        ::= { accRip 2 }
    accRipGateway OBJECT-TYPE
        SYNTAX  INTEGER {
                    on(1),
                    off(2),
                    extended(3)
                }
        ACCESS  read-write
        STATUS  obsolete
        DESCRIPTION
             "Declares if the unit is the gateway unit for an AS.
              Indicates if the unit does or does not advertise that
              it is the default route.
              Extended mode causes EGP-derived information to be
              included in RIP packets."
        ::= { accRip 3 }
    accRipNeighborList OBJECT IDENTIFIER ::= { accRip 5 }
                -- A list of RIP neighbors.
                -- The instance of an entry is its IP address.
                -- To add an element, the VarBind of a SetRequest PDU will
                -- have both an object instance and value of accRipNeighbor.
                -- To delete an element, a SetRequest-PDU for the specific
                -- instance of accRipNeighbor with a NULL value encoding is
                -- used.
    accRipNeighbor OBJECT-TYPE
        SYNTAX	IpAddress
        ACCESS  read-write
        STATUS  obsolete
        DESCRIPTION
             "A neighbor to whom routing updates are sent,
              and from whom updates are accepted.
              RIP neighbors must be on the local network.
              In the case of an unnumbered link this object
              indicates the ifIndex of the link the neighbor
              is connected to."
        ::= { accRipNeighborList 1 }
    accRipNeighborIfindex OBJECT-TYPE
        SYNTAX  INTEGER
        ACCESS  read-only
        STATUS  obsolete
        DESCRIPTION
             "The ifIndex of the port this RIP neighbor is conected
              to. It is derived from the IP network table
              (accIpAddrTable). "
        ::= { accRipNeighborList 2 }
    accRipInCmdCnts OBJECT-TYPE
        SYNTAX  Counter
        ACCESS  read-only
        STATUS  obsolete
        DESCRIPTION
             "Number of RIP command packets successfully received."
        ::= { accRip 6 }
    accRipInRspCnts OBJECT-TYPE
        SYNTAX  Counter
        ACCESS  read-only
        STATUS  obsolete
        DESCRIPTION
             "Number of RIP response packets successfully received."
        ::= { accRip 7 }
    accRipInErrors OBJECT-TYPE
        SYNTAX  Counter
        ACCESS  read-only
        STATUS  obsolete
        DESCRIPTION
             "Number of RIP response and command packets received with
              errors.  Also includes count of packets that could
              not be handled due to internal errors."
        ::= { accRip 8 }
    accRipOutCmdCnts OBJECT-TYPE
        SYNTAX  Counter
        ACCESS  read-only
        STATUS  obsolete
        DESCRIPTION
             "Number of RIP command packets successfully transmitted."
        ::= { accRip 9 }
    accRipOutRspCounts OBJECT-TYPE
        SYNTAX  Counter
        ACCESS  read-only
        STATUS  obsolete
        DESCRIPTION
             "Number of RIP response packets successfully transmitted."
        ::= { accRip 10 }
    --
    --  RIP general parameters and information
    --
    accRipMessageLevel OBJECT-TYPE
        SYNTAX  INTEGER (1..7)
        ACCESS  read-write
        STATUS  mandatory
        DESCRIPTION
                 "The configured diagnostic level for RIP. Setting this value 
		  to 1 enables RIP to generate important diagnostic information. 
		  Increasing the value increases the diagnostic information. 
		  Level 7 is mostly informational."
	DEFVAL { 1 }
        ::= { accRipGeneral 1 }
    accRipDefaultVersion OBJECT-TYPE
        SYNTAX  INTEGER {
		    v1(1),
		    v2(2)
		}
        ACCESS  read-write
        STATUS  mandatory
        DESCRIPTION
	     "The default verison of RIP to use on new RIP interfaces."
	DEFVAL { v1 }
        ::= { accRipGeneral 2 }
    --
    --	Extensions to rfc1724 rip2IfConfTable
    --
    accRip2IfConfExtTable OBJECT-TYPE
        SYNTAX  	SEQUENCE OF AccRip2IfConfExtEntry 
        ACCESS  	not-accessible
        STATUS  	mandatory
        DESCRIPTION
            "An extension of the rip2IfConfTable."
    ::= { accRip 12 }
    accRip2IfConfExtEntry OBJECT-TYPE
        SYNTAX 		AccRip2IfConfExtEntry
        ACCESS 		not-accessible
        STATUS  	mandatory
        DESCRIPTION
             "Each entry in this table contains proprietary extensions to the
              rip2IfConfTable"
        INDEX   { accRip2IfConfExtAddress }
        ::= { accRip2IfConfExtTable 1 }
    AccRip2IfConfExtEntry ::=
        SEQUENCE {
            accRip2IfConfExtAddress		IpAddress,
            accRip2IfConfExtProfile		INTEGER,
            accRip2IfConfExtDefaultOnly		INTEGER,
            accRip2IfConfExtDefaultMetric	INTEGER,
            accRip2IfConfExtMessageLevel	INTEGER,
            accRip2IfConfExtAdminStat		INTEGER,
            accRip2IfConfExtTxOnly		INTEGER
        }
        accRip2IfConfExtAddress OBJECT-TYPE
            SYNTAX      IpAddress
            ACCESS      read-only
            STATUS      mandatory
            DESCRIPTION
                 "Same definition as rip2IfConfAddress."
            ::= { accRip2IfConfExtEntry 1 }
        accRip2IfConfExtProfile OBJECT-TYPE
            SYNTAX 	INTEGER (1..4)
            ACCESS 	read-write
            STATUS  	mandatory
            DESCRIPTION
                 "An index into the accRipProfileTable"
            DEFVAL { 1 }
            ::= { accRip2IfConfExtEntry 2 }
        accRip2IfConfExtDefaultOnly OBJECT-TYPE
            SYNTAX 	INTEGER {
        		    yes(1),
        		    no(2)
        		}
            ACCESS 	read-write
            STATUS  	mandatory
            DESCRIPTION
                 "Generate a default route only on this interface."
            DEFVAL { no }
            ::= { accRip2IfConfExtEntry 3 }
        accRip2IfConfExtDefaultMetric OBJECT-TYPE
            SYNTAX 	INTEGER (1..15)
            ACCESS 	read-write
            STATUS  	mandatory
            DESCRIPTION
                 "If generating a default route this is the metric that will
        	  be used in updates sent out this interface."
            DEFVAL { 1 }
            ::= { accRip2IfConfExtEntry 4 }
        accRip2IfConfExtMessageLevel OBJECT-TYPE
            SYNTAX 	INTEGER (1..7)
            ACCESS 	read-write
            STATUS  	mandatory
            DESCRIPTION
                 "The configured diagnostic level for this RIP interface. Setting this 
		  value to 1 will enable the interface to generate critical diagnostic 
		  information. Increasing the value increases the diagnostic information. 
		  Level 7 is mostly informational."
            DEFVAL { 1 }
            ::= { accRip2IfConfExtEntry 5 }
        accRip2IfConfExtAdminStat OBJECT-TYPE
            SYNTAX      INTEGER {
			    enabled(1),
			    disabled(2)
			}
            ACCESS      read-write
            STATUS      mandatory
            DESCRIPTION
                 "The administrative state of this RIP interface."
            DEFVAL { enabled }
            ::= { accRip2IfConfExtEntry 6 }
        accRip2IfConfExtTxOnly OBJECT-TYPE
            SYNTAX      INTEGER {
                            yes(1),
                            no(2)
			}
            ACCESS      read-write
            STATUS      mandatory
            DESCRIPTION
                 "Send RIP updates and ignore received updates on this interface."
            DEFVAL { no }
            ::= { accRip2IfConfExtEntry 7 }
        --
        --		The RIP Profile Table
        --
    accRipProfileTable OBJECT-TYPE
        SYNTAX  	SEQUENCE OF AccRipProfileEntry 
        ACCESS  	not-accessible
        STATUS  	mandatory
        DESCRIPTION
             "A table describing each of the RIP Profile groups."
        ::= { accRip 13 }
    accRipProfileEntry OBJECT-TYPE
        SYNTAX 	AccRipProfileEntry
        ACCESS 	not-accessible
        STATUS  	mandatory
        DESCRIPTION
             "Each entry in this table describes a Rip Profile Entry."
        INDEX   { accRipProfileId }
        ::= { accRipProfileTable 1 }
    AccRipProfileEntry ::=
        SEQUENCE {
            accRipProfileId		INTEGER,
            accRipProfileUpdateInterval	INTEGER,
            accRipProfilePacketGap	INTEGER,
            accRipProfileMaxPkts	INTEGER,
            accRipProfileRetxTO		INTEGER,
            accRipProfileShortPollRetries INTEGER,
            accRipProfileBackground     INTEGER,
            accRipProfileStatus         RowStatus
        }
        accRipProfileId OBJECT-TYPE
            SYNTAX 	INTEGER (1..4)
            ACCESS 	read-only
            STATUS  	mandatory
            DESCRIPTION
                 "The index into the accRipTimerGroupTable"
            ::= { accRipProfileEntry 1 }
        accRipProfileUpdateInterval OBJECT-TYPE
            SYNTAX 	INTEGER (5..3600)
            ACCESS 	read-write
            STATUS  	mandatory
            DESCRIPTION
                 "The periodic RIP update interval."
            DEFVAL { 30 }
            ::= { accRipProfileEntry 2 }
        accRipProfilePacketGap OBJECT-TYPE
            SYNTAX	INTEGER (0..100)
            ACCESS 	read-write
            STATUS  	mandatory
            DESCRIPTION
                 "The inter-packet gap between fragmented updates in
                  1/100's of a second."
            DEFVAL { 0 }
            ::= { accRipProfileEntry 3 }
        accRipProfileMaxPkts OBJECT-TYPE
            SYNTAX 	INTEGER (0..100)
            ACCESS 	read-write
            STATUS  	mandatory
            DESCRIPTION
                 "The maximum number of packets that can be issued during
                  any update burst."
            DEFVAL { 0 }
            ::= { accRipProfileEntry 4 }
        accRipProfileRetxTO OBJECT-TYPE
            SYNTAX 	INTEGER (1..30)
            ACCESS 	read-write
            STATUS  	mandatory
            DESCRIPTION
                 "The interval in seconds that RIP will wait before retransmitting
                  a triggered update (fragment)."
            DEFVAL { 5 }
            ::= { accRipProfileEntry 5 }
        accRipProfileShortPollRetries OBJECT-TYPE
            SYNTAX      INTEGER (0..120)
            ACCESS      read-write
            STATUS      mandatory
            DESCRIPTION
                 "The number of times RIP will retry to establish a non-responding
                  neighbor using the short poll interval (5 minutes) after the
                  neighbor has gone non-responding."
            DEFVAL { 10 }
            ::= { accRipProfileEntry 6 }
        accRipProfileBackground OBJECT-TYPE
            SYNTAX 	INTEGER (0..1440)
            ACCESS 	read-write
            STATUS  	mandatory
            DESCRIPTION
                 "The background poll interval that RIP will attempt to re-establish
                  a neighbor relationship."
            DEFVAL { 0 }
            ::= { accRipProfileEntry 7 }
        accRipProfileStatus OBJECT-TYPE
            SYNTAX      RowStatus
            ACCESS      read-write
            STATUS      mandatory
            DESCRIPTION
                 "The current status of this protocol entry."
            ::= { accRipProfileEntry 8 }
    --
    --          Obsoleted RIP Export Policy Table
    --
    -- 		{ accRip 14 }
    --
    --          The RIP Import Policy Table
    --
    --		{ accRip 15 }
    --
    --	The RIP Administrative Neighbor Table
    --
    accRipNbrTable OBJECT-TYPE
        SYNTAX  	SEQUENCE OF AccRipNbrEntry 
        ACCESS  	not-accessible
        STATUS  	mandatory
        DESCRIPTION
             "A table describing RIP neighbor relationships."
    ::= { accRip 16 }
    accRipNbrEntry OBJECT-TYPE
        SYNTAX 		AccRipNbrEntry
        ACCESS 		not-accessible
        STATUS  	mandatory
        DESCRIPTION
             "Each entry in this table describes a administratively
              configured RIP neighbor. Only the neighbors listed on
              a interface are listened toÕ."
        INDEX   { accRipNbrIpAddr }
        ::= { accRipNbrTable 1 }
    AccRipNbrEntry ::=
        SEQUENCE {
            accRipNbrIpAddr		IpAddress,
            accRipNbrTriggered          INTEGER,
            accRipNbrType          	INTEGER,
            accRipNbrStatus		RowStatus
        }
        accRipNbrIpAddr OBJECT-TYPE
            SYNTAX 	IpAddress
            ACCESS 	read-only
            STATUS  	mandatory
            DESCRIPTION
                 "The IP address of this system on the indicated subnet."
            ::= { accRipNbrEntry 1 }
        accRipNbrTriggered OBJECT-TYPE
            SYNTAX 	INTEGER {
                           yes(1),
                           no(4)
                        }
            ACCESS 	read-write
            STATUS  	mandatory
            DESCRIPTION
		 "Indicates the RIP neighbor is using triggered (on demand) RIP."
            DEFVAL { no }
            ::= { accRipNbrEntry 2 }
        accRipNbrType OBJECT-TYPE
            SYNTAX      INTEGER
            ACCESS      read-write
            STATUS      mandatory
            DESCRIPTION
                 "The ifIndex for the associated IP Interface. A non-zero valueindicates
                  that the interface is an unnumbered interface and ripNbrIfIpAddr has
                  the value of 0.0.0.0."
            ::= { accRipNbrEntry 3 }
        accRipNbrStatus OBJECT-TYPE
            SYNTAX 	RowStatus
            ACCESS 	read-write
            STATUS  	mandatory
            DESCRIPTION
                 "The current status of this protocol entry."
            ::= { accRipNbrEntry 4 }
    --
    --		Demand RIP Statistics
    --
    accDemandRipTable OBJECT-TYPE
        SYNTAX  	SEQUENCE OF AccDemandRipEntry 
        ACCESS  	not-accessible
        STATUS  	mandatory
        DESCRIPTION
             "This table contains information about demand RIP neighbors that
              have been either administratively configured or dynamically 
              learnt."
        ::= { accRip 17 }
    accDemandRipEntry OBJECT-TYPE
        SYNTAX 		AccDemandRipEntry
        ACCESS 		not-accessible
        STATUS  	mandatory
        DESCRIPTION
             "Each entry of this table represents a single demand RIP neighbor."
        INDEX   { accDemandRipNeighbor }
        ::= { accDemandRipTable 1 }
    AccDemandRipEntry ::=
        SEQUENCE {
            accDemandRipNeighbor                IpAddress,
            accDemandRipRetxTimeouts	        Gauge,
	    accDemandRipShortPollRetries	Gauge,
            accDemandRipBackGroundRetries       Gauge,
            accDemandRipTransitions             Counter,
	    accDemandRipSeqNumber		INTEGER, 
            accDemandRipStatus                  INTEGER
        }
        accDemandRipNeighbor OBJECT-TYPE
            SYNTAX 	IpAddress
            ACCESS 	read-only
            STATUS  	mandatory
            DESCRIPTION
                 "The RIP neighbors IP address. If this is an unnumbered link
                  then this object will represent the ifIndex of the interface."
            ::= { accDemandRipEntry 1 }
        accDemandRipRetxTimeouts OBJECT-TYPE
            SYNTAX  	Gauge
            ACCESS  	read-only
            STATUS 	mandatory
            DESCRIPTION
                 "The number of times a retransmit timeout has occurred on
                  a demand RIP interface."
            ::= { accDemandRipEntry 2 }
        accDemandRipShortPollRetries OBJECT-TYPE
            SYNTAX      Gauge
            ACCESS      read-only
            STATUS      mandatory
            DESCRIPTION
                 "The number of short poll retries to this neighbor."
            ::= { accDemandRipEntry 3 }
        accDemandRipBackGroundRetries OBJECT-TYPE
            SYNTAX      Gauge
            ACCESS      read-only
            STATUS      mandatory
            DESCRIPTION
                 "The number of background poll retries to this neighbor."
            ::= { accDemandRipEntry 4 }
        accDemandRipTransitions OBJECT-TYPE
            SYNTAX      Counter
            ACCESS      read-only
            STATUS      mandatory
            DESCRIPTION
                 "The number of times this neighbor has transitioned from
                  the Down state to an Up state."
            ::= { accDemandRipEntry 5 }
        accDemandRipSeqNumber OBJECT-TYPE
            SYNTAX      INTEGER
            ACCESS      read-only
            STATUS      mandatory
            DESCRIPTION
                 "The sequence number of the last received update."
            ::= { accDemandRipEntry 6 }
        accDemandRipStatus  OBJECT-TYPE
            SYNTAX 	INTEGER {
                            up(1),
                            down(2),
                            notResponding(3),
                            attempt(4),
                            exchange(5),
                            flushed(6)
                        }
            ACCESS 	read-only
            STATUS  	mandatory
            DESCRIPTION
                 "The current status of the demand RIP neighbor."
            ::= { accDemandRipEntry 7 }
    --
    --          The RIP Export Policy Table
    --
    accRipExportTable OBJECT-TYPE
        SYNTAX          SEQUENCE OF AccRipExportEntry
        ACCESS          not-accessible
        STATUS          mandatory
        DESCRIPTION
             "A table describing RIP export policies."
        ::= { accRip 18 }
    accRipExportEntry OBJECT-TYPE
        SYNTAX          AccRipExportEntry
        ACCESS          not-accessible
        STATUS          mandatory
        DESCRIPTION
             "Each entry in this table describes a administratively
              configured export policy."
        INDEX   { accRipExportProtocol, accRipExportProtoSpecific,
		  accRipExportNetwork, accRipExportMask,
		  accRipExportDestIf
		}
        ::= { accRipExportTable 1 }
    AccRipExportEntry ::=
        SEQUENCE {
            accRipExportProtocol        INTEGER,
            accRipExportProtoSpecific   INTEGER,
            accRipExportNetwork         IpAddress,
            accRipExportMask            IpAddress,
            accRipExportDestIf          IpAddress,
            accRipExportAction          INTEGER,
            accRipExportMetric          INTEGER,
            accRipExportStatus          RowStatus
        }
        accRipExportProtocol OBJECT-TYPE
            SYNTAX      INTEGER {
                           any(1),
                           local(2),
                           static(3),
                           iospf(4),
                           eospf(5),
                           rip(6),
                           ebgp(7),
                           ibgp(8)
                        }
            ACCESS      read-only
            STATUS      mandatory
            DESCRIPTION
                 "The routing protocol by which the route was learned."
            ::= { accRipExportEntry 1 }
        accRipExportProtoSpecific  OBJECT-TYPE
            SYNTAX      INTEGER
            ACCESS      read-only
            STATUS      mandatory
            DESCRIPTION
                 "Protocol dependant. Not currently used. Should always have an
                  instance value of zero."
            ::= { accRipExportEntry 2 }
        accRipExportNetwork OBJECT-TYPE
            SYNTAX      IpAddress
            ACCESS      read-only
            STATUS      mandatory
            DESCRIPTION
                 "The prefix to be used when matching policies. Routes are
                  logically anded with the policies mask and compared to this
                  prefix."
            ::= { accRipExportEntry 3 }
        accRipExportMask OBJECT-TYPE
            SYNTAX      IpAddress
            ACCESS      read-only
            STATUS      mandatory
            DESCRIPTION
                 "The mask to be used when matching policies."
            ::= { accRipExportEntry 4 }
        accRipExportDestIf OBJECT-TYPE
            SYNTAX      IpAddress
            ACCESS      read-only
            STATUS      mandatory
            DESCRIPTION
                 "The outbound interface for the update being created."
            ::= { accRipExportEntry 5 }
        accRipExportAction OBJECT-TYPE
            SYNTAX      INTEGER {
                         export(1),
                         block(2)
                        }
            ACCESS      read-write
            STATUS      mandatory
            DESCRIPTION
                 "Determines the policy taken on routes matching this
                  set of criteria."
            DEFVAL { export }
            ::= { accRipExportEntry 6 }
        accRipExportMetric OBJECT-TYPE
            SYNTAX      INTEGER (0..17)
            ACCESS      read-write
            STATUS      mandatory
            DESCRIPTION
                 "The metric that is to be used when exporting a route
                  into the routing domain on the outgoing interface. The
                  value 16 tells RIP to use the protocol owners metric.
                  Reading the value 17 means that this object is not used."
            DEFVAL { 16 }
            ::= { accRipExportEntry 7 }
        accRipExportStatus OBJECT-TYPE
            SYNTAX      RowStatus
            ACCESS      read-write
            STATUS      mandatory
            DESCRIPTION
                 "The current status of this protocol entry."
            ::= { accRipExportEntry 8 }
    --
    --          The RIP Import Policy Table
    --
    accRipImportTable OBJECT-TYPE
        SYNTAX          SEQUENCE OF AccRipImportEntry
        ACCESS          not-accessible
        STATUS          mandatory
        DESCRIPTION
             "A table describing RIP import policies."
        ::= { accRip 19 }
    accRipImportEntry OBJECT-TYPE
        SYNTAX          AccRipImportEntry
        ACCESS          not-accessible
        STATUS          mandatory
        DESCRIPTION
             "Each entry in this table describes a administratively
              configured import policy."
        INDEX   { accRipImportInterface, accRipImportPeerAddress,
		  accRipImportNetwork, accRipImportMask
		}
        ::= { accRipImportTable 1 }
    AccRipImportEntry ::=
        SEQUENCE {
            accRipImportInterface       IpAddress,
            accRipImportPeerAddress     IpAddress,
            accRipImportNetwork         IpAddress,
            accRipImportMask            IpAddress,
            accRipImportAction          INTEGER,
            accRipImportMetric          INTEGER,
            accRipImportPref            INTEGER,
            accRipImportStatus          RowStatus
        }
        accRipImportInterface  OBJECT-TYPE
            SYNTAX      IpAddress
            ACCESS      read-only
            STATUS      mandatory
            DESCRIPTION
                 "The interface from which the RIP update was received."
            ::= { accRipImportEntry 1 }
        accRipImportPeerAddress OBJECT-TYPE
            SYNTAX      IpAddress
            ACCESS      read-only
            STATUS      mandatory
            DESCRIPTION
                 "The RIP neighbors address."
            ::= { accRipImportEntry 2 }
        accRipImportNetwork OBJECT-TYPE
            SYNTAX      IpAddress
            ACCESS      read-only
            STATUS      mandatory
            DESCRIPTION
                 "The prefix to be used when matching policies. Routes are
                  logically anded with the policies mask and compared to this
                  prefix."
            ::= { accRipImportEntry 3 }
        accRipImportMask OBJECT-TYPE
            SYNTAX      IpAddress
            ACCESS      read-only
            STATUS      mandatory
            DESCRIPTION
                 "The mask to be used when matching policies."
            ::= { accRipImportEntry 4 }
        accRipImportAction OBJECT-TYPE
            SYNTAX      INTEGER {
                            import(1),
                            ignore(2)
                        }
            ACCESS      read-write
            STATUS      mandatory
            DESCRIPTION
                 "The action to take when a policy match occurs."
            ::= { accRipImportEntry 5 }
        accRipImportMetric OBJECT-TYPE
            SYNTAX      INTEGER (1..16)
            ACCESS      read-write
            STATUS      mandatory
            DESCRIPTION
                 "The metric that is to be used when importing a route
                  that has matched this policy. The value 16 tells RIP to
                  use the protocol owners metric."
            DEFVAL { 16 }
            ::= { accRipImportEntry 6 }
        accRipImportPref OBJECT-TYPE
            SYNTAX      INTEGER (1..255)
            ACCESS      read-write
            STATUS      mandatory
            DESCRIPTION
                 "The preference that RIP will assign to a
		  route matching this policy. The preference
		  is used to determine precedence between
		  other routing protocols that learn paths
		  to the same destination."
            DEFVAL { 16 }
            ::= { accRipImportEntry 7 }
        accRipImportStatus OBJECT-TYPE
            SYNTAX      RowStatus
            ACCESS      read-write
            STATUS      mandatory
            DESCRIPTION
                 "The current status of this protocol entry."
            ::= { accRipImportEntry 8 }
-- START CFG_TRAP_ENHANCEMENTS
-- rip traps
       accRipTraps OBJECT IDENTIFIER   ::= { accRip 20 }
       accRipTrapMsg   OBJECT-TYPE
        SYNTAX          DisplayString
        ACCESS          read-only
        STATUS          mandatory
        DESCRIPTION
                "Enterprise Trap Message for rip."
        ::= { accRipTraps 1 }
-- END MANILA 

       accRipFiltPolAllocTrap TRAP-TYPE
        ENTERPRISE       accRipTraps 
        VARIABLES       {accRipTrapMsg,
                         accRipImportInterface,
                         accRipImportPeerAddress,
                         accRipImportNetwork,
                         accRipImportMask ,
                          accTrapLogSeqNum}
        DESCRIPTION
                "Is due the memory shortage. This may mean that maximum 
		 number of filter policies were already allocated.
SEVERITY-DEFAULT: Warning 
EVENTTYPE-DEFAULT: 10 
ADDITIONAL-TEXT-VARIABLES: { accTrapLogSeqNum,accRipTrapMsg }
PCAUSE-DEFAULT: 32 " 
 
        ::= 1
       accRipFiltPolTrap TRAP-TYPE
        ENTERPRISE       accRipTraps 
        VARIABLES       {accRipTrapMsg,
                         accRipImportInterface,
                         accRipImportPeerAddress,
                         accRipImportNetwork,
                         accRipImportMask ,
                          accTrapLogSeqNum}
        DESCRIPTION
                "It happens when the user tries to delete a filter 
		 policy that doesnt exist.
SEVERITY-DEFAULT: Warning 
EVENTTYPE-DEFAULT: 10 
ADDITIONAL-TEXT-VARIABLES: { accTrapLogSeqNum,accRipTrapMsg }
PCAUSE-DEFAULT: 7 " 
 
        ::= 2
       accRipImpPolAllocTrap TRAP-TYPE
        ENTERPRISE       accRipTraps 
        VARIABLES       {accRipTrapMsg,
                         accRipExportMask,
                         accRipExportNetwork,
                         accRipExportProtocol,
                         accRipExportProtoSpecific,
                         accRipExportDestIf ,
                          accTrapLogSeqNum}
        DESCRIPTION
                "Is due the memory shortage. This may mean that maximum 
		 number of Import policies were already allocated.
SEVERITY-DEFAULT: Warning 
EVENTTYPE-DEFAULT: 10 
ADDITIONAL-TEXT-VARIABLES: { accTrapLogSeqNum,accRipTrapMsg }
PCAUSE-DEFAULT: 32 " 
 
        ::= 3
       accRipImpPolTrap TRAP-TYPE
        ENTERPRISE       accRipTraps 
        VARIABLES       {accRipTrapMsg,
                         accRipExportMask,
                         accRipExportNetwork, 
                         accRipExportProtocol,
                         accRipExportProtoSpecific,
                         accRipExportDestIf ,
                          accTrapLogSeqNum}
        DESCRIPTION
                "It happens when the user tries to delete an Import 
		 policy that doesnt exist.
SEVERITY-DEFAULT: Warning 
EVENTTYPE-DEFAULT: 10 
ADDITIONAL-TEXT-VARIABLES: { accTrapLogSeqNum,accRipTrapMsg }
PCAUSE-DEFAULT: 7 " 
 
        ::= 4
       accRipNbrTrap TRAP-TYPE
        ENTERPRISE       accRipTraps 
        VARIABLES       {accRipTrapMsg,
                         accRipNbrIpAddr,
                         accRip2IfConfExtAddress ,
                          accTrapLogSeqNum}
        DESCRIPTION
                "The rip neighbor address entered by the user is 
		 unreachable.
SEVERITY-DEFAULT: Warning 
EVENTTYPE-DEFAULT: 10 
ADDITIONAL-TEXT-VARIABLES: { accTrapLogSeqNum,accRipTrapMsg }
PCAUSE-DEFAULT: 7 " 
 
        ::= 5
       accRipNbrIncompatTrap TRAP-TYPE
        ENTERPRISE       accRipTraps 
        VARIABLES       {accRipTrapMsg,
                         accRipNbrIpAddr,
                         accRip2IfConfExtAddress ,
                          accTrapLogSeqNum}
        DESCRIPTION
                "This is due the fact that either Unumbered Ip 
		 Neighbor is on a Numbered Link or vice versa.
SEVERITY-DEFAULT: Warning 
EVENTTYPE-DEFAULT: 10 
ADDITIONAL-TEXT-VARIABLES: { accTrapLogSeqNum,accRipTrapMsg }
PCAUSE-DEFAULT: 7 " 
 
        ::= 6
       accRipDefProfTrap TRAP-TYPE
        ENTERPRISE       accRipTraps 
        VARIABLES       {accRipTrapMsg,
                         accRipProfileId ,
                          accTrapLogSeqNum}
        DESCRIPTION
                "User tried to delete default profile. Default profile 
		 entry cant be deleted.
SEVERITY-DEFAULT: Warning 
EVENTTYPE-DEFAULT: 10 
ADDITIONAL-TEXT-VARIABLES: { accTrapLogSeqNum,accRipTrapMsg }
PCAUSE-DEFAULT: 7 " 
 
        ::= 7
       accRipProfUsedByIntfTrap TRAP-TYPE
        ENTERPRISE       accRipTraps 
        VARIABLES       {accRipTrapMsg,
                         accRipProfileId,
                         ifIndex,
                         accRip2IfConfExtAddress ,
                          accTrapLogSeqNum}
        DESCRIPTION
                "User can delete only if the profile is not being used.
SEVERITY-DEFAULT: Warning 
EVENTTYPE-DEFAULT: 10 
ADDITIONAL-TEXT-VARIABLES: { accTrapLogSeqNum,accRipTrapMsg }
PCAUSE-DEFAULT: 7 " 
 
        ::= 8
       accRipMustBeDisbldTrap TRAP-TYPE
        ENTERPRISE       accRipTraps 
        VARIABLES       {accRipTrapMsg,
                         accRipAdminStatus ,
                          accTrapLogSeqNum}
        DESCRIPTION
                "Can change profiles only if RIP disabled.
SEVERITY-DEFAULT: Warning 
EVENTTYPE-DEFAULT: 10 
ADDITIONAL-TEXT-VARIABLES: { accTrapLogSeqNum,accRipTrapMsg }
PCAUSE-DEFAULT: 7 " 
 
        ::= 9
       accRipUpdateIntTrap TRAP-TYPE
        ENTERPRISE       accRipTraps 
        VARIABLES       {accRipTrapMsg,
                         accRipProfileId ,
                          accTrapLogSeqNum}
        DESCRIPTION
                "Occurs when the number of routes that RIP must send 
		 in the updates out an interface causes the ppu value 
		 and inter-packet gap to exceed the RIP update interval 
		 of the iterface. To rectify this, either shorten the 
		 inter-packet interval or increase the number of 
		 packets-per-update. Another solution is to reduce the 
		 number of routes sent out the interface by implementing 
		 policy or aggregation.
SEVERITY-DEFAULT: Major 
EVENTTYPE-DEFAULT: 10 
ADDITIONAL-TEXT-VARIABLES: { accTrapLogSeqNum,accRipTrapMsg }
PCAUSE-DEFAULT: 8 " 
 
        ::= 10
       accRipInitNbrTrap TRAP-TYPE
        ENTERPRISE       accRipTraps 
        VARIABLES       {accRipTrapMsg,
                         accRipNbrIpAddr ,
                          accTrapLogSeqNum}
        DESCRIPTION
                "Failed initializing the neighbor due to the memory 
		 shortage encoutered in allocating memory for either 
		 the trigger timer for the group or for the structure 
		 to hold Neighbors triggered RIP related information.
SEVERITY-DEFAULT: Major 
EVENTTYPE-DEFAULT: 10 
ADDITIONAL-TEXT-VARIABLES: { accTrapLogSeqNum,accRipTrapMsg }
PCAUSE-DEFAULT: 32 " 
 
        ::= 11
       accRipNbrAvlInsrtTrap TRAP-TYPE
        ENTERPRISE       accRipTraps 
        VARIABLES       {accRipTrapMsg,
                         accRipNbrIpAddr ,
                          accTrapLogSeqNum}
        DESCRIPTION
                "Is due the memory shortage. This trap is while creating 
		 a neighbor strucutre for the RIP interface.
SEVERITY-DEFAULT: Major 
EVENTTYPE-DEFAULT: 10 
ADDITIONAL-TEXT-VARIABLES: { accTrapLogSeqNum,accRipTrapMsg }
PCAUSE-DEFAULT: 32 " 
 
        ::= 12
       accRipRtNotifIdTrap TRAP-TYPE
        ENTERPRISE       accRipTraps 
        VARIABLES       {accRipTrapMsg,
                         accRipNbrIpAddr ,
                          accTrapLogSeqNum}
        DESCRIPTION
                "This is a NBMA interface and it is up. Trap occured 
		 while acquiring cl_id for this neighbor.
SEVERITY-DEFAULT: Warning 
EVENTTYPE-DEFAULT: 10 
ADDITIONAL-TEXT-VARIABLES: { accTrapLogSeqNum,accRipTrapMsg }
PCAUSE-DEFAULT: 0 " 
 
        ::= 13 
       accRipNbrNxtHopMemTrap TRAP-TYPE
        ENTERPRISE       accRipTraps 
        VARIABLES       {accRipTrapMsg ,
                          accTrapLogSeqNum}
        DESCRIPTION
                " 
SEVERITY-DEFAULT: Major 
EVENTTYPE-DEFAULT: 10 
ADDITIONAL-TEXT-VARIABLES: { accTrapLogSeqNum,accRipTrapMsg }
PCAUSE-DEFAULT: 32 " 
 
        ::= 14
       accRipNoIntfMemTrap TRAP-TYPE
        ENTERPRISE       accRipTraps 
        VARIABLES       {accRipTrapMsg,
                         accRipDefaultVersion,
                         accRip2IfConfExtAddress ,
                          accTrapLogSeqNum}
        DESCRIPTION
                "No memory for RIP interface.
SEVERITY-DEFAULT: Major 
EVENTTYPE-DEFAULT: 10 
ADDITIONAL-TEXT-VARIABLES: { accTrapLogSeqNum,accRipTrapMsg }
PCAUSE-DEFAULT: 32 " 
 
        ::= 15
       accRipAddNbrRtTrap TRAP-TYPE
        ENTERPRISE       accRipTraps 
        VARIABLES       {accRipTrapMsg,
                         accRipNbrIpAddr ,
                          accTrapLogSeqNum}
        DESCRIPTION
                "Add nbr route faild due to the memory shortage.
SEVERITY-DEFAULT: Major 
EVENTTYPE-DEFAULT: 10 
ADDITIONAL-TEXT-VARIABLES: { accTrapLogSeqNum,accRipTrapMsg }
PCAUSE-DEFAULT: 32 " 
 
        ::= 16
       accRipMaxIntfGrpTrap TRAP-TYPE
        ENTERPRISE       accRipTraps 
        VARIABLES       {accRipTrapMsg ,
                          accTrapLogSeqNum}
        DESCRIPTION
                "The number of different interface groups is limited 
		 to the constant by RIP_MAX_INTF_GROUPS.
SEVERITY-DEFAULT: Warning 
EVENTTYPE-DEFAULT: 10 
ADDITIONAL-TEXT-VARIABLES: { accTrapLogSeqNum,accRipTrapMsg }
PCAUSE-DEFAULT: 7 " 
 
        ::= 17
       accRipMemReqTrap TRAP-TYPE
        ENTERPRISE       accRipTraps 
        VARIABLES       {accRipTrapMsg ,
                          accTrapLogSeqNum}
        DESCRIPTION
                "Memory request failure.
SEVERITY-DEFAULT: Major 
EVENTTYPE-DEFAULT: 10 
ADDITIONAL-TEXT-VARIABLES: { accTrapLogSeqNum,accRipTrapMsg }
PCAUSE-DEFAULT: 32 " 
 
        ::= 18
       accRipUpdateEvntHndlrTrap TRAP-TYPE
        ENTERPRISE       accRipTraps 
        VARIABLES       {accRipTrapMsg,
                         accRipProfileId ,
                          accTrapLogSeqNum}
        DESCRIPTION
                "Is due the memory shortage. It is while creating 
		 update timer.
SEVERITY-DEFAULT: Major 
EVENTTYPE-DEFAULT: 10 
ADDITIONAL-TEXT-VARIABLES: { accTrapLogSeqNum,accRipTrapMsg }
PCAUSE-DEFAULT: 32 " 
 
        ::= 19
       accRipIntfLnkUpTrap TRAP-TYPE
        ENTERPRISE       accRipTraps 
        VARIABLES       {accRipTrapMsg,
                         accRip2IfConfExtAddress,
                         ifIndex ,
accTrapLogSeqNum}
        DESCRIPTION
       		"Is due the memory shortage. It is while creating 
		 update timer.
SEVERITY-DEFAULT: Major 
EVENTTYPE-DEFAULT: 10 
ADDITIONAL-TEXT-VARIABLES: { accTrapLogSeqNum,accRipTrapMsg }
PCAUSE-DEFAULT: 32 " 
 
        ::= 20
       accRipEnableTrap TRAP-TYPE
        ENTERPRISE       accRipTraps 
        VARIABLES       {accRipTrapMsg,
                         accRipDefaultVersion,
                         accRip2IfConfExtAddress ,
                          accTrapLogSeqNum}
        DESCRIPTION
                "This is when enabling the RIP interface is failed 
		 which is due to either Insufficient info or rip 
		 interface group not bound.
SEVERITY-DEFAULT: Major 
EVENTTYPE-DEFAULT: 10 
ADDITIONAL-TEXT-VARIABLES: { accTrapLogSeqNum,accRipTrapMsg }
PCAUSE-DEFAULT: 7 " 
 
        ::= 21
       accRipInitFiltPolTrap TRAP-TYPE
        ENTERPRISE       accRipTraps 
        VARIABLES       {accRipTrapMsg ,
                          accTrapLogSeqNum}
        DESCRIPTION
                "Failed initializing nbr  due to memory shortage.
SEVERITY-DEFAULT: Major 
EVENTTYPE-DEFAULT: 10 
ADDITIONAL-TEXT-VARIABLES: { accTrapLogSeqNum,accRipTrapMsg }
PCAUSE-DEFAULT: 32 " 
 
        ::= 22
       accRipInitImpPolTrap TRAP-TYPE
        ENTERPRISE       accRipTraps 
        VARIABLES       {accRipTrapMsg ,
                          accTrapLogSeqNum}
        DESCRIPTION
                "Indicates that the function rip_mgr_init_import_policy 
		 returned FALSE.
SEVERITY-DEFAULT: Warning 
EVENTTYPE-DEFAULT: 10 
ADDITIONAL-TEXT-VARIABLES: { accTrapLogSeqNum,accRipTrapMsg }
PCAUSE-DEFAULT: 7 " 
 
        ::= 23
       accRipNoNotifIdTrap TRAP-TYPE
        ENTERPRISE       accRipTraps 
        VARIABLES       {accRipTrapMsg,
                         accRipNbrIpAddr ,
                          accTrapLogSeqNum}
        DESCRIPTION
                "Each instance of a routing protocol or the IP instance 
		 itself has a bit in the RTH for a change list entry. 
		 The trap indicates that it is due to the inability of 
		 getting bit offset in this field which is reserved for 
		 it in each rt_head in the routing table.
SEVERITY-DEFAULT: Major 
EVENTTYPE-DEFAULT: 10 
ADDITIONAL-TEXT-VARIABLES: { accTrapLogSeqNum,accRipTrapMsg }
PCAUSE-DEFAULT: 152 " 
 
        ::= 24
       accRipMaxReTxTrap TRAP-TYPE
        ENTERPRISE       accRipTraps 
        VARIABLES       {accRipTrapMsg,
                         accRipNbrIpAddr ,
                          accTrapLogSeqNum}
        DESCRIPTION
                "Retransmission reaches its limit .max_retransmission 
		 period is defined in the profile group.
SEVERITY-DEFAULT: Minor 
EVENTTYPE-DEFAULT: 10 
ADDITIONAL-TEXT-VARIABLES: { accTrapLogSeqNum,accRipTrapMsg }
PCAUSE-DEFAULT: 7 " 
 
        ::= 25
END
