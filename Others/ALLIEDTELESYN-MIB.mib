-- ATRouter Private MIB Version 1.04  30/Aug/99
-- Private MIB for AR series Remote Access Router

ALLIEDTELESYN-MIB DEFINITIONS ::= BEGIN

        IMPORTS
           enterprises, IpAddress,
           Counter, TimeTicks
                FROM RFC1155-SMI
           DisplayString, PhysAddress
                FROM RFC1213-MIB
           TRAP-TYPE
                FROM RFC-1215
           OBJECT-TYPE
                FROM RFC-1212
				InterfaceIndex FROM IF-MIB;

--  Textual convention for an interface index type which may not reference an actual member of ifTable, in which case the value
--  zero should be used.
	InterfaceIndexOrZero ::= INTEGER (0..2147483647)

        -- define the top of the alliedTelesyn MIB.

        alliedTelesyn            OBJECT IDENTIFIER ::= { enterprises 207 }
        products                 OBJECT IDENTIFIER ::= { alliedTelesyn 1 }
        mibObject                OBJECT IDENTIFIER ::= { alliedTelesyn 8 }

        bridgeRouter             OBJECT IDENTIFIER ::= { products 1 }
        centreCOM-AR300Router    OBJECT IDENTIFIER ::= { bridgeRouter 8 }
        centreCOM-AR720Router    OBJECT IDENTIFIER ::= { bridgeRouter 11 }
        centreCOM-AR300LRouter   OBJECT IDENTIFIER ::= { bridgeRouter 12 }
        centreCOM-AR310Router    OBJECT IDENTIFIER ::= { bridgeRouter 13 }
        centreCOM-AR300LURouter  OBJECT IDENTIFIER ::= { bridgeRouter 14 }
        centreCOM-AR300URouter   OBJECT IDENTIFIER ::= { bridgeRouter 15 }
        centreCOM-AR310URouter   OBJECT IDENTIFIER ::= { bridgeRouter 16 }
        centreCOM-AR350Router    OBJECT IDENTIFIER ::= { bridgeRouter 17 }
        centreCOM-AR370Router    OBJECT IDENTIFIER ::= { bridgeRouter 18 }
        centreCOM-AR330Router    OBJECT IDENTIFIER ::= { bridgeRouter 19 }
        centreCOM-AR395Router    OBJECT IDENTIFIER ::= { bridgeRouter 20 }
        centreCOM-AR390Router    OBJECT IDENTIFIER ::= { bridgeRouter 21 }
        centreCOM-AR370URouter   OBJECT IDENTIFIER ::= { bridgeRouter 22 }
    

        brouterMib               OBJECT IDENTIFIER ::= { mibObject 4 }
        atRouter                 OBJECT IDENTIFIER ::= { brouterMib 4 }
 
    -- groups in ATROUTER

    objects     OBJECT IDENTIFIER ::= { atRouter 1 }

    traps       OBJECT IDENTIFIER ::= { atRouter 2 }

    sysinfo     OBJECT IDENTIFIER ::= { atRouter 3 }

    modules     OBJECT IDENTIFIER ::= { atRouter 4 }

    arInterfaces  OBJECT IDENTIFIER ::= { atRouter 5 }
--  this used to be interfaces, but this clashes with interfaces group in MIB-II

    protocols   OBJECT IDENTIFIER ::= { atRouter 6 }

    -- objects for AT router

    boards      OBJECT IDENTIFIER ::= { objects 1 }

    ppr-icm-ar023           OBJECT IDENTIFIER ::= { boards 39 }
    ppr-icm-ar021           OBJECT IDENTIFIER ::= { boards 40 }
    ppr-icm-ar022           OBJECT IDENTIFIER ::= { boards 41 }
    ppr-icm-ar025           OBJECT IDENTIFIER ::= { boards 45 }
    ppr-icm-ar024           OBJECT IDENTIFIER ::= { boards 46 }
    ppr-ar300               OBJECT IDENTIFIER ::= { boards 49 }
    ppr-ar300L              OBJECT IDENTIFIER ::= { boards 52 }
    ppr-ar310               OBJECT IDENTIFIER ::= { boards 53 }
    ppr-ar300Lu             OBJECT IDENTIFIER ::= { boards 55 }
    ppr-ar300u              OBJECT IDENTIFIER ::= { boards 56 }
    ppr-ar310u              OBJECT IDENTIFIER ::= { boards 57 }
    ppr-ar350               OBJECT IDENTIFIER ::= { boards 58 }
    ppr-ar720               OBJECT IDENTIFIER ::= { boards 63 } 
    ppr-ar010               OBJECT IDENTIFIER ::= { boards 67 }
    ppr-ar012               OBJECT IDENTIFIER ::= { boards 68 }
    ppr-ar011               OBJECT IDENTIFIER ::= { boards 69 }
    ppr-ar370               OBJECT IDENTIFIER ::= { boards 70 }
    ppr-ar330               OBJECT IDENTIFIER ::= { boards 71 }
    ppr-ar395               OBJECT IDENTIFIER ::= { boards 72 }
    ppr-ar390               OBJECT IDENTIFIER ::= { boards 73 }
    ppr-ar370u              OBJECT IDENTIFIER ::= { boards 75 }
    ppr-icm-ar020           OBJECT IDENTIFIER ::= { boards 76 }

    release     OBJECT IDENTIFIER ::= { objects 2 }

    iftypes     OBJECT IDENTIFIER ::= { objects 3 }

    iface-eth       OBJECT IDENTIFIER ::= { iftypes 1 }
    iface-syn       OBJECT IDENTIFIER ::= { iftypes 2 }
    iface-asyn      OBJECT IDENTIFIER ::= { iftypes 3 }
    iface-bri       OBJECT IDENTIFIER ::= { iftypes 4 }
    iface-pri       OBJECT IDENTIFIER ::= { iftypes 5 }
    iface-pots      OBJECT IDENTIFIER ::= { iftypes 6 }

    chips       OBJECT IDENTIFIER ::= { objects 4 }

    chip-68020-cpu      OBJECT IDENTIFIER ::= { chips 1 }
    chip-68340-cpu      OBJECT IDENTIFIER ::= { chips 2 }
    chip-68302-cpu      OBJECT IDENTIFIER ::= { chips 3 }
    chip-68360-cpu      OBJECT IDENTIFIER ::= { chips 4 }
    chip-860T-cpu       OBJECT IDENTIFIER ::= { chips 5 }
    chip-rtc1           OBJECT IDENTIFIER ::= { chips 21 }
    chip-rtc2           OBJECT IDENTIFIER ::= { chips 22 }
    chip-rtc3           OBJECT IDENTIFIER ::= { chips 23 }
    chip-rtc4           OBJECT IDENTIFIER ::= { chips 24 }
    chip-ram-1mb        OBJECT IDENTIFIER ::= { chips 31 }
    chip-ram-2mb        OBJECT IDENTIFIER ::= { chips 32 }
    chip-ram-3mb        OBJECT IDENTIFIER ::= { chips 33 }
    chip-ram-4mb        OBJECT IDENTIFIER ::= { chips 34 }
    chip-ram-6mb        OBJECT IDENTIFIER ::= { chips 36 }
    chip-ram-8mb        OBJECT IDENTIFIER ::= { chips 38 }
    chip-ram-12mb       OBJECT IDENTIFIER ::= { chips 42 }
    chip-ram-16mb       OBJECT IDENTIFIER ::= { chips 46 }
    chip-ram-20mb       OBJECT IDENTIFIER ::= { chips 50 }
    chip-ram-32mb       OBJECT IDENTIFIER ::= { chips 62 }
    chip-flash-1mb      OBJECT IDENTIFIER ::= { chips 71 }
    chip-flash-2mb      OBJECT IDENTIFIER ::= { chips 72 }
    chip-flash-3mb      OBJECT IDENTIFIER ::= { chips 73 }
    chip-flash-4mb      OBJECT IDENTIFIER ::= { chips 74 }
    chip-flash-6mb      OBJECT IDENTIFIER ::= { chips 76 }
    chip-flash-8mb      OBJECT IDENTIFIER ::= { chips 78 }
    chip-pem            OBJECT IDENTIFIER ::= { chips 120 }

--  Router interfaces tables.

--  A router consists of a number of "boards". Each board may have a
--  number of "positions", each of which contains a single router
--  interface. Each boards may also have a number of "slots", which are
--  places which can take other boards. Thus the physical construction
--  of a router may be seen as a tree whose nodes are boards and
--  interfaces, and whose links are positions and slots.
--  For example, an AR720 with a single Ethernet ICM in Bay 1 has the
--  following tree:
--  Bd:AR720 base board
--           === P1 === Int: Asyn0
--           === P2 === Int: Asyn1
--           === P3 === Int: Eth0
--           === S1 (Bay0) === <empty>
--           === S2 (Bay1) === Bd:Ethernet ICM === P1 === Int: Eth1
--           === S3 (MAC) === <empty>
--  The function of the interface MIB tables is to represent this tree
--  and to map elements in this tree to other MIB variables. Note that
--  any given board has a fixed configuration of positions and slots,
--  it is what is contained in the slots that give different hardware
--  configurations.

--	The highest index of boards in this router. Boards will have indices
--  from 1 to the value of this object. There may be gaps in the
--  sequence if the router has hot-swap capability. If the router has no
--  hot-swap capability, or no swapping has taken place since boot, the
--  sequence of boards will have no gaps.

    arBoardMaxIndex OBJECT-TYPE
        SYNTAX  INTEGER
        ACCESS  read-only
        STATUS  mandatory
        DESCRIPTION
                "The maximum index of boards in the board table. Index 1
                is reserved for the main system board of the router."
        ::= { arInterfaces 1 }

--  Router boards table. This table describes all of the physical boards
--  present in this router. A board is defined as a separate circuit
--  board with its own serial number.

    arBoardTable OBJECT-TYPE
        SYNTAX  SEQUENCE OF ArBoardEntry
        ACCESS  not-accessible
        STATUS  mandatory
        DESCRIPTION
                "The table of boards in the AR router."
        ::= { arInterfaces 2 }

    arBoardEntry OBJECT-TYPE
        SYNTAX  ArBoardEntry
        ACCESS  not-accessible
        STATUS  mandatory
        DESCRIPTION
                "A single entry in the board table. Each entry consists
                of information about one board in the router."
        INDEX   { arBoardIndex }
        ::= { arBoardTable 1 }

    ArBoardEntry ::=
        SEQUENCE {
            arBoardIndex
                INTEGER,
            arBoardId
                OBJECT IDENTIFIER,
            arBoardName
                DisplayString,
            arBoardRevision
                DisplayString,
            arBoardSerialNumber
                DisplayString,
            arBoardTotalSlots
                INTEGER,
			arBoardTotalPositions
				INTEGER
        }

    arBoardIndex OBJECT-TYPE
        SYNTAX  INTEGER
        ACCESS  read-only
        STATUS  mandatory
        DESCRIPTION
                "The index of the board in the board table. Index 1 is
                reserved for the main system board of the router. Other
                boards will take index numbers as they are initialised
                at router startup, or for routers with hot-swap
                capability, as boards are added to and removed from the
                router."
        ::= { arBoardEntry 1 }

    arBoardId OBJECT-TYPE
        SYNTAX  OBJECT IDENTIFIER
        ACCESS  read-only
        STATUS  mandatory
        DESCRIPTION
                "The type of board in this board entry. The values of
                this object are taken from the ppr-xxx object IDs under
                the boards sub-tree."
       ::= { arBoardEntry 2 }

    arBoardName OBJECT-TYPE
        SYNTAX  DisplayString (SIZE(0..255))
        ACCESS  read-only
        STATUS  mandatory
        DESCRIPTION
                "The name of the board in this board entry. This is a
                readable string which identifies the board to the
                manager."
        ::= { arBoardEntry 3 }

    arBoardRevision OBJECT-TYPE
        SYNTAX  DisplayString (SIZE(0..255))
        ACCESS  read-only
        STATUS  mandatory
        DESCRIPTION
                "The manufacturing revision of the board in this board
                entry. This string has the format Xm-n, where X is P for
                prototype, or M for manufacturing, m is the major
                revision number for this board, and n is the field
                upgrade revision number for this board."
        ::= { arBoardEntry 4 }

    arBoardSerialNumber OBJECT-TYPE
        SYNTAX  DisplayString (SIZE(0..255))
        ACCESS  read-only
        STATUS  mandatory
        DESCRIPTION
                "The serial number of the board in this board entry.
                Serial numbers are strings of decimal numbers up to 10
                digits in length. Each and every serial number is
                globally unique. It is possible for the serial number of
                a board to be invalid. In this case the value returned
                for this object will be '*** Invalid ***'"
        ::= { arBoardEntry 5 }

    arBoardTotalSlots OBJECT-TYPE
        SYNTAX  INTEGER
        ACCESS  read-only
        STATUS  mandatory
        DESCRIPTION
                "The number of slots on this board. Each slot from 1 to
                the value of this object may be empty or occupied by
                another board. By searching the arSlotTable with this
                board's board index and all values of slot index from 1
                to the value of this object, a tree of the boards in
                this router can be built. The value 0 for this object
                means that it has no slots."
        ::= { arBoardEntry 6 }

    arBoardTotalPositions OBJECT-TYPE
        SYNTAX  INTEGER
        ACCESS  read-only
        STATUS  mandatory
        DESCRIPTION
                "The number of positions on this board. Each position
                from 1 to the value of this object contains a single
                router interface. Note that positions are different from
                slots. An position contains an actual interface while a
                slot contains a different board which itself may contain
                interfaces in its positions."
        ::= { arBoardEntry 7 }


--  Router board slot table. This table is indexed by board index and
--  slot index and gives the board index of the board occupying the
--  given slot in the given board.

    arSlotTable OBJECT-TYPE
        SYNTAX  SEQUENCE OF ArSlotEntry
        ACCESS  not-accessible
        STATUS  mandatory
        DESCRIPTION
                "The table of slots in the router, indexed by board
                index and slot index."
        ::= { arInterfaces 3 }

    arSlotEntry OBJECT-TYPE
        SYNTAX  ArSlotEntry
        ACCESS  not-accessible
        STATUS  mandatory
        DESCRIPTION
                "A single entry in the board slot table."
        INDEX   { arSlotBoardIndex, arSlotSlotIndex }
        ::= { arSlotTable 1 }

    ArSlotEntry ::=
        SEQUENCE {
            arSlotBoardIndex
                INTEGER,
            arSlotSlotIndex
                INTEGER,
            arSlotHeldBoardIndex
                INTEGER,
            arSlotDescription
                INTEGER
        }

    arSlotBoardIndex OBJECT-TYPE
        SYNTAX  INTEGER
        ACCESS  read-only
        STATUS  mandatory
        DESCRIPTION
                "The index of the board for this slot entry. Index 1 is
                reserved for the main system board of the router."
        ::= { arSlotEntry 1 }

    arSlotSlotIndex OBJECT-TYPE
        SYNTAX  INTEGER
        ACCESS  read-only
        STATUS  mandatory
        DESCRIPTION
                "The index of the slot for this slot entry. Indices
                start from 1 and are specific to each different board
                type. There are no gaps in the sequence of slot indices.
                The maximum value for slot index is given by the value
                of arBoardTotalSlots for this board."
        ::= { arSlotEntry 2 }

    arSlotHeldBoardIndex OBJECT-TYPE
        SYNTAX  INTEGER
        ACCESS  read-only
        STATUS  mandatory
        DESCRIPTION
                "The index of the board held in the slot for this slot
                entry. This is an index into the arBoardTable. A value
                of 0 for this object means that the slot is not
                populated."
        ::= { arSlotEntry 3 }

    arSlotDescription OBJECT-TYPE
        SYNTAX  DisplayString (SIZE(0..255))
        ACCESS  read-only
        STATUS  mandatory
        DESCRIPTION
                "A description for this slot entry. This is a textual
                description which gives the manager a clue as to what
                the slot for this entry is. For example, the slots on an
                AR 720 have descriptions 'Bay0', 'Bay1' and 'MAC'."
        ::= { arSlotEntry 4 }

--  Router interfaces table. This table has an entry for each physical
--  interface on the router. The indices for this table are the router
--  board index and a board position index.

    arInterfaceTable OBJECT-TYPE
        SYNTAX  SEQUENCE OF ArInterfaceEntry
        ACCESS  not-accessible
        STATUS  mandatory
        DESCRIPTION
                "The table of physical interfaces in the AR router."
        ::= { arInterfaces 4 }

    arInterfaceEntry OBJECT-TYPE
        SYNTAX  ArInterfaceEntry
        ACCESS  not-accessible
        STATUS  mandatory
        DESCRIPTION
                "A single entry in the interface table. Each entry consists of
                information about one interface in the router, and is indexed
                by the board index and the position of the interface on the
                board."
        INDEX   { arInterfaceBoardIndex, arInterfacePosition }
        ::= { arInterfaceTable 1 }

    ArInterfaceEntry ::=
        SEQUENCE {
            arInterfaceBoardIndex
                INTEGER,
            arInterfacePosition
                INTEGER,
            arInterfaceIfIndex
                InterfaceIndexOrZero,
			arInterfaceName
				DisplayString
        }

    arInterfaceBoardIndex OBJECT-TYPE
        SYNTAX  INTEGER
        ACCESS  read-only
        STATUS  mandatory
        DESCRIPTION
                "The index of the board in the board table which contains this
                interface. Index 1 is reserved for the main system board of the
                router."
        ::= { arInterfaceEntry 1 }

    arInterfacePosition OBJECT-TYPE
        SYNTAX  INTEGER
        ACCESS  read-only
        STATUS  mandatory
        DESCRIPTION
                "The position of the interface on the board. Each board type
                will have well-known positions which are the interfaces
                provided by the board. The number of positions on a given board
                is given by the object arBoardTotalPositions for this board."
        ::= { arInterfaceEntry 2 }

    arInterfaceIfIndex OBJECT-TYPE
        SYNTAX  InterfaceIndexOrZero
        ACCESS  read-only
        STATUS  mandatory
        DESCRIPTION
                "The ifIndex for the interface represented by this entry of the
                interfaces table. This is the ifIndex of the ifEntry used to
                represent the physical interface. The value 0 is used for
                interfaces which don't have an ifIndex."
        ::= { arInterfaceEntry 3 }

    arInterfaceName OBJECT-TYPE
        SYNTAX  DisplayString (SIZE(0..255))
        ACCESS  read-only
        STATUS  mandatory
        DESCRIPTION
                "The name of this interface. This is the name that the manager
                can use to refer to this interface in entering router
                commands."
        ::= { arInterfaceEntry 4 }


--  Start of module MIBs. Each MIB under here represents a particular module in the router software.

    -- ==========   ETH module   ==========
    -- ==========   ETH module   ==========
    -- ==========   ETH module   ==========
    -- The Ethernet module. This group consists of a table of Ethernet
    -- interfaces indexed by ifIndex which provide MIB objects not given in a
    -- convenient form by other standard MIBs.

    ethernet OBJECT IDENTIFIER ::= { modules 23 }
    -- The index off the modules subtree is from modules.h.

    -- The Ethernet interface table. Each entry is a single Ethernet interface
    -- on the router.

    ethIntTable OBJECT-TYPE
        SYNTAX  SEQUENCE OF EthIntEntry
        ACCESS  not-accessible
        STATUS  mandatory
        DESCRIPTION
                "The table of Ethernet interfaces."
        ::= { ethernet 1 }

    ethIntEntry OBJECT-TYPE
        SYNTAX  EthIntEntry
        ACCESS  not-accessible
        STATUS  mandatory
        DESCRIPTION
                "A single entry in the Ethernet interfaces table."
        INDEX   { ethIntIndex }
        ::= { ethIntTable 1 }

    EthIntEntry ::=
        SEQUENCE {
            ethIntIndex
                InterfaceIndex,
            ethIntBoardIndex
                INTEGER,
            ethIntBoardPosition
                INTEGER,
            ethIntDuplexMode
                INTEGER
        }

    ethIntIndex OBJECT-TYPE
        SYNTAX  InterfaceIndex
        ACCESS  read-only
        STATUS  mandatory
        DESCRIPTION
                "The ifIndex of the Ethernet interface."
        ::= { ethIntEntry 1 }

    ethIntBoardIndex OBJECT-TYPE
        SYNTAX  INTEGER
        ACCESS  read-only
        STATUS  mandatory
        DESCRIPTION
                "The index in the arBoardTable of the board on which this
                Ethernet interface resides. If this Ethernet interface is not
                found, the value of this object is 0."
        ::= { ethIntEntry 2 }

    ethIntBoardPosition OBJECT-TYPE
        SYNTAX  INTEGER
        ACCESS  read-only
        STATUS  mandatory
        DESCRIPTION
                "The position on this Ethernet interface's board of this
                Ethernet interface. If this Ethernet interface is not found,
                the value of this object is 0."
        ::= { ethIntEntry 3 }

    ethIntDuplexMode OBJECT-TYPE
        SYNTAX  INTEGER {
                    full-duplex (1),
                    half-duplex (2),
                    unknown (3)
                }
        ACCESS  read-only
        STATUS  mandatory
        DESCRIPTION
                "The duplex mode of this Ethernet interface. The value unknown
                is returned when the interface cannot or has not yet made a
                determination of its duplex mode, or when the interface cannot
                be found."
        ::= { ethIntEntry 4 }


    -- ==========   CC module   ==========
    -- ==========   CC module   ==========
    -- ==========   CC module   ==========
    -- The ISDN Call Control group. This group consists of:
    --   1. the call details table
    --   2. the CLI list table
    --   3. the active calls table
    --   4. the call log table
    --   5. the attachment table
    --   6. the B channel allocation table

    cc OBJECT IDENTIFIER ::= { modules 37 }
    -- The index off the modules subtree is from modules.h.

    -- The ISDN call details table. This consists of a number of entries containing
    -- configuration information for ISDN calls.

    ccDetailsTable OBJECT-TYPE
        SYNTAX  SEQUENCE OF CcDetailsEntry
        ACCESS  not-accessible
        STATUS  mandatory
        DESCRIPTION
                "The table of call details parameters."
        ::= { cc 1 }

    ccDetailsEntry OBJECT-TYPE
        SYNTAX  CcDetailsEntry
        ACCESS  not-accessible
        STATUS  mandatory
        DESCRIPTION
                "A single entry of ISDN call details. This contains the
                parameters of a single ISDN call details."
        INDEX   { ccDetailsIndex }
        ::= { ccDetailsTable 1 }

    CcDetailsEntry ::=
        SEQUENCE {
            ccDetailsIndex
                INTEGER,
            ccDetailsName
                DisplayString,
            ccDetailsRemoteName
                DisplayString,
            ccDetailsCalledNumber
                DisplayString,
            ccDetailsCallingNumber
                DisplayString,
            ccDetailsAlternateNumber
                DisplayString,
            ccDetailsEnabled
                INTEGER,
            ccDetailsDirection
                INTEGER,
            ccDetailsPrecedence
                INTEGER,
            ccDetailsHoldupTime
                INTEGER,
            ccDetailsPreferredIfIndex
                InterfaceIndexOrZero,
            ccDetailsRequiredIfIndex
                InterfaceIndexOrZero,
            ccDetailsPriority
                INTEGER,
            ccDetailsRetryT1
                INTEGER,
            ccDetailsRetryN1
                INTEGER,
            ccDetailsRetryT2
                INTEGER,
            ccDetailsRetryN2
                INTEGER,
            ccDetailsKeepup
                INTEGER,
            ccDetailsOutSetupCli
                INTEGER,
            ccDetailsOutSetupUser
                INTEGER,
            ccDetailsOutSetupCalledSub
                INTEGER,
            ccDetailsOutSubaddress
                DisplayString,
            ccDetailsCallback
                INTEGER,
            ccDetailsCallbackDelay
                INTEGER,
            ccDetailsInSetupCalledSubSearch
                INTEGER,
            ccDetailsInSetupUserSearch
                INTEGER,
            ccDetailsInSetupCliSearch
                INTEGER,
            ccDetailsInSetupCliSearchList
                INTEGER,
            ccDetailsInAnyFlag
                INTEGER,
            ccDetailsInSetupCalledSubCheck
                INTEGER,
            ccDetailsInSetupUserCheck
                INTEGER,
            ccDetailsInSetupCliCheck
                INTEGER,
            ccDetailsInSetupCliCheckList
                INTEGER,
            ccDetailsUserType
                INTEGER,
            ccDetailsLoginType
                INTEGER,
            ccDetailsUsername
                INTEGER,
            ccDetailsPassword
                INTEGER,
            ccDetailsBumpDelay
                INTEGER,
            ccDetailsDataRate
                INTEGER,
            ccDetailsPppTemplate
                INTEGER,
            ccDetailsUserModule
                INTEGER,
            ccDetailsNumberAttachments
                INTEGER
        }

    ccDetailsIndex OBJECT-TYPE
        SYNTAX  INTEGER (1..128)
        ACCESS  read-only
        STATUS  mandatory
        DESCRIPTION
                "The index of the call details entry in the call details table. When an entry is created in this table, the index
                does not have to be written. However, to reference the values that are written, an unused index must be found by
                reading the index values of the table until a no such object error is returned. Attempting to create a row by
                using an already used index will result in simply changing the parameters of an existing call details entry."
        ::= { ccDetailsEntry 1 }

    ccDetailsName OBJECT-TYPE
        SYNTAX  DisplayString (SIZE (0..15))
        ACCESS  read-write
        STATUS  mandatory
        DESCRIPTION
                "The name of the ISDN call details. This must be unique for all ISDN call details, when comparisons are done
                ignoring the case of letters. Valid characters in the ISDN call name include 0-9, a-z, A-Z and '-'. A name
                consisting of all digits is not valid. Setting this object is mandatory on row creation. However, this object
                cannot be set for an existing call. This is because for the command line interface calls are identified by name.
                There is one exception. Setting ccDetailsName to an empty string will cause the call details to be deleted."
        ::= { ccDetailsEntry 2 }

    ccDetailsRemoteName OBJECT-TYPE
        SYNTAX  DisplayString (SIZE (0..15))
        ACCESS  read-write
        STATUS  mandatory
        DESCRIPTION
                "The remote ISDN call name. This name can be referenced by certain other call details parameters related with
                setting up the Q.931 SETUP message for outgoing calls, or searching for calls for incoming calls. Valid characters
                in the ISDN remote call name include 0-9, a-z, A-Z and '-'. A remote name consisting of all digits is valid."
        DEFVAL  { "" }
        ::= { ccDetailsEntry 3 }

    ccDetailsCalledNumber OBJECT-TYPE
        SYNTAX  DisplayString (SIZE (0..31))
        ACCESS  read-write
        STATUS  mandatory
        DESCRIPTION
                "The number called when this call details is activated. The number should include all telephone network access
                codes, country codes and area codes required to make a call from the particular ISDN interface. Setting this
                object is mandatory on row creation."
        ::= { ccDetailsEntry 4 }

    ccDetailsCallingNumber OBJECT-TYPE
        SYNTAX  DisplayString (SIZE (0..31))
        ACCESS  read-write
        STATUS  mandatory
        DESCRIPTION
                "The number used as the calling number when this call is activated. The calling number can optionally be placed
                in the outgoing SETUP message."
        DEFVAL  { "" }
        ::= { ccDetailsEntry 5 }

    ccDetailsAlternateNumber OBJECT-TYPE
        SYNTAX  DisplayString (SIZE (0..31))
        ACCESS  read-write
        STATUS  mandatory
        DESCRIPTION
                "The number called when all retries with the main called number have failed. In this event, the router tries
                once with the alternate number, then checks the ccDetailsKeepup object to determine whether to try again with
                the main number."
        DEFVAL  { "" }
        ::= { ccDetailsEntry 6 }

    ccDetailsEnabled OBJECT-TYPE
        SYNTAX  INTEGER {
                    disabled (1),
                    enabled (2)
                }
        ACCESS  read-write
        STATUS  mandatory
        DESCRIPTION
                "Whether this ISDN call is enabled or disabled for incoming and outgoing calls. If the call details entry is
                disabled, all existing active calls based on this call details entry are left active."
        DEFVAL  { enabled }
        ::= { ccDetailsEntry 7 }

    ccDetailsDirection OBJECT-TYPE
        SYNTAX  INTEGER {
                    in-only (1),
                    out-only (2),
                    both (3)
                }
        ACCESS  read-write
        STATUS  mandatory
        DESCRIPTION
                "The direction for which calls may be made or received using this call details entry."
        DEFVAL  { both }
        ::= { ccDetailsEntry 8 }

    ccDetailsPrecedence OBJECT-TYPE
        SYNTAX  INTEGER {
                    in (1),
                    out (2)
                }
        ACCESS  read-write
        STATUS  mandatory
        DESCRIPTION
                "The precedence of this call details entry in the event of call collision. Call collision occurs when an
                incoming call for a given details entry is detected while an outgoing call is waiting to complete. This
                object configures whether the router treats the incoming or outgoing call as having precedence. Since the
                device at the other end will also probably be experiencing a call collision, the precedence should be
                configured to the opposite value at the other end. Setting this object is mandatory on row creation."
        ::= { ccDetailsEntry 9 }

    ccDetailsHoldupTime OBJECT-TYPE
        SYNTAX  INTEGER (0..7200)
        ACCESS  read-write
        STATUS  mandatory
        DESCRIPTION
                "The time, in seconds, that active calls created from this call details should be held up after initial
                activation. The call will be held up for at least this time, unless cleared from the network. Thus, for example,
                PPP idle timeouts will not bring the call down."
        DEFVAL  { 0 }
        ::= { ccDetailsEntry 10 }

    ccDetailsPreferredIfIndex OBJECT-TYPE
        SYNTAX  InterfaceIndexOrZero
        ACCESS  read-write
        STATUS  mandatory
        DESCRIPTION
                "The ifIndex of an ISDN interface on this router which is the preferred ISDN interface on which to make an
                outgoing call using this call details entry. The ifIndex, if not 0, should reference the ifEntry which contains
                information about the entire ISDN interface, at the lowest layer. If a channel is not available on this interface,
                the call can try other interfaces in order to make the call. This object is not used on incoming calls. If the
                value of this object is set to 0, no interface will be preferred over any other. If the value of this object does
                not reference the ifEntry for the entire ISDN interface, no interface will be preferred."
        DEFVAL  { 0 }
        ::= { ccDetailsEntry 11 }

    ccDetailsRequiredIfIndex OBJECT-TYPE
        SYNTAX  InterfaceIndexOrZero
        ACCESS  read-write
        STATUS  mandatory
        DESCRIPTION
                "The ifIndex of an ISDN interface on this router which is the required ISDN interface on which to make an
                outgoing call using this call details entry. The ifIndex, if not 0, must reference the ifEntry which contains
                information about the entire ISDN interface, at the lowest layer. If a channel is not available on this interface,
                the call fails. This object is not used on incoming calls. If the value of this object is set to 0, no interface
                will be required. If the value of this object does not reference the ifEntry for the entire ISDN interface, no
                interface will be required."
        DEFVAL  { 0 }
        ::= { ccDetailsEntry 12 }

    ccDetailsPriority OBJECT-TYPE
        SYNTAX  INTEGER (0..99)
        ACCESS  read-write
        STATUS  mandatory
        DESCRIPTION
                "The priority of calls generated from this call details entry. The priority determines whether calls can be bumped
                for higher priority calls. The value of priority falls into ranges:
                0-19 - call bumped by incoming or outgoing, voice or data calls
                20-39 - call bumped by outgoing voice and incoming or outgoing data calls
                40-59 - call bumped by emergency voice calls or incoming or outgoing data calls
                60-99 - call bumped by emergency voice calls or outgoing data calls.
                Note that when the call is bumped by a data call, the data call must have higher
                priority than the call being bumped."
        DEFVAL { 50 }
        ::= { ccDetailsEntry 13 }

    -- Retry parameters. ISDN calls can be automatically retries in the event of a failure to establish the call. Parameters
    -- exist to set up groups of retries (N1 retries with time T1 between each retry) and groups of groups of retries (N2 retry
    -- groups with time T2 between groups).

    ccDetailsRetryT1 OBJECT-TYPE
        SYNTAX  INTEGER (5..120)
        ACCESS  read-write
        STATUS  mandatory
        DESCRIPTION
                "The time in seconds between retries of calls generated from this call details entry."
        DEFVAL  { 30 }
        ::= { ccDetailsEntry 14 }

    ccDetailsRetryN1 OBJECT-TYPE
        SYNTAX  INTEGER (0..10)
        ACCESS  read-write
        STATUS  mandatory
        DESCRIPTION
                "The number of retries in a retry group for calls generated from this call details entry. Note that the default
                value means that by default the call will not be retried."
        DEFVAL { 0 }
        ::= { ccDetailsEntry 15 }

    ccDetailsRetryT2 OBJECT-TYPE
        SYNTAX  INTEGER (300..1200)
        ACCESS  read-write
        STATUS  mandatory
        DESCRIPTION
                "The time in seconds between retry groups for retries of calls generated from this call details entry."
        DEFVAL  { 600 }
        ::= { ccDetailsEntry 16 }

    ccDetailsRetryN2 OBJECT-TYPE
        SYNTAX  INTEGER (0..5)
        ACCESS  read-write
        STATUS  mandatory
        DESCRIPTION
                "The number of retry groups for calls generated from this call details entry. Note that the default value means
                that by default no retry groups will be attempted."
        DEFVAL  { 0 }
        ::= { ccDetailsEntry 17 }

    ccDetailsKeepup OBJECT-TYPE
        SYNTAX  INTEGER {
                    no (1),
                    yes (2)
                }
        ACCESS  read-write
        STATUS  mandatory
        DESCRIPTION
                "A flag indicating whether calls generated from this call details entry should be kept up always. Inspection of
                this flag takes place when a call is cleared from an external source. If set to 'yes', the call will be retried."
        DEFVAL  { no }
        ::= { ccDetailsEntry 18 }

    ccDetailsOutSetupCli OBJECT-TYPE
        SYNTAX  INTEGER {
                    off (1),
                    calling (2),
                    interface (3),
                    nonumber (4)
                }
        ACCESS  read-write
        STATUS  mandatory
        DESCRIPTION
                "The CLI information placed into outgoing SETUP messages when this call details is used to generate an outgoing
                call. The value 'off' means that no CLI information in placed in the SETUP message. The value 'calling' means that
                the calling number from the call details entry is placed in the SETUP message. The value 'interface' means that
                the Q.931 interface number for the interface and DLC on which the call is made is placed in the SETUP message. The
                value 'nonumber' means that the CLI information element is placed in the SETUP message with no number information.
                The network will fill the number in."
        DEFVAL  { off }
        ::= { ccDetailsEntry 19 }

    ccDetailsOutSetupUser OBJECT-TYPE
        SYNTAX  INTEGER {
                    off (1),
                    local (2),
                    remote (3)
                }
        ACCESS  read-write
        STATUS  mandatory
        DESCRIPTION
                "The user-user information placed into outgoing SETUP messages when this call details is used to generate an
                outgoing call. The value 'off' means that no user-user information in placed in the SETUP message. The value
                'local' means that the call name from the call details entry is placed in the SETUP message. The value 'remote'
                means that the remote call name from the call details entry is placed in the SETUP message."
        DEFVAL  { off }
        ::= { ccDetailsEntry 20 }

    ccDetailsOutSetupCalledSub OBJECT-TYPE
        SYNTAX  INTEGER {
                    off (1),
                    local (2),
                    remote (3)
                }
        ACCESS  read-write
        STATUS  mandatory
        DESCRIPTION
                "The called subaddress information placed into outgoing SETUP messages when this call details is used to generate
                an outgoing call. The value 'off' means that no called subaddress information in placed in the SETUP message. The
                value 'local' means that the call name from the call details entry is placed in the SETUP message. The value
                'remote' means that the remote call name from the call details entry is placed in the SETUP message. Note that
                the action of this object is overridden by the value of the object ccDetailsOutSubaddress."
        DEFVAL  { off }
        ::= { ccDetailsEntry 21 }

    ccDetailsOutSubaddress OBJECT-TYPE
        SYNTAX  DisplayString (SIZE(0..31))
        ACCESS  read-write
        STATUS  mandatory
        DESCRIPTION
                "This object gives a way to override the called subaddress information placed into outgoing SETUP messages when
                this call details is used to generate an outgoing call, as given by the ccDetailsOutSetupCalledSub object. The
                object is an arbitrary string of ASCII characters, from 0 to 31 characters long."
        DEFVAL  { "" }
        ::= { ccDetailsEntry 22 }

    ccDetailsCallback OBJECT-TYPE
        SYNTAX  INTEGER {
                    no (1),
                    yes (2)
                }
        ACCESS  read-write
        STATUS  mandatory
        DESCRIPTION
                "A flag indicating whether or not to call back the caller when an incoming call is generated from this call
                details entry. If set to 'yes', the incoming call will be cleared, and after a short delay, an outgoing call will
                be activated for this call details entry."
        DEFVAL  { no }
        ::= { ccDetailsEntry 23 }

    ccDetailsCallbackDelay OBJECT-TYPE
        SYNTAX  INTEGER (0..100)
        ACCESS  read-write
        STATUS  mandatory
        DESCRIPTION
                "The time, in tenths of a second, which the router will wait after clearing an incoming call whose call details
                entry specified that the caller should be called back before making the return call. The purpose of this object
                is to allow the user to specify a delay in callback which will allow the network to properly clear the call at
                both this end and the remote end."
        DEFVAL  { 41 }
        ::= { ccDetailsEntry 24 }

    ccDetailsInSetupCalledSubSearch OBJECT-TYPE
        SYNTAX  INTEGER {
                    off (1),
                    local (2),
                    remote (3)
                }
        ACCESS  read-write
        STATUS  mandatory
        DESCRIPTION
                "Determines whether this call details entry is used in a search of call details for an incoming call based on the
                contents of the called subaddress information in the incoming SETUP message. The value 'off' means that this call
                details entry is not used in the search. The value 'local' means that the call details entry is used in the search
                and the called subaddress information is compared with the call details entry name. The value 'remote' means that
                the call details entry is used in the search and the called subaddress information is compared with the call
                details entry remote name. A number of searches are carried out until a matching call is found. First a search
                against the called subaddress in the SETUP message, then a search against the user-user information in the SETUP
                message, then a search against the calling number information in the SETUP message, then a search for any call
                that is configured to respond to any incoming call."
        DEFVAL  { off }
        ::= { ccDetailsEntry 25 }

    ccDetailsInSetupUserSearch OBJECT-TYPE
        SYNTAX  INTEGER {
                    off (1),
                    local (2),
                    remote (3)
                }
        ACCESS  read-write
        STATUS  mandatory
        DESCRIPTION
                "Determines whether this call details entry is used in a search of call details for an incoming call based on the
                contents of the user-user information in the incoming SETUP message. The value 'off' means that this call details
                entry is not used in the search. The value 'local' means that the call details entry is used in the search and
                the user-user information is compared with the call details entry name. The value 'remote' means that the call
                details entry is used in the search and the user-user information is compared with the call details entry remote
                name. A number of searches are carried out until a matching call is found. First a search against the called
                subaddress in the SETUP message, then a search against the user-user information in the SETUP message, then a
                search against the calling number information in the SETUP message, then a search for any call that is configured
                to respond to any incoming call."
        DEFVAL  { off }
        ::= { ccDetailsEntry 26 }

    ccDetailsInSetupCliSearch OBJECT-TYPE
        SYNTAX  INTEGER {
                    off (1),
                    on (2),
                    list (3)
                }
        ACCESS  read-write
        STATUS  mandatory
        DESCRIPTION
                "Determines whether this call details entry is used in a search of call details for an incoming call based on the
                contents of the calling number information in the incoming SETUP message. The value 'off' means that this call
                details entry is not used in the search. The value 'on' means that the call details entry is used in the search
                and the calling number information is compared with the call details entry called number. The value 'list' means
                that the call details entry is used in the search and the calling number information is compared with the numbers
                on the CLI list reference by the object ccDetailsInSetupCliSearchList. The value 'list' cannot be set by an SNMP
                management entity. Rather the ccDetailsInSetupCliSearchList object should be set to a non-zero value, which will
                automatically set this object to 'list'.
                A number of searches are carried out until a matching call is found. First a search against the called subaddress
                in the SETUP message, then a search against the user-user information in the SETUP message, then a search against
                the calling number information in the SETUP message, then a search for any call that is configured to respond to
                any incoming call."
        DEFVAL  { off }
        ::= { ccDetailsEntry 27 }

    ccDetailsInSetupCliSearchList OBJECT-TYPE
        SYNTAX  INTEGER (0..100)
        ACCESS  read-write
        STATUS  mandatory
        DESCRIPTION
                "If the ccDetailsInSetupCliSearch object is set to 'list', this object gives the index of the CLI list to search.
                The value of CLI list indices is 1..100. The value 0 is returned when the ccDetailsInSetupCliSearch object is not
                set to 'list'. If the value of this object is set to 0 via SNMP, then the ccDetailsInSetupCliSearch object will
                be internally set to 'off'. Subsequently setting the value of this object to a non-zero value will set the
                ccDetailsInSetupCliSearch object to 'list'."
        DEFVAL  { 0 }
        ::= { ccDetailsEntry 28 }

    ccDetailsInAnyFlag OBJECT-TYPE
        SYNTAX  INTEGER {
                    no (1),
                    yes (2)
                }
        ACCESS  read-write
        STATUS  mandatory
        DESCRIPTION
                "Determines whether this call details entry will match any incoming call. After all searched for incoming calls
                have been carried out based on called subaddress, user-user information and calling number, a search is carried
                out for the first call found with this flag set to 'yes'."
        DEFVAL  { no }
        ::= { ccDetailsEntry 29 }

    ccDetailsInSetupCalledSubCheck OBJECT-TYPE
        SYNTAX  INTEGER {
                    off (1),
                    local (2),
                    remote (3)
                }
        ACCESS  read-write
        STATUS  mandatory
        DESCRIPTION
                "Determines whether to perform a check when an incoming call matches this call details entry based on the
                contents of the called subaddress information in the incoming SETUP message. The value 'off' means that the check
                is not carried out. The value 'local' means that the check is carried out and the called subaddress information
                is compared with the call details entry name. The value 'remote' means that the check is carried out and the
                called subaddress information is compared with the call details entry remote name. A number of checks are
                optionally carried out once a matching call is found. The first check is against the called subaddress in the
                SETUP message, then against the user-user information in the SETUP message, then against the calling number
                information in the SETUP message."
        DEFVAL  { off }
        ::= { ccDetailsEntry 30 }

    ccDetailsInSetupUserCheck OBJECT-TYPE
        SYNTAX  INTEGER {
                    off (1),
                    local (2),
                    remote (3)
                }
        ACCESS  read-write
        STATUS  mandatory
        DESCRIPTION
                "Determines whether to perform a check when an incoming call matches this call details entry based on the
                contents of the user-user information in the incoming SETUP message. The value 'off' means that the check
                is not carried out. The value 'local' means that the check is carried out and the user-user information
                is compared with the call details entry name. The value 'remote' means that the check is carried out and the
                user-user information is compared with the call details entry remote name. A number of checks are
                optionally carried out once a matching call is found. The first check is against the called subaddress in the
                SETUP message, then against the user-user information in the SETUP message, then against the calling number
                information in the SETUP message."
        DEFVAL  { off }
        ::= { ccDetailsEntry 31 }

    ccDetailsInSetupCliCheck OBJECT-TYPE
        SYNTAX  INTEGER {
                    off (1),
                    present (2),
                    required (3)
                }
        ACCESS  read-write
        STATUS  mandatory
        DESCRIPTION
                "Determines whether to perform a check and which check to perform when an incoming call matches this call details
                entry based on the contents of the calling number information in the incoming SETUP message. The value 'off' means
                that the check is not carried out. The value 'present' means that the check is carried out only if calling number
                information is present. The value 'required' means that the calling number must be present for the check to pass.
                When the check is carried out, the calling number information is compared with the numbers in the CLI list
                referenced by the object ccDetailsInSetupCliCheckList.
                A number of checks are optionally carried out once a matching call is found. The first check is against the called
                subaddress in the SETUP message, then against the user-user information in the SETUP message, then against the
                calling number information in the SETUP message."
        DEFVAL  { off }
        ::= { ccDetailsEntry 32 }

    ccDetailsInSetupCliCheckList OBJECT-TYPE
        SYNTAX  INTEGER (0..100)
        ACCESS  read-write
        STATUS  mandatory
        DESCRIPTION
                "If the ccDetailsInSetupCliCheck object is set to 'present' or 'required', this object gives the index of the
                CLI list to check against. The value of CLI list indices is 1..100. The value 0 means that no list to check against
                is defined and the check immediately fails."
        DEFVAL  { 0 }
        ::= { ccDetailsEntry 33 }

    ccDetailsUserType OBJECT-TYPE
        SYNTAX  INTEGER {
                    attach (1),
                    ppp (2)
                }
        ACCESS  read-write
        STATUS  mandatory
        DESCRIPTION
                "The type of user of this call. The value 'attach' means that users have to attach to this call before the call
                can be used for outgoing or incoming calls. The value 'ppp' means that for incoming calls only dynamic PPP
                interfaces will be created whenever this call details entry is matched."
        DEFVAL  { attach }
        ::= { ccDetailsEntry 34 }

    ccDetailsLoginType OBJECT-TYPE
        SYNTAX  INTEGER {
                    none (1),
                    userdb (2),
                    radius (3),
                    pap-tacacs (4),
                    chap (5),
                    pap-radius (6),
                    tacacs (7),
                    all (8)
                }
        ACCESS  read-write
        STATUS  mandatory
        DESCRIPTION
                "The type of login for calls generated using this call details entry, for incoming calls only. Incoming calls
                can be configured to go through a logging in phase before the call is brought up. This object defines which login
                types are used. The value 'none' means don't do a login phase. The value 'userdb' means use the user database on
                the router to check login parameters. The value 'radius' means use the router's configured RADIUS servers to
                check the login parameters. The values 'pap-tacacs', 'chap' and 'pap-radius' apply only when the user is 'ppp' and
                determine how the dynamic PPP interface are configured for authentication. The value 'pap-tacacs' means use PAP
                to authenticate and use the TACACS server to check the login parameters. The value 'pap-radius' means use PAP
                to authenticate and use the RADIUS server to check the login parameters. The value 'chap' means use CHAP to
                authenticate. The value 'tacacs' means use the TACACS server to check login parameters. The value 'all' means use
                the user database, TACACS and RADIUS to check the login parameters. The login parameters for values 'userdb',
                'radius', 'tacacs' and 'all' are determined by the ccDetailsUsername and ccDetailsPassword objects."
        DEFVAL  { none }
        ::= { ccDetailsEntry 35 }

    ccDetailsUsername OBJECT-TYPE
        SYNTAX  INTEGER {
                    none (1),
                    cli (2),
                    calledsub (3),
                    useruser (4),
                    callname (5)
                }
        ACCESS  read-write
        STATUS  mandatory
        DESCRIPTION
                "The source of the username when the ccDetailsLoginType object has a value of 'userdb', 'radius', 'tacacs' or
                'all'. The value 'none' means no username is defined. The value 'cli' means take the username from the 
                calling number information in the SETUP message. The value 'calledsub' means take the username from the called
                subaddress information in the SETUP message. The value 'useruser' means take the username from the user-user
                information in the SETUP message. The value 'callname' means take the username from the call details entry name."
        DEFVAL  { none }
        ::= { ccDetailsEntry 36 }

    ccDetailsPassword OBJECT-TYPE
        SYNTAX  INTEGER {
                    none (1),
                    cli (2),
                    calledsub (3),
                    useruser (4),
                    callname (5)
                }
        ACCESS  read-write
        STATUS  mandatory
        DESCRIPTION
                "The source of the password when the ccDetailsLoginType object has a value of 'userdb', 'radius', 'tacacs' or
                'all'. The value 'none' means no password is defined. The value 'cli' means take the password from the 
                calling number information in the SETUP message. The value 'calledsub' means take the password from the called
                subaddress information in the SETUP message. The value 'useruser' means take the password from the user-user
                information in the SETUP message. The value 'callname' means take the password from the call details entry name."
        DEFVAL  { none }
        ::= { ccDetailsEntry 37 }

    ccDetailsBumpDelay OBJECT-TYPE
        SYNTAX  INTEGER (0..100)
        ACCESS  read-write
        STATUS  mandatory
        DESCRIPTION
                "The time, in tenths of a second, which the router will wait after clearing an existing call which has been bumped
                to make way for a call based on this call details entry."
        DEFVAL  { 5 }
        ::= { ccDetailsEntry 38 }

    ccDetailsDataRate OBJECT-TYPE
        SYNTAX  INTEGER {
                    rate-64k (1),
                    rate-56k (2)
                }
        ACCESS  read-write
        STATUS  mandatory
        DESCRIPTION
                "The data rate to use for active calls based on this call details entry. The actual data rate for outgoing calls
                is determined by both this object and the data rate parameter for the Q.931 interface chosen for the call. If
                either this object or the interface object specify a rate of 56k, then 56k will be the rate for the call.
                Otherwise, the default rate of 64k will be used. This allows interoperability between ISDNs which only allow 56k
                of data on a B channel."
        DEFVAL  { rate-64k }
        ::= { ccDetailsEntry 39 }

    ccDetailsPppTemplate OBJECT-TYPE
        SYNTAX  INTEGER (1..33)
        ACCESS  read-write
        STATUS  mandatory
        DESCRIPTION
                "The PPP template to use when creating dynamic PPP interfaces for calls generated from this call details entry.
                The value 33 represents a default PPP template, the values 1 to 32 represent PPP templates that are currently
                defined in the router."
        DEFVAL  { 33 }
        ::= { ccDetailsEntry 40 }

    ccDetailsUserModule OBJECT-TYPE
        SYNTAX  INTEGER
        ACCESS  read-only
        STATUS  mandatory
        DESCRIPTION
                "The module ID of the user module currently attached to this ISDN call details entry."
        ::= { ccDetailsEntry 41 }

    ccDetailsNumberAttachments OBJECT-TYPE
        SYNTAX  INTEGER
        ACCESS  read-only
        STATUS  mandatory
        DESCRIPTION
                "The number of attachments from the user module currently attached to this call details entry. The
                ccAttachmentsTable gives the actual attachments for each call details entry."
        ::= { ccDetailsEntry 42 }


    -- The ISDN CLI list table. This consists of a number of entries containing numbers for matching against CLI information.

    ccCliListTable OBJECT-TYPE
        SYNTAX  SEQUENCE OF CcCliListEntry
        ACCESS  not-accessible
        STATUS  mandatory
        DESCRIPTION
                "The table of CLI list entries."
        ::= { cc 2 }

    ccCliListEntry OBJECT-TYPE
        SYNTAX  CcCliListEntry
        ACCESS  not-accessible
        STATUS  mandatory
        DESCRIPTION
                "A single entry in the CLI list table. This contains a single number, as well as index information."
        INDEX   { ccCliListListIndex, ccCliListEntryIndex }
        ::= { ccCliListTable 1 }

    CcCliListEntry ::=
        SEQUENCE {
            ccCliListListIndex
                INTEGER,
            ccCliListEntryIndex
                INTEGER,
            ccCliListNumber
                DisplayString
        }

    ccCliListListIndex OBJECT-TYPE
        SYNTAX  INTEGER (1..100)
        ACCESS  read-only
        STATUS  mandatory
        DESCRIPTION
                "The index of the CLI list. CLI lists from 1 to 100 are defined in the router."
        ::= { ccCliListEntry 1 }

    ccCliListEntryIndex OBJECT-TYPE
        SYNTAX  INTEGER
        ACCESS  read-only
        STATUS  mandatory
        DESCRIPTION
                "The index of the CLI list entry within the CLI list. The minimum CLI list entry is 1. CLI lists are unlimited in
                length, although internal memory requirements could result in failure to create a given entry. When creating a row
                in this table, the entry index should be set to index the first empty row. Only one CLI list row in a given list
                should be created in any one SNMP message. Attempting to create more than one row will result in failure."
        ::= { ccCliListEntry 2 }

    ccCliListNumber OBJECT-TYPE
        SYNTAX  DisplayString (SIZE (0..31))
        ACCESS  read-write
        STATUS  mandatory
        DESCRIPTION
                "The number for this CLI list entry. Setting the number to a zero length string removes the entry from the CLI
                list, with consequent reshuffling of CLI entry indices. Thus the easiest way to delete an entire CLI list is to
                repeatedly set the first element in the list to a zero length string. A failure to SET will occur when this is
                attempted on an empty list."
        ::= { ccCliListEntry 3 }


    -- The active calls table. This consists of a number of entries containing details of actual active calls. Active calls are
    -- created by internal router processes, so this is a read-only table.

    ccActiveCallTable OBJECT-TYPE
        SYNTAX  SEQUENCE OF CcActiveCallEntry
        ACCESS  not-accessible
        STATUS  mandatory
        DESCRIPTION
                "The table of ISDN active calls."
        ::= { cc 3 }

    ccActiveCallEntry OBJECT-TYPE
        SYNTAX  CcActiveCallEntry
        ACCESS  not-accessible
        STATUS  mandatory
        DESCRIPTION
                "A single entry in the active call table."
        INDEX   { ccActiveCallIndex }
        ::= { ccActiveCallTable 1 }

    CcActiveCallEntry ::=
        SEQUENCE {
            ccActiveCallIndex
                INTEGER,
            ccActiveCallDetailsIndex
                INTEGER,
            ccActiveCallIfIndex
                InterfaceIndexOrZero,
            ccActiveCallDataRate
                INTEGER,
            ccActiveCallState
                INTEGER,
            ccActiveCallDirection
                INTEGER,
            ccActiveCallUserModule
                INTEGER,
            ccActiveCallUserInstance
                INTEGER,
            ccActiveCallBchannelIndex
                INTEGER
        }

    ccActiveCallIndex OBJECT-TYPE
        SYNTAX  INTEGER (1..128)
        ACCESS  read-only
        STATUS  mandatory
        DESCRIPTION
                "The index of the active call. There are 128 possible active calls in the router simultaneously."
        ::= { ccActiveCallEntry 1 }

    ccActiveCallDetailsIndex OBJECT-TYPE
        SYNTAX  INTEGER (1..128)
        ACCESS  read-only
        STATUS  mandatory
        DESCRIPTION
                "The index of the call details entry which generated this active call. Thus the index into the ccDetailsTable for
                this call."
        ::= { ccActiveCallEntry 2 }

    ccActiveCallIfIndex OBJECT-TYPE
        SYNTAX  InterfaceIndexOrZero
        ACCESS  read-only
        STATUS  mandatory
        DESCRIPTION
                "The interface index of the interface on which this active call is being made or received. A value of zero
                indicates that the active has not yet had an interface assigned to it. The ifEntry indexed by this object is the
                ifEntry for the entire ISDN interface, not the ifEntry for the active call's B channel."
        ::= { ccActiveCallEntry 3 }

    ccActiveCallDataRate OBJECT-TYPE
        SYNTAX  INTEGER {
                    rate-64k (1),
                    rate-56k (2)
                }
        ACCESS  read-only
        STATUS  mandatory
        DESCRIPTION
                "The data rate in use for this active call. This is determined by the call details setting of data rate, the
                ISDN interface setting for data rate, and the contents of the bearer capability information in the incoming
                SETUP message."
        ::= { ccActiveCallEntry 4 }

    ccActiveCallState OBJECT-TYPE
        SYNTAX  INTEGER {
                    null (1),
                    off (2),
                    try (3),
                    on (4),
                    wait (5),
                    await1 (6)
                }
        ACCESS  read-only
        STATUS  mandatory
        DESCRIPTION
                "The state of this active call. The value 'null' indicates that this active call does not actually exist, in other
                words it is in the process of being created or destroyed. The value 'off' means that the active call is just being
                activated. The value 'try' means that the active call is attempting to establish. The value 'on' means that the
                active call is established. The value 'wait' means that the active call is waiting to retry. The value 'await1'
                means that the active call is waiting for authentication to succeed before becoming established."
        ::= { ccActiveCallEntry 5 }

    ccActiveCallDirection OBJECT-TYPE
        SYNTAX  INTEGER {
                    in (1),
                    out (2),
                    undefined (3)
                }
        ACCESS  read-only
        STATUS  mandatory
        DESCRIPTION
                "The direction of this active call. The value 'in' indicates that this active call is an incoming call, the value
                'out' indicates that the active call is an outgoing call. The value 'undefined' indicates that the active call has
                just been created and a direction has not been assigned to it yet."
        ::= { ccActiveCallEntry 6 }

    ccActiveCallUserModule OBJECT-TYPE
        SYNTAX  INTEGER
        ACCESS  read-only
        STATUS  mandatory
        DESCRIPTION
                "The module ID of the user module attached to this ISDN active call."
        ::= { ccActiveCallEntry 7 }

    ccActiveCallUserInstance OBJECT-TYPE
        SYNTAX  INTEGER
        ACCESS  read-only
        STATUS  mandatory
        DESCRIPTION
                "The instance of the user module attached to this ISDN active call."
        ::= { ccActiveCallEntry 8 }

    ccActiveCallBchannelIndex OBJECT-TYPE
        SYNTAX  INTEGER (0..31)
        ACCESS  read-only
        STATUS  mandatory
        DESCRIPTION
                "The B channel number for this active entry. BRI interfaces have B channels in the range 1..2, PRI interfaces
                have B channels in the range 1..31, excluding a channel which is the D channel. A value of 0 for this entry means
                that either a B channel is not currently allocated for this call, or that more than one B channel is allocated.
                In the second case, the management client will have to walk the B channel allocation table looking for channels
                with the same active call index as this call's."
        ::= { ccActiveCallEntry 9 }

    -- The call log table. This consists of a number of entries containing log details of ISDN calls. This is a read-only table.

    ccCallLogTable OBJECT-TYPE
        SYNTAX  SEQUENCE OF CcCallLogEntry
        ACCESS  not-accessible
        STATUS  mandatory
        DESCRIPTION
                "The table of ISDN call log entries."
        ::= { cc 4 }

    ccCallLogEntry OBJECT-TYPE
        SYNTAX  CcCallLogEntry
        ACCESS  not-accessible
        STATUS  mandatory
        DESCRIPTION
                "A single entry in the ISDN call log table."
        INDEX   { ccCallLogIndex }
        ::= { ccCallLogTable 1 }

    CcCallLogEntry ::=
        SEQUENCE {
            ccCallLogIndex
                INTEGER,
            ccCallLogName
                DisplayString,
            ccCallLogState
                INTEGER,
            ccCallLogTimeStarted
                DisplayString,
            ccCallLogDirection
                INTEGER,
            ccCallLogDuration
                INTEGER,
            ccCallLogRemoteNumber
                DisplayString
        }

    ccCallLogIndex OBJECT-TYPE
        SYNTAX  INTEGER
        ACCESS  read-only
        STATUS  mandatory
        DESCRIPTION
                "The index of the call log entry. Since the call log table is dynamic, there is no guarantee that this index will
                continue to refer to the same log entry over time."
        ::= { ccCallLogEntry 1 }

    ccCallLogName OBJECT-TYPE
        SYNTAX  DisplayString (SIZE(0..255))
        ACCESS  read-only
        STATUS  mandatory
        DESCRIPTION
                "The name of the call details entry which generated the active call for which this is the log entry."
        ::= { ccCallLogEntry 2 }

    ccCallLogState OBJECT-TYPE
        SYNTAX  INTEGER {
                    initial (1),
                    active (2),
                    disconnected (3),
                    cleared (4)
                }
        ACCESS  read-only
        STATUS  mandatory
        DESCRIPTION
                "The state of the log entry. The value 'initial' means that the call is being established. The value 'active'
                means that the call is currently established. The value 'disconnected' means that the call was disconnected after
                being established for some time. The value 'cleared' means that the call was cleared abormally while in the
                establishment phase."
        ::= { ccCallLogEntry 3 }

    ccCallLogTimeStarted OBJECT-TYPE
        SYNTAX  DisplayString (SIZE(0..255))
        ACCESS  read-only
        STATUS  mandatory
        DESCRIPTION
                "A string in the format 'dd-mmm-yyyy hh:mm:ss' which gives the start time of the call for which this is the log
                entry. If the call never reached or has not yet reached the active state, this object will be a zero-length
                string."
        ::= { ccCallLogEntry 4 }

    ccCallLogDirection OBJECT-TYPE
        SYNTAX  INTEGER {
                    in (1),
                    out (2)
                }
        ACCESS  read-only
        STATUS  mandatory
        DESCRIPTION
                "The direction of the call for which this is the log entry."
        ::= { ccCallLogEntry 5 }

    ccCallLogDuration OBJECT-TYPE
        SYNTAX  INTEGER
        ACCESS  read-only
        STATUS  mandatory
        DESCRIPTION
                "The duration in seconds, of the call for which this is the log entry. A value of 0 in this field means either
                that the call has just started, that the call was cleared before becoming established, or that the call is still
                active. In other words, a non-zero value is present in this object only for calls which reach establishment and
                have since been cleared."
        ::= { ccCallLogEntry 6 }

    ccCallLogRemoteNumber OBJECT-TYPE
        SYNTAX  DisplayString (SIZE(0..255))
        ACCESS  read-only
        STATUS  mandatory
        DESCRIPTION
                "For incoming calls, the calling number, if this was made available in the SETUP message. For outgoing calls,
                the number dialed. If the number was not available, this object is a zero length string."
        ::= { ccCallLogEntry 7 }


    -- The call details attachment table. This is a table indexed by call detail index and list index of all the attachments from
    -- the user module. Since attachments are generated internally by other processes, this is a read-only table.

    ccAttachmentTable OBJECT-TYPE
        SYNTAX  SEQUENCE OF CcAttachmentEntry
        ACCESS  not-accessible
        STATUS  mandatory
        DESCRIPTION
                "The table of call detail attachment entries."
        ::= { cc 5 }

    ccAttachmentEntry OBJECT-TYPE
        SYNTAX  CcAttachmentEntry
        ACCESS  not-accessible
        STATUS  mandatory
        DESCRIPTION
                "A single entry in the attachment table."
        INDEX   { ccAttachmentDetailsIndex, ccAttachmentEntryIndex }
        ::= { ccAttachmentTable 1 }

    CcAttachmentEntry ::=
        SEQUENCE {
            ccAttachmentDetailsIndex
                INTEGER,
            ccAttachmentEntryIndex
                INTEGER,
            ccAttachmentActiveCallIndex
                INTEGER,
            ccAttachmentUserInstance
                INTEGER
        }

    ccAttachmentDetailsIndex OBJECT-TYPE
        SYNTAX  INTEGER (1..128)
        ACCESS  read-only
        STATUS  mandatory
        DESCRIPTION
                "The index of the call details entry to which this attachment entry belongs."
        ::= { ccAttachmentEntry 1 }

    ccAttachmentEntryIndex OBJECT-TYPE
        SYNTAX  INTEGER
        ACCESS  read-only
        STATUS  mandatory
        DESCRIPTION
                "The index of the attachment entry within the attachment list."
        ::= { ccAttachmentEntry 2 }

    ccAttachmentActiveCallIndex OBJECT-TYPE
        SYNTAX  INTEGER (0..128)
        ACCESS  read-only
        STATUS  mandatory
        DESCRIPTION
                "The index of the active call for this attachment. A value of 0 indicates that there is currently no active call
                for this attachment. A value of 1 to 128 references the active call currently in place for this attachment."
        ::= { ccAttachmentEntry 3 }

    ccAttachmentUserInstance OBJECT-TYPE
        SYNTAX  INTEGER
        ACCESS  read-only
        STATUS  mandatory
        DESCRIPTION
                "The instance of the user module attached to the ISDN active call for this attachment. This object should return
                the same value as the object ccActiveCallUserInstance for the active call indexed by ccAttachmentActiveCallIndex,
                if this is not 0."
        ::= { ccAttachmentEntry 4 }


    -- The B channel attachment table. This is a table indexed by ISDN interface ifIndex and B channel index of all the
    -- attachments to ISDN B channels. Since attachments are generated internally by other processes, this is a read-only table.

    ccBchannelTable OBJECT-TYPE
        SYNTAX  SEQUENCE OF CcBchannelEntry
        ACCESS  not-accessible
        STATUS  mandatory
        DESCRIPTION
                "The table of B channel attachment entries."
        ::= { cc 6 }

    ccBchannelEntry OBJECT-TYPE
        SYNTAX  CcBchannelEntry
        ACCESS  not-accessible
        STATUS  mandatory
        DESCRIPTION
                "A single entry in the B channel attachment table."
        INDEX   { ccBchannelIfIndex, ccBchannelChannelIndex }
        ::= { ccBchannelTable 1 }

    CcBchannelEntry ::=
        SEQUENCE {
            ccBchannelIfIndex
                INTEGER,
            ccBchannelChannelIndex
                INTEGER,
            ccBchannelAllocated
                INTEGER,
            ccBchannelCallType
                INTEGER,
            ccBchannelActiveCallIndex
                INTEGER,
            ccBchannelPriority
                INTEGER,
            ccBchannelDirection
                INTEGER
        }

    ccBchannelIfIndex OBJECT-TYPE
        SYNTAX  InterfaceIndexOrZero
        ACCESS  read-only
        STATUS  mandatory
        DESCRIPTION
                "The interface index of the interface which this B channel entry is on. The ifEntry indexed by this object is the
                ifEntry for the entire ISDN interface, not the ifEntry for the active call's B channel."
        ::= { ccBchannelEntry 1 }

    ccBchannelChannelIndex OBJECT-TYPE
        SYNTAX  INTEGER (1..31)
        ACCESS  read-only
        STATUS  mandatory
        DESCRIPTION
                "The B channel number for this B channel entry. BRI interfaces have B channels in the range 1..2, PRI interfaces
                have B channels in the range 1..31, excluding a channel which is the D channel."
        ::= { ccBchannelEntry 2 }

    ccBchannelAllocated OBJECT-TYPE
        SYNTAX  INTEGER {
                    no (1),
                    yes (2)
                }
        ACCESS  read-only
        STATUS  mandatory
        DESCRIPTION
                "A flag indicating whether this B channel is actually allocated to a call or not."
        ::= { ccBchannelEntry 3 }

    ccBchannelCallType OBJECT-TYPE
        SYNTAX  INTEGER {
                    undefined (1),
                    data (2),
                    voice (3),
                    x25 (4)
                }
        ACCESS  read-only
        STATUS  mandatory
        DESCRIPTION
                "The type of call on this B channel. If the B channel is not allocated, the call type will be undefined."
        ::= { ccBchannelEntry 4 }

    ccBchannelActiveCallIndex OBJECT-TYPE
        SYNTAX  INTEGER (0..128)
        ACCESS  read-only
        STATUS  mandatory
        DESCRIPTION
                "The index of the active call which is currently attached to this B channel. If the value of this object is 0 the
                channel is either not allocated, or is not allocated to a data call."
        ::= { ccBchannelEntry 5 }

    ccBchannelPriority OBJECT-TYPE
        SYNTAX  INTEGER
        ACCESS  read-only
        STATUS  mandatory
        DESCRIPTION
                "The priority of the call which has this B channel allocated to it. This is in the range 0..99 for data calls, 150
                for voice calls and 200 for emergency voice calls. A B channel which is not allocated will have a priority of 0."
        ::= { ccBchannelEntry 6 }

    ccBchannelDirection OBJECT-TYPE
        SYNTAX  INTEGER {
                    in (1),
                    out (2),
                    unallocated (3)
                }
        ACCESS  read-only
        STATUS  mandatory
        DESCRIPTION
                "The direction of the call which has this B channel allocated to it. If this B channel is not allocated the value
                will be 'unallocated'."
        ::= { ccBchannelEntry 7 }


    -- ==========   BRI module   ==========
    -- ==========   BRI module   ==========
    -- ==========   BRI module   ==========
    -- The BRI module. This group consists of a table of BRI interfaces indexed
    -- by ifIndex which provide MIB objects not given in a convenient form by
    -- other standard MIBs. There is also a BRI channel MIB indexed by ifIndex
    -- and channel index which gives information about the channels on the
    -- interface.

    bri OBJECT IDENTIFIER ::= { modules 41 }
    -- The index off the modules subtree is from modules.h.

    -- The BRI interface table. Each entry is a BRI interface on the router.

    briIntTable OBJECT-TYPE
        SYNTAX  SEQUENCE OF BriIntEntry
        ACCESS  not-accessible
        STATUS  mandatory
        DESCRIPTION
                "The table of BRI interfaces."
        ::= { bri 1 }

    briIntEntry OBJECT-TYPE
        SYNTAX  BriIntEntry
        ACCESS  not-accessible
        STATUS  mandatory
        DESCRIPTION
                "A single entry in the BRI interfaces table."
        INDEX   { briIntIndex }
        ::= { briIntTable 1 }

    BriIntEntry ::=
        SEQUENCE {
            briIntIndex
                INTEGER,
            briIntBoardIndex
                INTEGER,
            briIntBoardPosition
                INTEGER,
            briIntMode
                INTEGER,
            briIntTdmChannelMap
                INTEGER,
            briIntIsdnChannelMap
                INTEGER
        }

    briIntIndex OBJECT-TYPE
        SYNTAX  INTEGER
        ACCESS  read-only
        STATUS  mandatory
        DESCRIPTION
                "The ifIndex of the BRI interface."
        ::= { briIntEntry 1 }

    briIntBoardIndex OBJECT-TYPE
        SYNTAX  INTEGER
        ACCESS  read-only
        STATUS  mandatory
        DESCRIPTION
                "The index in the arBoardTable of the board on which this BRI
                interface resides."
        ::= { briIntEntry 2 }

    briIntBoardPosition OBJECT-TYPE
        SYNTAX  INTEGER
        ACCESS  read-only
        STATUS  mandatory
        DESCRIPTION
                "The position on this BRI interface's board of this BRI
                interface."
        ::= { briIntEntry 3 }

    briIntMode OBJECT-TYPE
        SYNTAX  INTEGER {
                    isdn (1),
                    tdm (2),
                    mixed (3)
                }
        ACCESS  read-only
        STATUS  mandatory
        DESCRIPTION
                "The mode of operation of this BRI interface. The value isdn
                means that the entire interface is operating as an ISDN
                interface, the value tdm means that the entire interface is
                operating as TDM groups and the value mixed means that some
                channels in the interface are dedicated to ISDN and some to TDM
                groups."
        ::= { briIntEntry 4 }

    briIntTdmChannelMap OBJECT-TYPE
        SYNTAX  INTEGER
        ACCESS  read-only
        STATUS  mandatory
        DESCRIPTION
                "A bit map of the channels in the BRI interface which are
                dedicated to TDM. Channel B1 has channel map value of 1,
                channel B2 has a channel map value of 2."
        ::= { briIntEntry 5 }

    briIntIsdnChannelMap OBJECT-TYPE
        SYNTAX  INTEGER
        ACCESS  read-only
        STATUS  mandatory
        DESCRIPTION
                "A bit map of the channels in the BRI interface which are
                dedicated to ISDN. Channel B1 has channel map value of 1,
                channel B2 has a channel map value of 2."
        ::= { briIntEntry 6 }

    -- The BRI channel table. Each entry is a channel on a BRI interface.

    briChanTable OBJECT-TYPE
        SYNTAX  SEQUENCE OF BriChanEntry
        ACCESS  not-accessible
        STATUS  mandatory
        DESCRIPTION
                "The table of channels on BRI interfaces."
        ::= { bri 2 }

    briChanEntry OBJECT-TYPE
        SYNTAX  BriChanEntry
        ACCESS  not-accessible
        STATUS  mandatory
        DESCRIPTION
                "A single entry in the BRI channels table."
        INDEX   { briChanIntIndex, briChanChannelIndex }
        ::= { briChanTable 1 }

    BriChanEntry ::=
        SEQUENCE {
            briChanIntIndex
                INTEGER,
            briChanChannelIndex
                INTEGER,
            briChanMode
                INTEGER,
            briChanState
                INTEGER
        }

    briChanIntIndex OBJECT-TYPE
        SYNTAX  INTEGER
        ACCESS  read-only
        STATUS  mandatory
        DESCRIPTION
                "The ifIndex of the BRI interface."
        ::= { briChanEntry 1 }

    briChanChannelIndex OBJECT-TYPE
        SYNTAX  INTEGER (1..3)
        ACCESS  read-only
        STATUS  mandatory
        DESCRIPTION
                "The channel index of the BRI channel. Channel B1 has index 1,
                channel B2 has index 2 and the D channel has index 3."
        ::= { briChanEntry 2 }

    briChanMode OBJECT-TYPE
        SYNTAX  INTEGER {
                    isdn (1),
                    tdm (2),
					none (3)
                }
        ACCESS  read-only
        STATUS  mandatory
        DESCRIPTION
                "The mode of this BRI channel. The value isdn means that the
                channel is reserved for use in ISDN calls. The value tdm
                means that the channel is reserved for use by TDM. For the D
                channel, this object will always have the value isdn."
        ::= { briChanEntry 3 }

    briChanState OBJECT-TYPE
        SYNTAX  INTEGER {
                    inactive (1),
                    active (2)
                }
        ACCESS  read-only
        STATUS  mandatory
        DESCRIPTION
                "The state of this BRI channel. The value inactive means that
                the channel does not currently have an active user, either an
                ISDN call or an active TDM group. The value active means that
                the channel is in use, either by an ISDN call or an active TDM
                group. For the D channel, this object will have the value
                active if LAPD is using the D channel (either for call control
                or X.25), or the value inactive otherwise."
        ::= { briChanEntry 4 }


    -- ==========   PRI module   ==========
    -- ==========   PRI module   ==========
    -- ==========   PRI module   ==========
    -- The PRI module. This group consists of a table of PRI interfaces indexed
    -- by ifIndex which provide MIB objects not given in a convenient form by
    -- other standard MIBs. There is also a PRI channel MIB indexed by ifIndex
    -- and channel index which gives information about the channels on the
    -- interface.

    pri OBJECT IDENTIFIER ::= { modules 42 }
    -- The index off the modules subtree is from modules.h.

    -- The PRI interface table. Each entry is a PRI interface on the router.

    priIntTable OBJECT-TYPE
        SYNTAX  SEQUENCE OF PriIntEntry
        ACCESS  not-accessible
        STATUS  mandatory
        DESCRIPTION
                "The table of PRI interfaces."
        ::= { pri 1 }

    priIntEntry OBJECT-TYPE
        SYNTAX  PriIntEntry
        ACCESS  not-accessible
        STATUS  mandatory
        DESCRIPTION
                "A single entry in the PRI interfaces table."
        INDEX   { priIntIndex }
        ::= { priIntTable 1 }

    PriIntEntry ::=
        SEQUENCE {
            priIntIndex
                INTEGER,
            priIntBoardIndex
                INTEGER,
            priIntBoardPosition
                INTEGER,
            priIntMode
                INTEGER,
            priIntTdmChannelMap
                INTEGER,
            priIntIsdnChannelMap
                INTEGER,
			priIntType
				INTEGER
        }

    priIntIndex OBJECT-TYPE
        SYNTAX  INTEGER
        ACCESS  read-only
        STATUS  mandatory
        DESCRIPTION
                "The ifIndex of the PRI interface."
        ::= { priIntEntry 1 }

    priIntBoardIndex OBJECT-TYPE
        SYNTAX  INTEGER
        ACCESS  read-only
        STATUS  mandatory
        DESCRIPTION
                "The index in the arBoardTable of the board on which this PRI
                interface resides."
        ::= { priIntEntry 2 }

    priIntBoardPosition OBJECT-TYPE
        SYNTAX  INTEGER
        ACCESS  read-only
        STATUS  mandatory
        DESCRIPTION
                "The position on this PRI interface's board of this PRI
                interface."
        ::= { priIntEntry 3 }

    priIntMode OBJECT-TYPE
        SYNTAX  INTEGER {
                    isdn (1),
                    tdm (2),
                    mixed (3)
                }
        ACCESS  read-only
        STATUS  mandatory
        DESCRIPTION
                "The mode of operation of this PRI interface. The value isdn
                means that the entire interface is operating as an ISDN
                interface, the value tdm means that the entire interface is
                operating as TDM groups and the value mixed means that some
                channels in the interface are dedicated to ISDN and some to TDM
                groups."
        ::= { priIntEntry 4 }

    priIntTdmChannelMap OBJECT-TYPE
        SYNTAX  INTEGER
        ACCESS  read-only
        STATUS  mandatory
        DESCRIPTION
                "A bit map of the channels in the PRI interface which are
                dedicated to TDM. PRI channels are numbered from 0 to 31, 0 is
                unused, 16 (E1) or 24 (T1) is the D channel. The map values are
                2 to the power of the channel number."
        ::= { priIntEntry 5 }

    priIntIsdnChannelMap OBJECT-TYPE
        SYNTAX  INTEGER
        ACCESS  read-only
        STATUS  mandatory
        DESCRIPTION
                "A bit map of the channels in the PRI interface which are
                dedicated to ISDN. PRI channels are numbered from 0 to 31, 0 is
                unused, 16 (E1) or 24 (T1) is the D channel. The map values are
                2 to the power of the channel number."
        ::= { priIntEntry 6 }

    priIntType OBJECT-TYPE
        SYNTAX  INTEGER {
                    e1 (1),
                    t1 (2),
                    unknown (3)
                }
        ACCESS  read-only
        STATUS  mandatory
        DESCRIPTION
                "The type of primary rate interface. E1 has 30 B + D channel,
                T1 has 23 B + D channel. If the value unknown is returned for
                this object, the exact PRI type has not yet been determined."
        ::= { priIntEntry 7 }

    -- The PRI channel table. Each entry is a channel on a PRI interface.

    priChanTable OBJECT-TYPE
        SYNTAX  SEQUENCE OF PriChanEntry
        ACCESS  not-accessible
        STATUS  mandatory
        DESCRIPTION
                "The table of channels on PRI interfaces."
        ::= { pri 2 }

    priChanEntry OBJECT-TYPE
        SYNTAX  PriChanEntry
        ACCESS  not-accessible
        STATUS  mandatory
        DESCRIPTION
                "A single entry in the PRI channels table."
        INDEX   { priChanIntIndex, priChanChannelIndex }
        ::= { priChanTable 1 }

    PriChanEntry ::=
        SEQUENCE {
            priChanIntIndex
                INTEGER,
            priChanChannelIndex
                INTEGER,
            priChanMode
                INTEGER,
            priChanState
                INTEGER
        }

    priChanIntIndex OBJECT-TYPE
        SYNTAX  INTEGER
        ACCESS  read-only
        STATUS  mandatory
        DESCRIPTION
                "The ifIndex of the PRI interface."
        ::= { priChanEntry 1 }

    priChanChannelIndex OBJECT-TYPE
        SYNTAX  INTEGER (1..3)
        ACCESS  read-only
        STATUS  mandatory
        DESCRIPTION
                "The channel index of the PRI channel. Valid channels have
                indices from 1 to 31. The D channel on an E1 interface has
                index 16, the D channel on a T1 interface has index 24."
        ::= { priChanEntry 2 }

    priChanMode OBJECT-TYPE
        SYNTAX  INTEGER {
                    isdn (1),
                    tdm (2),
					neither (3)
                }
        ACCESS  read-only
        STATUS  mandatory
        DESCRIPTION
                "The mode of this PRI channel. The value isdn means that the
                channel is reserved for use in ISDN calls. The value tdm
                means that the channel is reserved for use by TDM. For the D
                channel, this object will usually have the value isdn. An
                exception is if the interface is running common D channel mode
                and the D channel is reserved for TDM."
        ::= { priChanEntry 3 }

    priChanState OBJECT-TYPE
        SYNTAX  INTEGER {
                    inactive (1),
                    active (2)
                }
        ACCESS  read-only
        STATUS  mandatory
        DESCRIPTION
                "The state of this PRI channel. The value inactive means that
                the channel does not currently have an active user, either an
                ISDN call or an active TDM group. The value active means that
                the channel is in use, either by an ISDN call or an active TDM
                group."
        ::= { priChanEntry 4 }


    -- ==========   LOAD module ==========
    -- ==========   LOAD module ==========
    -- ==========   LOAD module ==========
    -- The load group. This consists of a static and dynamic entry of load
    -- information and a load status variable.

    loader OBJECT IDENTIFIER ::= { modules 48 }
    -- The index off the modules subtree is from modules.h.

    -- The load table. This consists of a static and dynamic entry of load
    -- information. The static information will be used if there is no dynamic
    -- information available.

    loadTable OBJECT-TYPE
        SYNTAX  SEQUENCE OF LoadEntry
        ACCESS  not-accessible
        STATUS  mandatory
        DESCRIPTION
                "The table of load parameters, dynamic and static."
        ::= { loader 1 }

    loadEntry OBJECT-TYPE
        SYNTAX  LoadEntry
        ACCESS  not-accessible
        STATUS  mandatory
        DESCRIPTION
                "A single entry of load parameters. This contains the
                parameters required to perform a load from the router."
        INDEX   { loadIndex }
        ::= { loadTable 1 }

    LoadEntry ::=
        SEQUENCE {
            loadIndex
                INTEGER,
            loadServer
                IpAddress,
            loadDestination
                INTEGER,
            loadFilename
                DisplayString,
            loadDelay
                INTEGER
        }

    loadIndex OBJECT-TYPE
        SYNTAX  INTEGER {
                    static(1),
                    dynamic(2)
                }
        ACCESS  read-write
        STATUS  mandatory
        DESCRIPTION
                "There are two sets of load information, dynamic and static.
                The dynamic information is used once, then cleared. The static
                information is used whenever the dynamic information is not
                available. The dynamic information is also used to indicate the
                current load parameters when a load is in progress."
        ::= { loadEntry 1 }

    loadServer OBJECT-TYPE
        SYNTAX  IpAddress
        ACCESS  read-write
        STATUS  mandatory
        DESCRIPTION
                "The IP address from which load will load."
        ::= { loadEntry 2 }

    loadDestination OBJECT-TYPE
        SYNTAX  INTEGER {
                    undefined(1),
                    nvs(2),
                    flash(3)
                }
        ACCESS  read-write
        STATUS  mandatory
        DESCRIPTION
                "The destination of the file loaded, either flash or nvs
                memory, or undefined."
        ::= { loadEntry 3 }

    loadFilename OBJECT-TYPE
        SYNTAX  DisplayString (SIZE (0..255))
        ACCESS  read-write
        STATUS  mandatory
        DESCRIPTION
                "The file name of the file being loaded."
        ::= { loadEntry 4 }

    loadDelay OBJECT-TYPE
        SYNTAX  INTEGER
        ACCESS  read-write
        STATUS  mandatory
        DESCRIPTION
                "A delay in seconds between the initiation of the load and the
                start of the load. This allows for time to set up TFTP servers
                in cases where the terminal and TFTP server are using the same
                piece of equipment but will not work simultaneously."
        ::= { loadEntry 5 }

    -- The load status value. This is used to start and reset a load, and to
    -- report on the progress of a load.

    loadStatus OBJECT-TYPE
        SYNTAX  INTEGER {
                    idle(1),        -- loader is doing nothing
                    wait(2),        -- loader is waiting to start
                    loading(3),     -- loader is loading a file
                    complete(4),    -- loader has successfully completed a load
                    reset(5),       -- loader was aborted
                    actionstart(6), -- cause a load to start
                    actionstop(7)   -- cause a load to stop
                }
        ACCESS  read-write
        STATUS  mandatory
        DESCRIPTION
                "Status and action object for the load module. The values 1 to
                5 are read-only values and reflect the state of the load
                module. Values 4 and 5 (complete and reset) are 'read-once',
                that is, if their values are read, either by SNMP or by manager
                console command, then they will be changed back to idle. The
                action values (6 and 7) cause a start and stop of the load
                process respectively. Starting the load can only occur if this
                field has the values 1, 4, or 5. Stopping the load can only
                occur is this field has the values 2 or 3. Reading the value of
                the loadStatus after one of actionstart or actionstop has been
                set will give one of the values 1 to 5."
        ::= { loader 2 }


    -- ==========   INSTALL module  ==========
    -- ==========   INSTALL module  ==========
    -- ==========   INSTALL module  ==========

    -- The install group. This group contains information relating to the install module in the
    -- router.

    install OBJECT IDENTIFIER ::= { modules 49 }
    -- The index off the modules subtree is from modules.h.

    -- The install table. This table controls the software release and patch
    -- running in the router.
    
    installTable OBJECT-TYPE
        SYNTAX  SEQUENCE OF InstallEntry
        ACCESS  not-accessible
        STATUS  mandatory
        DESCRIPTION
                "The list of install configurations for the router."
        ::= { install 1 }

    installEntry OBJECT-TYPE
        SYNTAX  InstallEntry
        ACCESS  not-accessible
        STATUS  mandatory
        DESCRIPTION
                "An entry in the list of install configurations."
        INDEX   { instIndex }
        ::= { installTable 1 }

    InstallEntry ::=
        SEQUENCE {
            instIndex
                INTEGER,
            instRelDevice
                INTEGER,
            instRelName
                DisplayString,
            instRelMajor
                INTEGER,
            instRelMinor
                INTEGER,
            instPatDevice
                INTEGER,
            instPatName
                DisplayString,
            instRelInterim
                INTEGER
        }

    instIndex OBJECT-TYPE
        SYNTAX  INTEGER {
                    temporary(1),
                    preferred(2),
                    default(3)
                }
        ACCESS  read-only
        STATUS  mandatory
        DESCRIPTION
                "The index for the install table. There are three install
                configurations defined in the router, default, preferred and
                temporary. The router will attempt to use these in the order
                temporary, preferred, default when it boots. An install that is
                undefined will be skipped, an install which points to a file
                which is not present will be skipped. When the temporary
                install is used, the information is deleted."
        ::= { installEntry 1 }

    instRelDevice OBJECT-TYPE
        SYNTAX  INTEGER {
                    none(1),
                    eprom(2),
                    flash(3)
                }
        ACCESS  read-write
        STATUS  mandatory
        DESCRIPTION
                "The device for the release in the install. If the device is
                flash the file for the release is given in instRelName. Devices
                none(1) or flash(3) are invalid for the default(3) release."
        ::= { installEntry 2 }

    instRelName OBJECT-TYPE
        SYNTAX  DisplayString (SIZE (0..255))
        ACCESS  read-write
        STATUS  mandatory
        DESCRIPTION
                "The file name for the release in the install, if the
                instRelDevice is flash(3). If the instRelDevice is none(1) or
                eprom(2), this object should be a null string."
        ::= { installEntry 3 }

    instRelMajor OBJECT-TYPE
        SYNTAX  INTEGER
        ACCESS  read-only
        STATUS  mandatory
        DESCRIPTION
                "The major release number for this install. This information is
                obtained by the router when the other elements in the row are
                set and is thus not directly set by management. If the release number
                is a.b.c, the major release number is a."
        ::= { installEntry 4 }

    instRelMinor OBJECT-TYPE
        SYNTAX  INTEGER
        ACCESS  read-only
        STATUS  mandatory
        DESCRIPTION
                "The minor release number for this install. This information is
                obtained by the router when the other elements in the row are
                set and is thus not directly set by management. If the release number
                is a.b.c, the major release number is b."
        ::= { installEntry 5 }

    instPatDevice OBJECT-TYPE
        SYNTAX  INTEGER {
                    none(1),
                    flash(3),
                    nvs(4)
                }
        ACCESS  read-write
        STATUS  mandatory
        DESCRIPTION
                "The device for the patch in the install. The file for the
                patch is given in instPatName unless the device is none(1)."
        ::= { installEntry 6 }

    instPatName OBJECT-TYPE
        SYNTAX  DisplayString (SIZE (0..255))
        ACCESS  read-write
        STATUS  mandatory
        DESCRIPTION
                "The file name for the patch in the install."
        ::= { installEntry 7 }

    instRelInterim OBJECT-TYPE
        SYNTAX  INTEGER
        ACCESS  read-only
        STATUS  mandatory
        DESCRIPTION
                "The interim release number for this install. This information is
                obtained by the router when the other elements in the row are
                set and is thus not directly set by management. If the release number
                is a.b.c, the major release number is c. If the release number is a.b,
                the interim release number is 0."
        ::= { installEntry 8 }

    -- The install history table. Each element is a descriptive line that tells
    -- of part of the install history of the last router reboot.

    installHistoryTable OBJECT-TYPE
        SYNTAX  SEQUENCE OF InstallHistoryEntry
        ACCESS  not-accessible
        STATUS  mandatory
        DESCRIPTION
                "The table of descriptions of events in the install history of
                the router."
        ::= { install 2 }

    installHistoryEntry OBJECT-TYPE
        SYNTAX  InstallHistoryEntry
        ACCESS  not-accessible
        STATUS  mandatory
        DESCRIPTION
                "A single line describing part of the install history of the
                router."
        INDEX   { instHistIndex }
        ::= { installHistoryTable 1 }

    InstallHistoryEntry ::=
        SEQUENCE {
            instHistIndex
                INTEGER,
            instHistLine
                DisplayString
        }

    instHistIndex OBJECT-TYPE
        SYNTAX  INTEGER
        ACCESS  read-only
        STATUS  mandatory
        DESCRIPTION
                "The index of this event in the install history. Indices run
                from 1 to the maximum number. The maximum number is not
                available as a managed object so this table will have to be
                traversed in order to find out how large it is."
        ::= { installHistoryEntry 1 }

    instHistLine OBJECT-TYPE
        SYNTAX  DisplayString (SIZE (0..255))
        ACCESS  read-only
        STATUS  mandatory
        DESCRIPTION
                "A line of text describing a single event in the install
                history of the router."
        ::= { installHistoryEntry 2 }

    -- The configuration file

    configFile OBJECT-TYPE
        SYNTAX  DisplayString (SIZE (0..255))
        ACCESS  read-write
        STATUS  mandatory
        DESCRIPTION
                "The name of the file that the router will configure from at
                boot. The format of the name is the same as that for fileName
                described above. If the configuration file name is a zero
                length string, then there is no configuration file defined in
                the router."
        ::= { install 3 }

    -- The release licence table. This table contains licences for releases of
    -- router software stored in flash.

    licenceTable OBJECT-TYPE
        SYNTAX  SEQUENCE OF LicenceEntry
        ACCESS  not-accessible
        STATUS  mandatory
        DESCRIPTION
                "The list of release licences in the router."
        ::= { install 4 }

    licenceEntry OBJECT-TYPE
        SYNTAX  LicenceEntry
        ACCESS  not-accessible
        STATUS  mandatory
        DESCRIPTION
                "An entry in the list of release licences."
        INDEX   { licenceIndex }
        ::= { licenceTable 1 }

    LicenceEntry ::=
        SEQUENCE {
            licenceIndex
                INTEGER,
            licenceStatus
                INTEGER,
            licenceRelease
                DisplayString,
            licenceMajor
                INTEGER,
            licenceMinor
                INTEGER,
            licencePassword
                DisplayString,
            licenceExpiry
                DisplayString,
            licenceInterim
                INTEGER
        }

    licenceIndex OBJECT-TYPE
        SYNTAX  INTEGER
        ACCESS  read-only
        STATUS  mandatory
        DESCRIPTION
                "A unique licence index. Licence indices are recalculated every
                time the router reboots to reflect the current licences on the
                router. As licences are added, new indices are allocated to the
                new licences."
        ::= { licenceEntry 1 }

    licenceStatus OBJECT-TYPE
        SYNTAX  INTEGER {
                    ok(1),      -- file exists and is OK
                    deleting(2) -- delete the file when this value written
                }
        ACCESS  read-write
        STATUS  mandatory
        DESCRIPTION
                "The status of the file. When read, this object will always
                return a value of ok(1), since the object will not exist if the
                value is deleting(2). Write the value deleting(2) to this
                object to delete the file."
        ::= { licenceEntry 2 }

    licenceRelease OBJECT-TYPE
        SYNTAX  DisplayString (SIZE (0..255))
        ACCESS  read-write
        STATUS  mandatory
        DESCRIPTION
                "The file name for the release whose licence this is."
        ::= { licenceEntry 3 }

    licenceMajor OBJECT-TYPE
        SYNTAX  INTEGER
        ACCESS  read-write
        STATUS  mandatory
        DESCRIPTION
                "The major release number for the release whose licence this is."
        ::= { licenceEntry 4 }

    licenceMinor OBJECT-TYPE
        SYNTAX  INTEGER
        ACCESS  read-write
        STATUS  mandatory
        DESCRIPTION
                "The minor release number for the release whose licence this is."
        ::= { licenceEntry 5 }

    licencePassword OBJECT-TYPE
        SYNTAX  DisplayString (SIZE (0..255))
        ACCESS  read-write
        STATUS  mandatory
        DESCRIPTION
                "The password for this release. The password is a string of hex
                digits."
        ::= { licenceEntry 6 }

    licenceExpiry OBJECT-TYPE
        SYNTAX  DisplayString (SIZE (0..255))
        ACCESS  read-only
        STATUS  mandatory
        DESCRIPTION
                "A human-readable string that gives the expiry date of this
                licence."
        ::= { licenceEntry 7 }

    licenceInterim OBJECT-TYPE
        SYNTAX  INTEGER
        ACCESS  read-write
        STATUS  mandatory
        DESCRIPTION
                "The interim release number for the release whose licence this is."
        ::= { licenceEntry 8 }

    -- The create configuration file

    createConfigFile OBJECT-TYPE
        SYNTAX  DisplayString (SIZE (0..255))
        ACCESS  read-write
        STATUS  mandatory
        DESCRIPTION
                "The name of a file to create containing the current router configuration. A
                read from this variable will return the same as the variable configFile. Thus
                to save the current configuration in the current configuration file, read
                createConfigFile first, then write the result back to createConfigFile. If
                this variable is written with the name of an existing file, the file will be
                replaced with the current configuration."
        ::= { install 5 }


    -- ==========   FILE module ==========
    -- ==========   FILE module ==========
    -- ==========   FILE module ==========

    -- The file group. This group contains information pertinent to the file system in the
    -- router.

    file OBJECT IDENTIFIER ::= { modules 56 }
    -- The index off the modules subtree is from modules.h.

    -- The file table

    fileTable OBJECT-TYPE
        SYNTAX  SEQUENCE OF FileEntry
        ACCESS  not-accessible
        STATUS  mandatory
        DESCRIPTION
                "A list of all the files in the router's non-volatile storage."
        ::= { file 1 }

    fileEntry OBJECT-TYPE
        SYNTAX  FileEntry
        ACCESS  not-accessible
        STATUS  mandatory
        DESCRIPTION
                "An entry in the list of files containing information about a
                single file in the router."
        INDEX   { fileIndex }
        ::= { fileTable 1 }

    FileEntry ::=
        SEQUENCE {
            fileIndex
                INTEGER,
            fileName
                DisplayString,
            fileDevice
                INTEGER,
            fileCreationTime
                DisplayString,
            fileStatus
                INTEGER,
            fileSize
                INTEGER
        }

    fileIndex OBJECT-TYPE
        SYNTAX  INTEGER
        ACCESS  read-only
        STATUS  mandatory
        DESCRIPTION
                "A unique file index. File indices are recalculated every time
                the router reboots to reflect the current files on the router.
                As files are added, new indices are allocated to the new
                files."
        ::= { fileEntry 1 }

    fileName OBJECT-TYPE
        SYNTAX  DisplayString (SIZE (0..255))
        ACCESS  read-only
        STATUS  mandatory
        DESCRIPTION
                "The name of the file, in the form <name.typ>. The name is up
                to eight characters long, the type is up to three characters
                long."
        ::= { fileEntry 2 }

    fileDevice OBJECT-TYPE
        SYNTAX  INTEGER {
                    flash(1),
                    nvs(2)
                }
        ACCESS  read-only
        STATUS  mandatory
        DESCRIPTION
                "The device on which the file resides."
        ::= { fileEntry 3 }

    fileCreationTime OBJECT-TYPE
        SYNTAX  DisplayString (SIZE (0..255))
        ACCESS  read-only
        STATUS  mandatory
        DESCRIPTION
                "The creation date and time for the file, in the format
                <dd-mmm-yy, hh:mm:ss>."
        ::= { fileEntry 4 }

    fileStatus OBJECT-TYPE
        SYNTAX  INTEGER {
                    ok(1),      -- file exists and is OK
                    deleting(2) -- delete the file when this value written
                }
        ACCESS  read-write
        STATUS  mandatory
        DESCRIPTION
                "The status of the file. When read, this object will always
                return a value of ok(1), since the object will not exist if the
                value is deleting(2). Write the value deleting(2) to this
                object to delete the file."
        ::= { fileEntry 5 }

    fileSize OBJECT-TYPE
        SYNTAX  INTEGER
        ACCESS  read-only
        STATUS  mandatory
        DESCRIPTION
                "The size, in bytes, of the file."
        ::= { fileEntry 6 }


    -- ==========   FIREWALL module ==========
    -- ==========   FIREWALL module ==========
    -- ==========   FIREWALL module ==========
    -- The firewall group. This consists of a single variable which is the last
    -- TRAP message sent.

    firewall OBJECT IDENTIFIER ::= { modules 77 }
    -- The index off the modules subtree is from modules.h.

    -- The last TRAP message sent from the firewall.
    firewallTrapMessage OBJECT-TYPE
        SYNTAX  DisplayString (SIZE (0..255))
        ACCESS  read-only
        STATUS  mandatory
        DESCRIPTION
                "The last message sent in a firewall TRAP. This variable is really
                just a placeholder for the object sent in the firewall TRAP, but can
                be read independently if required. Note however that a new TRAP will
                cause this variable to be overwritten."
        ::= { firewall 1 }

    firewallTrap TRAP-TYPE
        ENTERPRISE  firewall
        VARIABLES   { firewallTrapMessage }
        DESCRIPTION
                    "A firewall trap is generated when the firewall detects an intrusion or attack
                    and notifies the router manager. Firewall trap notifications are enabled with
                    the command ENABLE FIREWALL NOTIFY=SNMP."
        ::= 1

    END
