PDN-DEVICE-TIME-MIB DEFINITIONS ::= BEGIN

-- Version :  0.1 DRAFT
-- Enterprise Time mib
-- Copyright (C) 2000 Paradyne Corporation.

-- Created by : Prakash Easwar

IMPORTS
IpAddress
FROM RFC1155-SMI
OBJECT-TYPE
FROM RFC-1212
DateAndTime
FROM SNMPv2-TC
NTPMode
FROM PDN-TC
pdn-time
FROM PDN-HEADER-MIB

;
devTimeMIBObjects       OBJECT IDENTIFIER ::= { pdn-time 1 }
devTimeMIBTraps         OBJECT IDENTIFIER ::= { pdn-time 2 }
devTimeAndDate          OBJECT IDENTIFIER ::= { devTimeMIBObjects 1 }
devNTP                  OBJECT IDENTIFIER ::= { devTimeMIBObjects 2 }


-- Time And Date Group

devDateAndTime OBJECT-TYPE
    SYNTAX  DateAndTime
    ACCESS  read-write
    STATUS  mandatory
    DESCRIPTION
       "This objects displays the date and time on the entity.
       It allows an NMS to set the date and time in the appropriate
       timezone "
    ::= { devTimeAndDate 1 }

-- NTP (Network Time Protocol) group

devNTPServerIP OBJECT-TYPE
    SYNTAX  IpAddress
    ACCESS  read-write
    STATUS  mandatory
    DESCRIPTION
        "This Objects allows an NMS to configure theNTP server 
         IP address"
    ::= { devNTP 1 }

devNTPMode OBJECT-TYPE
    SYNTAX  NTPMode
    ACCESS  read-write
    STATUS  mandatory
    DESCRIPTION
        "This Objects allows an NMS to configure the mode NTP will operate in
         Unicast mode -- In this mode NTP will poll a specific server. In this 
         mode it is necessary for a NTP server to be configured using the 
         NTPServerIP object Broadcast Mode -- In this  mode NTP will broadcast
        a request and any NTP server could respond Default value is Broadcast"
    ::= { devNTP 2 }

devNTPSynchronised OBJECT-TYPE
        SYNTAX  INTEGER (1 .. 24)
    ACCESS  read-write
    STATUS  mandatory
    DESCRIPTION
        "This Objects allows an NMS to configure the time interval (in hrs)    
         when the device will synchronize its clock with the NTP server
         Default value is 1"
     ::= { devNTP 3 }

END
