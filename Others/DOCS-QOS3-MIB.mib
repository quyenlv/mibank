-- *****************************************************************
-- DOCS-QOS3-MIB.my:
--
-- Aug 2007 Yueping Ye 
--
-- Initial Version: Aug 2007: Annex Q.7 from CM-SP-OSSIv3.0-I04-070803
--
-- Copyright (c) 2007 by cisco Systems, Inc.
-- All rights reserved.
-- *****************************************************************

DOCS-QOS3-MIB DEFINITIONS ::= BEGIN 
  IMPORTS 
    MODULE-IDENTITY, 
    OBJECT-TYPE, 
    Unsigned32, 
    Counter32, 
    Counter64 
             FROM SNMPv2-SMI           -- RFC 2578 
    TEXTUAL-CONVENTION, 
    RowStatus, 
    TruthValue, 
    MacAddress, 
    TimeStamp, 
    StorageType 
             FROM SNMPv2-TC            -- RFC 2579 
    OBJECT-GROUP, 
    MODULE-COMPLIANCE 
             FROM SNMPv2-CONF          -- RFC 2580 
    SnmpAdminString 
             FROM SNMP-FRAMEWORK-MIB   -- RFC 3411 
    InterfaceIndex, 
    ifIndex 
             FROM IF-MIB               -- RFC 2863 
    InetAddressType, 
    InetAddress, 
    InetPortNumber 
             FROM INET-ADDRESS-MIB 
    DscpOrAny 
             FROM DIFFSERV-DSCP-TC 
    DocsL2vpnIfList 
             FROM DOCS-L2VPN-MIB 
 
    AttributeMask, 
    AttrAggrRuleMask, 
    ChSetId, 
    Dsid, 
    ChId, 
    ChannelList 
             FROM DOCS-IF3-MIB 
    clabProjDocsis 
             FROM CLAB-DEF-MIB; 
 
docsQos3Mib MODULE-IDENTITY 
     LAST-UPDATED    "200708030000Z" -- August 03, 2007 
     ORGANIZATION    "Cable Television Laboratories, Inc." 
     CONTACT-INFO 
        "Postal: Cable Television Laboratories, Inc. 
        858 Coal Creek Circle 
        Louisville, Colorado 80027-9750 
        U.S.A. 
        Phone: +1 303-661-9100 
        Fax:   +1 303-661-9199 
        E-mail: mibs@cablelabs.com" 
     DESCRIPTION 
        "This MIB module contains the management objects for the 
        management of QOS for channel bonding." 
     REVISION        "200708030000Z" -- August 03, 2007 
     DESCRIPTION 
        "Revised Version includes ECN OSSIv3.0-N-07.0480-3 
        and published as I04" 
     REVISION        "200705180000Z" -- May 18, 2007 
     DESCRIPTION 
        "Revised Version includes ECNs 
        OSSIv3.0-N-07.0445-3 
        OSSIv3.0-N-07.0437-4 
        OSSIv3.0-N-07.0412-2 
        OSSIv3.0-N-07.0410-4 
        and published as I03" 
     REVISION        "200612071700Z" -- Dec 7, 2006 
     DESCRIPTION 
        "Initial version, published as part of the CableLabs 
        OSSIv3.0 specification CM-SP-OSSIv3.0-I01-061207 
        Copyright 1999-2007 Cable Television Laboratories, Inc. 
        All rights reserved." 
     ::= {  clabProjDocsis 21 } 
 
-- Textual Conventions 
 
IfDirection ::= TEXTUAL-CONVENTION 
    STATUS      current 
    DESCRIPTION 
       "Indicates a direction on an RF MAC interface. 
       The value downstream(1) is from Cable Modem 
       Termination System to Cable Modem. 
 
       The value upstream(2) is from Cable Modem to 
       Cable Modem Termination System." 
    SYNTAX      INTEGER { 
                         downstream(1), 
                         upstream(2) 
                        } 
 
BitRate ::= TEXTUAL-CONVENTION 
    DISPLAY-HINT "d" 
    STATUS      current 
    DESCRIPTION 
       "The rate of traffic in unit of bits per second. 
       Used to specify traffic rate for QOS." 
    SYNTAX          Unsigned32 
 
SchedulingType ::= TEXTUAL-CONVENTION 
    STATUS          current 
    DESCRIPTION 
       "The scheduling service provided by a CMTS for an 
       upstream Service Flow.  If the parameter is omitted 
       from an upstream QOS Parameter Set, this object 
       takes the value of bestEffort (2).  This parameter 
       must be reported as undefined (1) for downstream 
       QOS Parameter Sets." 
    SYNTAX      INTEGER { 
                         undefined (1), 
                         bestEffort (2), 
                         nonRealTimePollingService(3), 
                         realTimePollingService(4), 
                         unsolictedGrantServiceWithAD(5), 
                         unsolictedGrantService(6) 
                        } 
 
docsQos3MibObjects  OBJECT IDENTIFIER ::= { docsQos3Mib 1 } 
 
docsQos3PktClassTable OBJECT-TYPE 
     SYNTAX      SEQUENCE OF DocsQos3PktClassEntry 
     MAX-ACCESS  not-accessible 
     STATUS      current 
     DESCRIPTION 
        "This object describes the packet classification 
        configured on the CM or CMTS. 
        The model is that a packet either received as input from 
        an interface or transmitted for output on an interface 
        may be compared against an ordered list of rules 
        pertaining to the packet contents.  Each rule is an instance 
        of this object.  A matching rule provides a Service 
        Flow ID to which the packet is classified. 
        All rules need to match for a packet to match a classifier. 
         
         
        The attibutes in this row correspond to a set of Classifier 
        Encoding parameters in a DOCSIS MAC management 
        message.  The BitMap attribute indicates which particular 
        parameters were present in the classifier as 
        signaled in the DOCSIS message. 
        If the referenced parameter was not present in the signaled 
        Classifier, the corresponding attribute in 
        this instance reports a value as specified by that attribute 
        description." 
     REFERENCE 
        "DOCSIS 3.0 MAC and Upper Layer Protocols Interface 
        Specification CM-SP-MULPIv3.0-I05-070803, Service Flows and  
        Classifiers section."        
        ::= { docsQos3MibObjects 1} 
 
docsQos3PktClassEntry OBJECT-TYPE 
     SYNTAX      DocsQos3PktClassEntry 
     MAX-ACCESS  not-accessible 
     STATUS      current 
     DESCRIPTION 
        "The conceptual row of docsQos3PktClassTable. 
         The ifIndex key corresponds to the MAC Domain interface 
         of the service flow of this classifier." 
     INDEX { ifIndex,docsQos3ServiceFlowId,docsQos3PktClassId } 
     ::= { docsQos3PktClassTable 1 } 
 
DocsQos3PktClassEntry ::= SEQUENCE { 
     docsQos3PktClassId 
                  Unsigned32, 
     docsQos3PktClassDirection 
                  IfDirection, 
     docsQos3PktClassPriority 
                  Unsigned32, 
     docsQos3PktClassIpTosLow 
                  OCTET STRING, 
     docsQos3PktClassIpTosHigh 
                  OCTET STRING, 
     docsQos3PktClassIpTosMask 
                  OCTET STRING, 
     docsQos3PktClassIpProtocol 
                  Unsigned32, 
     docsQos3PktClassIpSourceAddr 
                  InetAddress, 
     docsQos3PktClassIpSourceMask 
                  InetAddress, 
     docsQos3PktClassIpDestAddr 
                  InetAddress, 
     docsQos3PktClassIpDestMask 
                  InetAddress, 
     docsQos3PktClassSourcePortStart 
                  InetPortNumber, 
     docsQos3PktClassSourcePortEnd 
                  InetPortNumber, 
     docsQos3PktClassDestPortStart 
                  InetPortNumber, 
     docsQos3PktClassDestPortEnd 
                  InetPortNumber, 
     docsQos3PktClassDestMacAddr 
                  MacAddress, 
     docsQos3PktClassDestMacMask 
                  MacAddress, 
     docsQos3PktClassSourceMacAddr 
                  MacAddress, 
     docsQos3PktClassEnetProtocolType 
                  INTEGER, 
     docsQos3PktClassEnetProtocol 
                  Unsigned32, 
     docsQos3PktClassUserPriLow 
                  Unsigned32, 
     docsQos3PktClassUserPriHigh 
                  Unsigned32, 
     docsQos3PktClassVlanId 
                  Unsigned32, 
     docsQos3PktClassState 
                  INTEGER, 
     docsQos3PktClassPkts 
                  Counter64, 
     docsQos3PktClassBitMap 
                  BITS, 
     docsQos3PktClassIpAddrType 
                  InetAddressType, 
     docsQos3PktClassFlowLabel 
                  Unsigned32, 
     docsQos3PktClassCmInterfaceMask 
                  DocsL2vpnIfList 
     } 
 
docsQos3PktClassId OBJECT-TYPE 
     SYNTAX      Unsigned32 (1..65535) 
     MAX-ACCESS  not-accessible 
     STATUS      current 
     DESCRIPTION 
        "This key indicates the assigned identifier to the 
        packet classifier instance by the CMTS, which is unique 
        per Service Flow. 
        For UDCs this corresponds to the Service Flow Reference 
        of the classifier." 
     REFERENCE 
        "DOCSIS 3.0 MAC and Upper Layer Protocols Interface 
        Specification CM-SP-MULPIv3.0-I05-070803, Classifier  
        Identifier section in the Common Radio Frequency Interface 
        Encodings Annex." 
     ::= { docsQos3PktClassEntry 1 } 
 
docsQos3PktClassDirection OBJECT-TYPE 
     SYNTAX      IfDirection 
     MAX-ACCESS  read-only 
     STATUS      current 
     DESCRIPTION 
        "This attribute indicates the direction to which the 
        classifier is applied." 
     ::= { docsQos3PktClassEntry 2 } 
 
docsQos3PktClassPriority OBJECT-TYPE 
     SYNTAX      Unsigned32 (0..255) 
     MAX-ACCESS  read-only 
     STATUS      current 
     DESCRIPTION 
        "This attribute specifies the order of evaluation 
        of the classifiers. 
        The higher the value, the higher the priority. 
        The value of 0 is used as default in provisioned Service 
        Flows Classifiers. 
        The default value of 64 is used for dynamic Service Flow 
        Classifiers. 
         
        If the referenced parameter is not present in a classifier, 
        this attribute reports the default 
        value as defined above." 
     REFERENCE 
        "DOCSIS 3.0 MAC and Upper Layer Protocols Interface 
        Specification CM-SP-MULPIv3.0-I05-070803, Rule Priority  
        section in the Common Radio Frequency Interface Encodings 
        Annex." 
     ::= { docsQos3PktClassEntry 3 } 
 
docsQos3PktClassIpTosLow OBJECT-TYPE 
     SYNTAX      OCTET STRING (SIZE (1)) 
     MAX-ACCESS  read-only 
     STATUS      current 
     DESCRIPTION 
        "This attribute indicates the low value of a range of 
        TOS byte values. 
        If the referenced parameter is not present in a classifier, 
        this attribute reports the value of 0. 
         
        The IP TOS octet, as originally defined in RFC 791, has 
        been superseded by the 6-bit Differentiated Services 
        Field (DSField, RFC 3260) and the 2-bit Explicit 
        Congestion Notification Field (ECN field, RFC 3168). 
        This object is defined as an 8-bit octet as per the DOCSIS 
        Specification for packet classification."  
     REFERENCE 
        "DOCSIS 3.0 MAC and Upper Layer Protocols Interface 
        Specification CM-SP-MULPIv3.0-I05-070803, IPv4 Type of  
        Service Range and Mask and IPv6 Traffic Class Range and  
        Mask sections in the Common Radio Frequency Interface  
        Encodings Annex." 
     ::= { docsQos3PktClassEntry 4 } 
 
docsQos3PktClassIpTosHigh OBJECT-TYPE 
     SYNTAX      OCTET STRING (SIZE (1)) 
     MAX-ACCESS  read-only 
     STATUS      current 
     DESCRIPTION 
        "This attribute indicates the 8-bit high value of a 
        range of TOS byte values. 
        If the referenced parameter is not present in a classifier, 
        this attribute reports the value of 0. 
        The IP TOS octet as originally defined in RFC 791 has been 
        superseded by the 6-bit Differentiated Services 
        Field (DSField, RFC 3260) and the 2-bit Explicit Congestion 
        Notification Field (ECN field, RFC 3168). 
        This object is defined as an 8-bit octet as defined by 
        the DOCSIS Specification for packet classification." 
     REFERENCE 
        "DOCSIS 3.0 MAC and Upper Layer Protocols Interface 
        Specification CM-SP-MULPIv3.0-I05-070803, IPv4 Type of  
        Service Range and Mask and IPv6 Traffic Class Range and  
        Mask sections in the Common Radio Frequency Interface  
        Encodings Annex." 
     ::= { docsQos3PktClassEntry 5 } 
 
docsQos3PktClassIpTosMask OBJECT-TYPE 
     SYNTAX      OCTET STRING (SIZE (1)) 
     MAX-ACCESS  read-only 
     STATUS      current 
     DESCRIPTION 
        "This attribute indicates the mask value is bitwise 
        ANDed with TOS byte in an IP packet, and this value is 
        used for range checking of TosLow and TosHigh. 
         
        If the referenced parameter is not present in a classifier, 
        this attribute reports the value of 0. 
         
        The IP TOS octet as originally defined in RFC 791 has been 
        superseded by the 6-bit Differentiated Services 
        Field (DSField, RFC 3260) and the 2-bit Explicit Congestion 
        Notification Field (ECN field, RFC 3168). 
        This object is defined as an 8-bit octet per the DOCSIS 
        Specification for packet classification." 
     REFERENCE 
        "DOCSIS 3.0 MAC and Upper Layer Protocols Interface 
        Specification CM-SP-MULPIv3.0-I05-070803, IPv4 Type of  
        Service Range and Mask and IPv6 Traffic Class Range and  
        Mask sections in the Common Radio Frequency Interface  
        Encodings Annex." 
     ::= { docsQos3PktClassEntry 6 } 
 
docsQos3PktClassIpProtocol OBJECT-TYPE 
     SYNTAX      Unsigned32 (0..258) 
     MAX-ACCESS  read-only 
     STATUS      current 
     DESCRIPTION 
        "This attribute indicates the value of the IP Protocol 
        field required for IP packets to match this rule. 
         
        The value 256 matches traffic with any IP Protocol value. 
        The value 257 by convention matches both TCP and 
        UDP. 
        If the referenced parameter is not present in a classifier, 
        this attibute reports the value of 258." 
     REFERENCE 
        "DOCSIS 3.0 MAC and Upper Layer Protocols Interface 
        Specification CM-SP-MULPIv3.0-I05-070803, IP Protocol and  
        IPv6 Next Header Type sections in the Common Radio Frequency 
        Interface Encodings Annex." 
     ::= { docsQos3PktClassEntry 7 } 
 
docsQos3PktClassIpSourceAddr OBJECT-TYPE 
     SYNTAX      InetAddress 
     MAX-ACCESS  read-only 
     STATUS      current 
     DESCRIPTION 
        "This attribute specifies the value of the IP Source 
        Address required for packets to match this rule. 
        An IP packet matches the rule when the packet IP Source 
        Address bitwise ANDed with the InetSourceMask value 
        equals the InetSourceAddr value. 
        The address type of this object is specified by InetAddressType. 
         
        If the referenced parameter is not present in a classifier, 
        this object reports the value of '00000000'H." 
     REFERENCE 
        "DOCSIS 3.0 MAC and Upper Layer Protocols Interface 
        Specification CM-SP-MULPIv3.0-I05-070803, IPv4 Source Address 
        and IPv6 Source Address sections in the Common Radio Frequency 
        Interface Encodings Annex." 
     ::= { docsQos3PktClassEntry 8 } 
 
docsQos3PktClassIpSourceMask OBJECT-TYPE 
     SYNTAX      InetAddress 
     MAX-ACCESS  read-only 
     STATUS      current 
     DESCRIPTION 
        "This attribute specifies which bits of a packet's 
        IP Source Address are compared to match this rule. 
        An IP packet matches the rule when the packet source address 
        bitwise ANDed with the InetSourceMask value 
        equals the docsIetfQosIpPktClassInetSourceAddr 
        value. 
        The address type of this attribute is specified by InetAddressType. 
         
        If the referenced parameter is not present in a classifier, 
        this attribute reports the value of 'FFFFFFFF'H." 
     REFERENCE 
        "DOCSIS 3.0 MAC and Upper Layer Protocols Interface 
        Specification CM-SP-MULPIv3.0-I05-070803, IPv4 Source Mask 
        and IPv6 Source Prefix Length (bits) sections in the Common Radio 
        Frequency Interface Encodings Annex." 
     ::= { docsQos3PktClassEntry 9 } 
 
docsQos3PktClassIpDestAddr OBJECT-TYPE 
     SYNTAX      InetAddress 
     MAX-ACCESS  read-only 
     STATUS      current 
     DESCRIPTION 
        "This attribute specifies the value of the IP Destination 
        Address required for packets to match this rule. 
         
        An IP packet matches the rule when the packet IP Destination 
        Address bitwise ANDed with the InetDestMask 
        value equals the InetDestAddr value. 
        The address type of this attribute is specified by  
        InetAddressType. 
         
        If the referenced parameter is not present in a classifier, 
        this attribute reports the value of '00000000'H." 
     REFERENCE 
        "DOCSIS 3.0 MAC and Upper Layer Protocols Interface 
        Specification CM-SP-MULPIv3.0-I05-070803, IPv4 Destination  
        Address and IPv6 Destination Address sections in the Common 
        Radio Frequency Interface Encodings Annex." 
     ::= { docsQos3PktClassEntry 10 } 
 
docsQos3PktClassIpDestMask OBJECT-TYPE 
     SYNTAX      InetAddress 
     MAX-ACCESS  read-only 
     STATUS      current 
     DESCRIPTION 
        "This attribute specifies which bits of a packet's 
        IP Destination Address are compared to match this rule. 
         
        An IP packet matches the rule when the packet destination 
        address bitwise ANDed with the InetDestMask value 
        equals the docsIetfQosIpPktClassInetDestAddr 
        value. 
        The address type of this attribute is specified by InetAddressType. 
         
        If the referenced parameter is not present in a classifier, 
        this attribute reports the value of 'FFFFFFFF'H." 
     REFERENCE 
        "DOCSIS 3.0 MAC and Upper Layer Protocols Interface 
        Specification CM-SP-MULPIv3.0-I05-070803, IPv4 Destination 
        Mask and IPv6 Destination Prefix Length (bits) sections in 
        the Common Radio Frequency Interface Encodings Annex." 
     ::= { docsQos3PktClassEntry 11 } 
 
docsQos3PktClassSourcePortStart OBJECT-TYPE 
     SYNTAX      InetPortNumber 
     MAX-ACCESS  read-only 
     STATUS      current 
     DESCRIPTION 
        "This attribute specifies the low-end inclusive range 
        of TCP/UDP source port numbers to which a packet 
        is compared.  This attribute is irrelevant for non-TCP/UDP 
        IP packets. 
        If the referenced parameter is not present in a classifier, 
        this attribute reports the value of 0." 
     REFERENCE 
        "DOCSIS 3.0 MAC and Upper Layer Protocols Interface 
        Specification CM-SP-MULPIv3.0-I05-070803, TCP/UDP Source 
        Port Start section in the Common Radio Frequency Interface 
        Encodings Annex." 
     ::= { docsQos3PktClassEntry 12 } 
 
docsQos3PktClassSourcePortEnd OBJECT-TYPE 
     SYNTAX      InetPortNumber 
     MAX-ACCESS  read-only 
     STATUS      current 
     DESCRIPTION 
        "This attribute specifies the high-end inclusive 
        range of TCP/UDP source port numbers to which a packet 
        is compared.  This attribute is irrelevant for non-TCP/UDP 
        IP packets. 
        If the referenced parameter is not present in a classifier, 
        this attribute reports the value of 65535." 
     REFERENCE 
        "DOCSIS 3.0 MAC and Upper Layer Protocols Interface 
        Specification CM-SP-MULPIv3.0-I05-070803, TCP/UDP Source 
        Port End section in the Common Radio Frequency Interface  
        Encodings Annex." 
     ::= { docsQos3PktClassEntry 13 } 
 
docsQos3PktClassDestPortStart OBJECT-TYPE 
     SYNTAX      InetPortNumber 
     MAX-ACCESS  read-only 
     STATUS      current 
     DESCRIPTION 
        "This attribute specifies the low-end inclusive  range 
        of TCP/UDP destination port numbers to which a packet 
        is compared. 
        If the referenced parameter is not present in a classifier, 
        this attribute reports the value of 0." 
     REFERENCE 
        "DOCSIS 3.0 MAC and Upper Layer Protocols Interface 
        Specification CM-SP-MULPIv3.0-I05-070803, TCP/UDP 
        Destination Port Start section in the Common Radio Frequency 
        Interface Encodings Annex." 
     ::= { docsQos3PktClassEntry 14 } 
 
docsQos3PktClassDestPortEnd OBJECT-TYPE 
     SYNTAX      InetPortNumber 
     MAX-ACCESS  read-only 
     STATUS      current 
     DESCRIPTION 
        "This attribute specifies the high-end inclusive 
        range of TCP/UDP destination port numbers to which a 
        packet is compared. 
        If the referenced parameter is not present in a classifier, 
        this attribute reports the value of 65535." 
     REFERENCE 
        "DOCSIS 3.0 MAC and Upper Layer Protocols Interface 
        Specification CM-SP-MULPIv3.0-I05-070803, TCP/UDP Destination 
        Port End section in the Common Radio Frequency Interface 
        Encodings Annex." 
     ::= { docsQos3PktClassEntry 15 } 
 
docsQos3PktClassDestMacAddr OBJECT-TYPE 
     SYNTAX      MacAddress 
     MAX-ACCESS  read-only 
     STATUS      current 
     DESCRIPTION 
        "An Ethernet packet matches an entry when its destination 
        MAC address bitwise ANDed with DestMacMask equals 
        the value of DestMacAddr. 
        If the referenced parameter is not present in a classifier, 
        this attribute reports the value of '000000000000'H." 
     REFERENCE 
        "DOCSIS 3.0 MAC and Upper Layer Protocols Interface 
        Specification CM-SP-MULPIv3.0-I05-070803, Destination MAC  
        Address section in the Common Radio Frequency Interface 
        Encodings Annex." 
     ::= { docsQos3PktClassEntry 16 } 
 
docsQos3PktClassDestMacMask OBJECT-TYPE 
     SYNTAX      MacAddress 
     MAX-ACCESS  read-only 
     STATUS      current 
     DESCRIPTION 
        "An Ethernet packet matches an entry when its destination 
        MAC address bitwise ANDed with DestMacMask equals 
        the value of DestMacAddr. 
        If the referenced parameter is not present in a classifier, 
        this attribute reports the value of '000000000000'H." 
     REFERENCE 
        "DOCSIS 3.0 MAC and Upper Layer Protocols Interface 
        Specification CM-SP-MULPIv3.0-I05-070803, Destination  
        MAC Address section in the Common Radio Frequency Interface 
        Encodings Annex." 
     ::= { docsQos3PktClassEntry 17 } 
 
docsQos3PktClassSourceMacAddr OBJECT-TYPE 
     SYNTAX      MacAddress 
     MAX-ACCESS  read-only 
     STATUS      current 
     DESCRIPTION 
        "An Ethernet packet matches this entry when its source 
        MAC address equals the value of this attribute. 
        If the referenced parameter is not present in a classifier, 
        this attribute reports the value of 'FFFFFFFFFFFF'" 
     REFERENCE 
        "DOCSIS 3.0 MAC and Upper Layer Protocols Interface 
        Specification CM-SP-MULPIv3.0-I05-070803, Source MAC  
        Address section in the Common Radio Frequency Interface 
        Encodings Annex." 
     ::= { docsQos3PktClassEntry 18 } 
 
docsQos3PktClassEnetProtocolType OBJECT-TYPE 
     SYNTAX      INTEGER { 
 
                        none(0), 
                        ethertype(1), 
                        dsap(2), 
                        mac(3), 
                        all(4) 
                      } 
     MAX-ACCESS  read-only 
     STATUS      current 
     DESCRIPTION 
        "This attribute indicates the format of the layer 3 
        protocol ID in the Ethernet packet.  A value of 'none' 
        means that the rule does not use the layer 3 protocol type 
        as a matching criteria. 
        A value of 'ethertype' means that the rule applies only 
        to frames that contain an EtherType value.  Ethertype 
        values are contained in packets using the Dec-Intel-Xerox 
        (DIX) encapsulation or the RFC1042 Sub-Network 
        Access Protocol (SNAP) encapsulation formats. 
         
        A value of 'dsap' means that the rule applies only to frames 
        using the IEEE802.3 encapsulation format with 
        a Destination Service Access Point (DSAP) other than 
        0xAA (which is reserved for SNAP). 
         
        A value of 'mac' means that the rule applies only to MAC 
        management messages for MAC management messages. 
         
        A value of 'all' means that the rule matches all Ethernet 
        packets. 
        If the Ethernet frame contains an 802.1P/Q Tag header 
        (i.e., EtherType 0x8100), this attribute applies 
        to the embedded EtherType field within the 802.1P/Q 
        header. 
        If the referenced parameter is not present in a classifier, 
        this attribute reports the value of 0." 
     REFERENCE 
        "DOCSIS 3.0 MAC and Upper Layer Protocols Interface 
        Specification CM-SP-MULPIv3.0-I05-070803,  
        Ethertype/DSAP/MacType section in the Common Radio  
        Frequency Interface Encodings Annex." 
     ::= { docsQos3PktClassEntry 19 } 

docsQos3PktClassEnetProtocol OBJECT-TYPE 
     SYNTAX      Unsigned32 (0..65535) 
     MAX-ACCESS  read-only 
     STATUS      current 
     DESCRIPTION 
        "If EnetProtocolType is 'none', this attribute is 
        ignored when considering whether a packet matches the 
        current rule. 
        If EnetProtocolType is 'ethertype', this attribute 
        gives the 16-bit value of the EtherType that the packet 
        must match in order to match the rule. 
        If EnetProtocolType is 'dsap', the lower 8 bits of this 
        attribute's value must match the DSAP byte of the packet 
        in order to match the rule. 
        If EnetProtocolType is 'mac', the lower 8 bits of this 
        attribute's value represent a 
        lower bound (inclusive) of MAC management message type 
        codes matched, and the upper 8 bits represent the 
        upper bound (inclusive) of matched MAC message type 
        codes.  Certain message type codes are excluded from 
        matching, as specified in the reference. 
        If the Ethernet frame contains an 802.1P/Q Tag header 
        (i.e., EtherType 0x8100), this attribute applies 
        to the embedded EtherType field within the 802.1P/Q 
        header. 
        If the referenced parameter is not present in the classifier, 
        the value of this attribute is reported as 0." 
     REFERENCE 
        "DOCSIS 3.0 MAC and Upper Layer Protocols Interface 
        Specification CM-SP-MULPIv3.0-I05-070803,  
        Ethertype/DSAP/MacType section in the Common Radio  
        Frequency Interface Encodings Annex." 
     ::= { docsQos3PktClassEntry 20 } 
 
docsQos3PktClassUserPriLow OBJECT-TYPE 
     SYNTAX      Unsigned32 (0..7) 
     MAX-ACCESS  read-only 
     STATUS      current 
     DESCRIPTION 
        "This attribute applies only to Ethernet frames using 
        the 802.1P/Q tag header (indicated with EtherType 
        0x8100).  Such frames include a 16-bit Tag that contains 
        a 3-bit Priority field and a 12-bit VLAN number. 
         
        Tagged Ethernet packets must have a 3-bit Priority field 
        within the range of PriLow to PriHigh in order to 
        match this rule.  
        If the referenced parameter is not present in the classifier, 
        the value of this attribute is reported as 0." 
     REFERENCE 
        "DOCSIS 3.0 MAC and Upper Layer Protocols Interface 
        Specification CM-SP-MULPIv3.0-I05-070803, IEEE 802.1P  
        User_Priority section in the Common Radio Frequency Interface 
        Encodings Annex." 
     ::= { docsQos3PktClassEntry 22 } 
 
docsQos3PktClassUserPriHigh OBJECT-TYPE 
     SYNTAX      Unsigned32 (0..7) 
     MAX-ACCESS  read-only 
     STATUS      current 
     DESCRIPTION 
        "This attribute applies only to Ethernet frames using 
        the 802.1P/Qtag header (indicated with EtherType 
        0x8100).  Such frames include a 16-bit Tag that contains 
        a 3-bit Priority field and a 12-bit VLAN number. 
         
        Tagged Ethernet packets must have a 3-bit Priority field 
        within the range of PriLow to 
        PriHigh in order to match this rule. 
        If the referenced parameter is not present in the classifier, 
        the value of this attribute is reported as 7." 
     REFERENCE 
        "DOCSIS 3.0 MAC and Upper Layer Protocols Interface 
        Specification CM-SP-MULPIv3.0-I05-070803, IEEE 802.1P  
        User_Priority section in the Common Radio Frequency Interface 
        Encodings Annex." 
     ::= { docsQos3PktClassEntry 23 } 
 
docsQos3PktClassVlanId OBJECT-TYPE 
     SYNTAX      Unsigned32 (0 | 1..4094) 
     MAX-ACCESS  read-only 
     STATUS      current 
     DESCRIPTION 
        "This attribute applies only to Ethernet frames 
        using the 802.1P/Q tag header.  
        Tagged packets must have a VLAN Identifier that matches 
        the value in order to match the rule. 
        If the referenced parameter is not present in the classifier, 
        the value of this attribute is reported as 0." 
     REFERENCE 
        "DOCSIS 3.0 MAC and Upper Layer Protocols Interface 
        Specification CM-SP-MULPIv3.0-I05-070803, IEEE 802.1Q VLAN_ID 
        section in the Common Radio Frequency Interface Encodings Annex." 
     ::= { docsQos3PktClassEntry 24 } 
 
docsQos3PktClassState OBJECT-TYPE 
     SYNTAX      INTEGER { 
 
                        active(1), 
                        inactive(2) 
                      } 
     MAX-ACCESS  read-only 
     STATUS      current 
     DESCRIPTION 
        "This attribute indicates whether or not the classifier 
        is enabled to classify packets to a Service Flow. 
         
        If the referenced parameter is not present in the classifier, 
        the value of this attribute is reported as 'true'." 
     REFERENCE 
        "DOCSIS 3.0 MAC and Upper Layer Protocols Interface 
        Specification CM-SP-MULPIv3.0-I05-070803, Classifier  
        Activation State section in the Common Radio Frequency Interface 
        Encodings Annex." 
     ::= { docsQos3PktClassEntry 25 } 
 
docsQos3PktClassPkts OBJECT-TYPE 
     SYNTAX      Counter64 
     MAX-ACCESS  read-only 
     STATUS      current 
     DESCRIPTION 
        "This attribute counts the number of packets that have 
        been classified using this entry. This includes 
        all packets delivered to a Service Flow maximum rate 
        policing function, whether or not that function drops 
        the packets. 
        This counter's last discontinuity is the  
        ifCounterDiscontinuityTime for the same ifIndex that  
        indexes this attribute." 
     ::= { docsQos3PktClassEntry 26 } 
 
docsQos3PktClassBitMap OBJECT-TYPE 
     SYNTAX      BITS { 
                        rulePriority(0), 
                        activationState(1), 
                        ipTos(2), 
                        ipProtocol(3), 
                        ipSourceAddr(4), 
                        ipSourceMask(5), 
                        ipDestAddr(6), 
                        ipDestMask(7), 
                        sourcePortStart(8), 
                        sourcePortEnd(9), 
                        destPortStart(10), 
                        destPortEnd(11), 
                        destMac(12), 
                        sourceMac(13), 
                        ethertype(14), 
                        userPri(15), 
                        vlanId(16), 
                        flowLabel(17), 
                        cmInterfaceMask(18) 
                      } 
     MAX-ACCESS  read-only 
     STATUS      current 
     DESCRIPTION 
        "This attribute indicates which parameter encodings 
        were actually present in the DOCSIS packet classifier 
        encoding signaled in the DOCSIS message that created 
        or modified the classifier.  Note that Dynamic 
        Service Change messages have replace semantics, so 
        that all non-default parameters must be present whether 
        the classifier is being created or changed. 
        A bit of this attribute is set to 1 if the parameter indicated 
        by the comment was present in the classifier encoding, 
        and to 0 otherwise. 
        Note that BITS are encoded most significant bit first, 
        so that if, for example, bits 6 and 7 are set, this attribute 
        is encoded as the octet string '030000'H." 
     ::= { docsQos3PktClassEntry 27 } 
 
docsQos3PktClassIpAddrType OBJECT-TYPE 
     SYNTAX      InetAddressType 
     MAX-ACCESS  read-only 
     STATUS      current 
     DESCRIPTION 
        "This attribute indicates the type of the Internet 
        address for InetSourceAddr, InetSourceMask, InetDestAddr, 
        and InetDestMask. 
        If the referenced parameter is not present in a classifier, 
        this object reports the value of 'ipv4'." 
     ::= { docsQos3PktClassEntry 28 } 
 
docsQos3PktClassFlowLabel OBJECT-TYPE 
     SYNTAX      Unsigned32 (0..1048575) 
     MAX-ACCESS  read-only 
     STATUS      current 
     DESCRIPTION 
        "This attribute represents the Flow Label field in 
        the IPv6 header to be matched by the classifier. 
        The value zero indicates that the Flow Label is not specified 
        as part of the classifier and is not matched against 
        the packets." 
     REFERENCE 
        "DOCSIS 3.0 MAC and Upper Layer Protocols Interface 
        Specification CM-SP-MULPIv3.0-I05-070803, IPv6 Flow Label 
        section in the Common Radio Frequency Interface Encodings 
        Annex." 
     ::= { docsQos3PktClassEntry 29 } 

docsQos3PktClassCmInterfaceMask OBJECT-TYPE 
     SYNTAX      DocsL2vpnIfList 
     MAX-ACCESS  read-only 
     STATUS      current 
     DESCRIPTION 
        "This attribute represents a bit-mask of the CM in-bound 
        interfaces to which this classifer applies. 
        This attribute only applies to QOS upstream Classifiers 
        and upstream Drop Classifiers. For QOS downstream 
        classifiers this object reports the zero-length 
        string." 
     REFERENCE 
        "DOCSIS 3.0 MAC and Upper Layer Protocols Interface 
        Specification CM-SP-MULPIv3.0-I05-070803, CM Interface 
        Mask (CMIM) Encoding section in the Common Radio Frequency 
        Interface Encodings Annex." 
     ::= { docsQos3PktClassEntry 30 } 
 
docsQos3ParamSetTable OBJECT-TYPE 
     SYNTAX      SEQUENCE OF DocsQos3ParamSetEntry 
     MAX-ACCESS  not-accessible 
     STATUS      current 
     DESCRIPTION 
        "This object describes the set of QOS parameters defined 
        in a managed device. 
        DOCSIS 1.0 COS service profiles are not represented 
        in this object. 
        Each row corresponds to a DOCSIS QOS Parameter Set as 
        signaled via DOCSIS MAC management messages.Each attribute 
        of an instance of this object corresponds to 
        one or part of oneService Flow Encoding. 
        The BitMap attribute indicates which particular parameters 
        were signaled in the original registration 
        or dynamic service request message that created the 
        QOS Parameter Set. 
        In many cases, even if a QOS Parameter Set parameter was 
        not signaled, the DOCSIS specification calls for 
        a default value to be used.  That default value is reported 
        as the value of the corresponding attribute in this 
        object instance. 
         
        Many attributes are not applicable, depending on the 
        Service Flow direction, upstream scheduling type 
        or Service Flow bonding configuration.  The attribute 
        value reported in this case is specified by those attributes 
        descriptions." 
     REFERENCE 
        "DOCSIS 3.0 MAC and Upper Layer Protocols Interface 
        Specification CM-SP-MULPIv3.0-I05-070803, Service Flow  
        Encodings section in the Common Radio Frequency Interface 
        Encodings Annex." 
     ::= { docsQos3MibObjects 2} 
 
docsQos3ParamSetEntry OBJECT-TYPE 
     SYNTAX      DocsQos3ParamSetEntry 
     MAX-ACCESS  not-accessible 
     STATUS      current 
     DESCRIPTION 
        "The conceptual row of docsQos3ParamSetTable. 
         The ifIndex key corresponds to the MAC Domain interface of the 
         service flow of this Qos Param Set." 
     INDEX { ifIndex,docsQos3ParamSetType,docsQos3ParamSetServiceFlowId } 
     ::= { docsQos3ParamSetTable 1 } 
 
DocsQos3ParamSetEntry ::= SEQUENCE { 
     docsQos3ParamSetServiceClassName 
                  SnmpAdminString, 
     docsQos3ParamSetPriority 
                  Unsigned32, 
     docsQos3ParamSetMaxTrafficRate 
                  BitRate, 
     docsQos3ParamSetMaxTrafficBurst 
                  Unsigned32, 
     docsQos3ParamSetMinReservedRate 
                  BitRate, 
     docsQos3ParamSetMinReservedPkt 
                  Unsigned32, 
     docsQos3ParamSetActiveTimeout 
                  Unsigned32, 
     docsQos3ParamSetAdmittedTimeout 
                  Unsigned32, 
     docsQos3ParamSetMaxConcatBurst 
                  Unsigned32, 
     docsQos3ParamSetSchedulingType 
                  SchedulingType, 
     docsQos3ParamSetNomPollInterval 
                  Unsigned32, 
     docsQos3ParamSetTolPollJitter 
                  Unsigned32, 
     docsQos3ParamSetUnsolicitGrantSize 
                  Unsigned32, 
     docsQos3ParamSetNomGrantInterval 
                  Unsigned32, 
     docsQos3ParamSetTolGrantJitter 
                  Unsigned32, 
     docsQos3ParamSetGrantsPerInterval 
                  Unsigned32, 
     docsQos3ParamSetTosAndMask 
                  OCTET STRING, 
     docsQos3ParamSetTosOrMask 
                  OCTET STRING, 
     docsQos3ParamSetMaxLatency 
                  Unsigned32, 
     docsQos3ParamSetType 
                  INTEGER, 
     docsQos3ParamSetRequestPolicyOct 
                  OCTET STRING, 
     docsQos3ParamSetBitMap 
                  BITS, 
     docsQos3ParamSetServiceFlowId 
                  Unsigned32, 
     docsQos3ParamSetRequiredAttrMask 
                  AttributeMask, 
     docsQos3ParamSetForbiddenAttrMask 
                  AttributeMask, 
     docsQos3ParamSetAttrAggrRuleMask 
                  AttrAggrRuleMask, 
     docsQos3ParamSetAppId 
                  Unsigned32, 
     docsQos3ParamSetMultiplierContentionReqWindow 
                  Unsigned32, 
     docsQos3ParamSetMultiplierBytesReq 
                  Unsigned32, 
     docsQos3ParamSetMaxReqPerSidCluster 
                  Unsigned32, 
     docsQos3ParamSetMaxOutstandingBytesPerSidCluster 
                  Unsigned32, 
     docsQos3ParamSetMaxTotBytesReqPerSidCluster 
                  Unsigned32, 
     docsQos3ParamSetMaxTimeInSidCluster 
                  Unsigned32, 
     docsQos3ParamSetPeakTrafficRate 
                  Unsigned32, 
     docsQos3ParamSetDsResequencing 
                  INTEGER 
     } 
 
docsQos3ParamSetServiceClassName OBJECT-TYPE 
     SYNTAX      SnmpAdminString (SIZE(0..15)) 
     MAX-ACCESS  read-only 
     STATUS      current 
     DESCRIPTION 
        "This attribute represents the Service Class Name 
        from which the parameter set values were derived. 
        If the referenced parameter is not present in the corresponding 
        DOCSIS QOS Parameter Set, this attribute returns the  
        zero-length string." 
     REFERENCE 
        "DOCSIS 3.0 MAC and Upper Layer Protocols Interface 
        Specification CM-SP-MULPIv3.0-I05-070803, Service Class Name 
        section in the Common Radio Frequency Interface  
        Encodings Annex." 
     ::= { docsQos3ParamSetEntry 4 } 
 
docsQos3ParamSetPriority OBJECT-TYPE 
     SYNTAX      Unsigned32 (0..7) 
     MAX-ACCESS  read-only 
     STATUS      current 
     DESCRIPTION 
        "This attribute represents the relative priority 
        of a Service Flow. Higher numbers indicate higher priority. 
         
        This priority should only be used to differentiate Service 
        Flow from identical parameter sets. 
        This attribute returns 0 if the referenced parameter 
        is not present in the corresponding DOCSIS QOS Parameter 
        Set or if the parameter is not applicable." 
     REFERENCE 
        "DOCSIS 3.0 MAC and Upper Layer Protocols Interface 
        Specification CM-SP-MULPIv3.0-I05-070803, Traffic Priority 
        section in the Common Radio Frequency Interface Encodings 
        Annex." 
     ::= { docsQos3ParamSetEntry 5 } 
 
docsQos3ParamSetMaxTrafficRate OBJECT-TYPE 
     SYNTAX      BitRate 
     UNITS       "bps" 
     MAX-ACCESS  read-only 
     STATUS      current 
     DESCRIPTION 
        "This attribute represents the maximum sustained 
        traffic rate allowed for this Service Flow in bits/sec. 
        It counts all MAC frame data PDUs from the bytes following 
        the MAC header HCS to the end of the CRC. The number 
        of bytes forwarded is limited during any time interval. 
        The value 0 means no maximum traffic rate is enforced. 
        This attribute applies to both upstream and 
        downstream Service Flows. 
        This attribute returns 0 if the referenced parameter 
        is not present in the corresponding DOCSIS QOS Parameter 
        Set, or if the parameter is not applicable." 
     REFERENCE 
        "DOCSIS 3.0 MAC and Upper Layer Protocols Interface 
        Specification CM-SP-MULPIv3.0-I05-070803, Maximum Sustained 
        Traffic Rate section in the Common Radio Frequency Interface 
        Encodings Annex." 
     ::= { docsQos3ParamSetEntry 6 } 
 
docsQos3ParamSetMaxTrafficBurst OBJECT-TYPE 
     SYNTAX      Unsigned32 
     UNITS       "bytes" 
     MAX-ACCESS  read-only 
     STATUS      current 
     DESCRIPTION 
        "This attribute specifies the token bucket size in 
        bytes for this parameter set. The value is calculated 
        from the byte following the MAC header HCS to  the end 
        of the CRC. This object is applied in conjunction with 
        MaxTrafficRate to calculate maximum sustained traffic 
        rate. 
        If the referenced parameter is not present in the corresponding 
        DOCSIS QOS Parameter Set, this attribute 
        returns 3044 for scheduling types 'bestEffort', 'nonRealTimePollingService' 
        and 'realTimePollingService'. 
         
        If this parameter is not applicable, it is reported as 
        0." 
     REFERENCE 
        "DOCSIS 3.0 MAC and Upper Layer Protocols Interface 
        Specification CM-SP-MULPIv3.0-I05-070803, Maximum Traffic 
        Burst section in the Common Radio Frequency Interface  
        Encodings Annex." 
     ::= { docsQos3ParamSetEntry 7 } 
 
docsQos3ParamSetMinReservedRate OBJECT-TYPE 
     SYNTAX      BitRate 
     UNITS       "bps" 
     MAX-ACCESS  read-only 
     STATUS      current 
     DESCRIPTION 
        "This attribute specifies the guaranteed minimum 
        rate in bits/sec for this parameter set. The value is 
        calculated from the byte following the MAC header HCS 
        to the end of the CRC. The value of 0 indicates that no 
        bandwidth is reserved. 
        If the referenced parameter is not present in the corresponding 
        DOCSIS QOS Parameter Set, this attribute 
        returns 0. If the parameter is not applicable, it is 
        reported as 0." 
     REFERENCE 
        "DOCSIS 3.0 MAC and Upper Layer Protocols Interface 
        Specification CM-SP-MULPIv3.0-I05-070803, Minimum Reserved 
        Traffic Rate section of the Common Radio Frequency Interface 
        Encodings Annex." 
     ::= { docsQos3ParamSetEntry 8 } 
 
docsQos3ParamSetMinReservedPkt OBJECT-TYPE 
     SYNTAX      Unsigned32 (0..65535) 
     UNITS       "bytes" 
     MAX-ACCESS  read-only 
     STATUS      current 
     DESCRIPTION 
        "This attribute specifies an assumed minimum packet 
        size in bytes for which the MinReservedRate will be 
        provided. The value is calculated from the byte following 
        the MAC header HCS to the end of the CRC. If the referenced 
        parameter is omitted from a DOCSIS QOS parameter 
        set, the used and reported value is CMTS implementation 
        and the CM reports a value of 0. If the referenced 
        parameter is not applicable to the direction or 
        scheduling type of the Service Flow, both CMTS and CM 
        report the value 0." 
     REFERENCE 
        "DOCSIS 3.0 MAC and Upper Layer Protocols Interface 
        Specification CM-SP-MULPIv3.0-I05-070803, Assumed Minimum 
        Reserved Rate Packet Size, in the Common Radio Frequency 
        Interface Encodings Annex." 
     ::= { docsQos3ParamSetEntry 9 } 
 
docsQos3ParamSetActiveTimeout OBJECT-TYPE 
     SYNTAX      Unsigned32 (0..65535) 
     UNITS       "seconds" 
     MAX-ACCESS  read-only 
     STATUS      current 
     DESCRIPTION 
        "This attribute specifies the maximum duration in 
        seconds that resources remain unused on an active service 
        flow before the CMTS signals that both the active 
        and admitted parameter sets are null. The value 0 signifies 
        an infinite amount of time.  
        If the referenced parameter is not present in the corresponding 
        DOCSIS QOS Parameter Set, this attribute 
        returns 0." 
     REFERENCE 
        "DOCSIS 3.0 MAC and Upper Layer Protocols Interface 
        Specification CM-SP-MULPIv3.0-I05-070803, Timeout for Active 
        QoS Parameters section in the Common Radio Frequency Interface 
        Encodings Annex." 
     ::= { docsQos3ParamSetEntry 10 } 
 
docsQos3ParamSetAdmittedTimeout OBJECT-TYPE 
     SYNTAX      Unsigned32 (0..65535) 
     UNITS       "seconds" 
     MAX-ACCESS  read-only 
     STATUS      current 
     DESCRIPTION 
        "This attribute specifies the maximum duration in 
        seconds that resources remain in admitted state before 
        resources must be released. The value of 0 signifies 
        an infinite amount  of time. If the referenced parameter 
        is not present in the corresponding DOCSIS QOS 
        Parameter Set, this attribute returns 200." 
     REFERENCE 
        "DOCSIS 3.0 MAC and Upper Layer Protocols Interface 
        Specification CM-SP-MULPIv3.0-I05-070803, Timeout for Admitted 
        QoS Parameters section in the Common Radio Frequency Interface 
        Encodings Annex." 
     ::= { docsQos3ParamSetEntry 11 } 
 
docsQos3ParamSetMaxConcatBurst OBJECT-TYPE 
     SYNTAX      Unsigned32 (0..65535) 
     UNITS       "bytes" 
     MAX-ACCESS  read-only 
     STATUS      current 
     DESCRIPTION 
        "This attribute specifies the maximum concatenated 
        burst in bytes that an upstream Service Flow is allowed. 
         
        The value is calculated from the FC byte of the Concatenation 
        MAC Header to the last CRC byte of the last concatenated 
        MAC frame, inclusive.  The value of 0 specifies 
        no maximum burst. 
        If the referenced parameter is not present in the corresponding 
        DOCSIS QOS Parameter Set, this attribute 
        returns the value of 1522 for scheduling types 'bestEffort', 
        'nonRealTimePollingService', and  'realTimePollingService'. 
        If the parameter is not applicable, 
        it is reported as 0." 
     REFERENCE 
        "DOCSIS 3.0 MAC and Upper Layer Protocols Interface 
        Specification CM-SP-MULPIv3.0-I05-070803, Maximum Concatenated 
        Burst section in the Common Radio Frequency Interface  
        Encodings Annex." 
     ::= { docsQos3ParamSetEntry 12 } 

docsQos3ParamSetSchedulingType OBJECT-TYPE 
     SYNTAX      SchedulingType 
     MAX-ACCESS  read-only 
     STATUS      current 
     DESCRIPTION 
        "This attribute specifies the upstream scheduling 
        service used for upstream Service Flow.  
        If the referenced parameter is not present in the corresponding 
        DOCSIS QOS Parameter Set of an upstream Service 
        Flow, this attribute returns the value of 'bestEffort'. 
        For QOS parameter sets of downstream Service 
        Flows, this attribute's value is reported as 'undefined'." 
     REFERENCE 
        "DOCSIS 3.0 MAC and Upper Layer Protocols Interface 
        Specification CM-SP-MULPIv3.0-I05-070803, Service Flow  
        Scheduling Type section in the Common Radio Frequency Interface 
        Encodings Annex." 
     ::= { docsQos3ParamSetEntry 13 } 
 
docsQos3ParamSetNomPollInterval OBJECT-TYPE 
     SYNTAX      Unsigned32 
     UNITS       "microseconds" 
     MAX-ACCESS  read-only 
     STATUS      current 
     DESCRIPTION 
        "This attribute specifies the nominal interval in 
        microseconds between successive unicast request opportunities 
        on an upstream Service Flow. 
        This attribute applies only to upstream Service Flows 
        with SchedulingType of value 'nonRealTimePollingService', 
        'realTimePollingService', and 'unsolictedGrantServiceWithAD'. 
        The parameter is mandatory 
        for 'realTimePollingService'. If the parameter 
        is omitted with 'nonRealTimePollingService', 
        the CMTS uses an implementation-dependent value. If 
        the parameter is omitted with 'unsolictedGrantServiceWithAD(5)' 
        the CMTS uses the value of the Nominal 
        Grant Interval parameter. In all cases, the CMTS reports 
        the value it is using when the parameter is applicable. 
        The CM reports the signaled parameter value 
        if it was signaled. Otherwise, it returns 0. 
        If the referenced parameter is not applicable to the 
        direction or scheduling type of the corresponding DOCSIS 
        QOS Parameter Set, both CMTS and CM report this 
        attribute's value as 0." 
     REFERENCE 
        "DOCSIS 3.0 MAC and Upper Layer Protocols Interface 
        Specification CM-SP-MULPIv3.0-I05-070803, Polling Interval 
        section in the Common Radio Frequency Interface  
        Encodings Annex." 
     ::= { docsQos3ParamSetEntry 14 } 
 
docsQos3ParamSetTolPollJitter OBJECT-TYPE 
     SYNTAX      Unsigned32 
     UNITS       "microseconds" 
     MAX-ACCESS  read-only 
     STATUS      current 
     DESCRIPTION 
        "This attribute specifies the maximum amount of time 
        in microseconds that the unicast request interval 
        may be delayed from the nominal periodic schedule on 
        an upstream Service Flow. This parameter is applicable 
        only to upstream Service Flows with a SchedulingType 
        of 'realTimePollingService' or 'unsolictedGrantServiceWithAD'. 
         
        If the referenced parameter is applicable but not present 
        in the corresponding DOCSIS QOS Parameter Set, 
        the CMTS uses an implementation-dependent value and 
        reports the value it is using. The CM reports a value 
        of 0 in this case. 
        If the parameter is not applicable to the direction or 
        upstream scheduling type of the Service Flow, both 
        CMTS and CM report this attribute's value as 0." 
     REFERENCE 
        "DOCSIS 3.0 MAC and Upper Layer Protocols Interface 
        Specification CM-SP-MULPIv3.0-I05-070803, Tolerated Poll 
        Jitter section in the Common Radio Frequency Interface  
        Encodings Annex." 
     ::= { docsQos3ParamSetEntry 15 } 
 
docsQos3ParamSetUnsolicitGrantSize OBJECT-TYPE 
     SYNTAX      Unsigned32 (0..65535) 
     UNITS       "bytes" 
     MAX-ACCESS  read-only 
     STATUS      current 
     DESCRIPTION 
        "This attribute specifies the unsolicited grant size 
        in bytes. The grant size includes the entire MAC frame 
        data PDU from the Frame Control byte to the end of 
        the MAC frame. 
        The referenced parameter is applicable only for upstream 
        flows with a SchedulingType of  'unsolicitedGrantServicewithAD' 
        or 'unsolicitedGrantService', 
        and it is mandatory when applicable. Both CMTS and 
        CM report the signaled value of the parameter in this 
        case. 
        If the referenced parameter is not applicable to the 
        direction or scheduling type of the corresponding DOCSIS 
        QOS Parameter Set, both CMTS and CM report this 
        attribute's value as 0." 
     REFERENCE 
        "DOCSIS 3.0 MAC and Upper Layer Protocols Interface 
        Specification CM-SP-MULPIv3.0-I05-070803, Unsolicited 
        Grant Size section in the Common Radio Frequency Interface 
        Encodings Annex." 
     ::= { docsQos3ParamSetEntry 16 } 
 
docsQos3ParamSetNomGrantInterval OBJECT-TYPE 
     SYNTAX      Unsigned32 
     UNITS       "microseconds" 
     MAX-ACCESS  read-only 
     STATUS      current 
     DESCRIPTION 
        "This attribute specifies the nominal interval in 
        microseconds between successive data grant opportunities 
        on an upstream Service Flow. 
        The referenced parameter is applicable only for upstream 
        flows with a SchedulingType of 'unsolicitedGrantServicewithAD' 
        or 'unsolicitedGrantService(6)', 
        and it is mandatory when applicable. Both CMTS 
        and CM report the signaled value of the parameter in this 
        case. 
        If the referenced parameter is not applicable to the 
        direction or scheduling type of the corresponding DOCSIS 
        QOS Parameter Set, both CMTS and CM report this 
        attribute's value as 0." 
     REFERENCE 
        "DOCSIS 3.0 MAC and Upper Layer Protocols Interface 
        Specification CM-SP-MULPIv3.0-I05-070803, Nominal Grant 
        Interval section in the Common Radio Frequency Interface 
        Encodings Annex." 
     ::= { docsQos3ParamSetEntry 17 } 

docsQos3ParamSetTolGrantJitter OBJECT-TYPE 
     SYNTAX      Unsigned32 
     UNITS       "microseconds" 
     MAX-ACCESS  read-only 
     STATUS      current 
     DESCRIPTION 
        "This attribute specifies the maximum amount of time 
        in microseconds that the transmission opportunities 
        may be delayed from the nominal periodic schedule. 
        The referenced parameter is applicable only for 
        upstream flows with a SchedulingType of 'unsolicitedGrantServicewithAD' 
        or 'unsolicitedGrantService(6)', 
        and it is mandatory when applicable. Both CMTS 
        and CM report the signaled value of the parameter 
        in this case.  
        If the referenced parameter is not applicable to the 
        direction or scheduling type of the corresponding DOCSIS 
        QOS Parameter Set, both CMTS and CM report this 
        attribute's value as 0." 
     REFERENCE 
        "DOCSIS 3.0 MAC and Upper Layer Protocols Interface 
        Specification CM-SP-MULPIv3.0-I05-070803, Tolerated Grant 
        Jitter section in the Common Radio Frequency Interface  
        Encodings Annex." 
     ::= { docsQos3ParamSetEntry 18 } 
 
docsQos3ParamSetGrantsPerInterval OBJECT-TYPE 
     SYNTAX      Unsigned32 (0..127) 
     UNITS       "dataGrants" 
     MAX-ACCESS  read-only 
     STATUS      current 
     DESCRIPTION 
        "This attribute specifies the number of data grants 
        per Nominal Grant Interval (NomGrantInterval). The 
        referenced parameter is applicable only for upstream 
        flows with a SchedulingType of 'unsolicitedGrantServicewithAD' 
        or 'unsolicitedGrantService', 
        and it is mandatory when applicable. Both CMTS and CM 
        report the signaled value of the parameter in this case. 
         
        If the referenced parameter is not applicable to the 
        direction or scheduling type of the corresponding DOCSIS 
        QOS Parameter Set, both CMTS and CM report this 
        attribute's value as 0." 
     REFERENCE 
        "DOCSIS 3.0 MAC and Upper Layer Protocols Interface 
        Specification CM-SP-MULPIv3.0-I05-070803, Grants per  
        Interval section in the Common Radio Frequency Interface 
        Encodings Annex." 
     ::= { docsQos3ParamSetEntry 19 } 
 
docsQos3ParamSetTosAndMask OBJECT-TYPE 
     SYNTAX      OCTET STRING (SIZE(1)) 
     MAX-ACCESS  read-only 
     STATUS      current 
     DESCRIPTION 
        "This attribute specifies the AND mask for the IP TOS 
        byte for overwriting an IPv4 packet's TOS value or IPv6 
        packet's Traffic Class value. The IP packet TOS byte 
        is bitwise ANDed with TosAndMask, then the result 
        is bitwise ORed with TosORMask and the result is written 
        to the IP packet TOS byte. 
        A value of 'FF'H for TosAndMask and a value of '00'H for 
        TosOrMask means that the IP Packet TOS byte is not overwritten. 
         
        This combination is reported if the referenced parameter 
        is not present in a QOS Parameter Set. 
        The IP TOS octet as originally defined in RFC 791 has been 
        superseded by the 6-bit Differentiated Services 
        Field (DSField, RFC 3260) and the 2-bit Explicit Congestion 
        Notification Field (ECN field, RFC 3168). 
        The IPv6 Traffic Class octet RFC 2460 is consistent with 
        that new definition. 
        Network operators SHOULD avoid specifying values of 
        TosAndMask and TosORMask that would result in the modification 
        of the ECN bits. 
        In particular, operators should not use values of TosAndMask 
        that have either of the least-significant 
        two bits set to 0. Similarly, operators should not use 
        values of TosORMask that have either of the least-significant 
        two bits set to 1. 
        Even though this attribute is only enforced by the CMTS, 
        the CM reports the value as signaled in the referenced 
        parameter." 
     REFERENCE 
        "DOCSIS 3.0 MAC and Upper Layer Protocols Interface 
        Specification CM-SP-MULPIv3.0-I05-070803, IP Type Of Service 
        (DSCP) Overwrite section in the Common Radio Frequency  
        Interface Encodings Annex; [RFC 3168]; [RFC 3260]; 
        [RFC 2460]; [RFC 791]." 
     ::= { docsQos3ParamSetEntry 20 } 
 
docsQos3ParamSetTosOrMask OBJECT-TYPE 
     SYNTAX      OCTET STRING (SIZE (1)) 
     MAX-ACCESS  read-only 
     STATUS      current 
     DESCRIPTION 
        "This attribute specifies the OR mask for the IPv4 TOS 
        value or IPv6 Traffic Class value. See the description 
        of TosAndMask for further details.  
        The IP TOS octet, as originally defined in RFC 791 has 
        been superseded by the 6-bit Differentiated Services 
        Field (DSField, RFC 3260) and the 2-bit Explicit Congestion 
        Notification Field (ECN field, RFC 3168). 
        The IPv6 Traffic Class octet RFC 2460 is consistent 
        with that new definition. 
        Network operators SHOULD avoid specifying values of 
        TosAndMask and TosORMask that would result in the modification 
        of the ECN bits." 
     REFERENCE 
        "DOCSIS 3.0 MAC and Upper Layer Protocols Interface 
        Specification CM-SP-MULPIv3.0-I05-070803, IP Type Of Service 
        (DSCP) Overwrite section in the Common Radio Frequency  
        Interface Encodings Annex; [RFC 3168]; [RFC 3260]; 
        [RFC 2460]; [RFC 791]." 
     ::= { docsQos3ParamSetEntry 21 } 
 
docsQos3ParamSetMaxLatency OBJECT-TYPE 
     SYNTAX      Unsigned32 
     UNITS       "microseconds" 
     MAX-ACCESS  read-only 
     STATUS      current 
     DESCRIPTION 
        "This attribute specifies the maximum latency between 
        the reception of a packet by the CMTS on its NSI and 
        the forwarding of the packet to the RF interface. A value 
        of 0 signifies no maximum latency is enforced. This 
        attribute only applies to downstream Service Flows. 
         
        If the referenced parameter is not present in the corresponding 
        downstream DOCSIS QOS Parameter Set, this 
        attribute returns 0. This parameter is not applicable 
        to upstream DOCSIS QOS Parameter Sets, so its value 
        is reported as 0 in that case." 
     REFERENCE 
        "DOCSIS 3.0 MAC and Upper Layer Protocols Interface 
        Specification CM-SP-MULPIv3.0-I05-070803, Maximum Downstream 
        Latency section in the Common Radio Frequency Interface 
        Encodings Annex." 
     ::= { docsQos3ParamSetEntry 22 } 
 
docsQos3ParamSetType OBJECT-TYPE 
     SYNTAX      INTEGER { 
 
                        active (1), 
                        admitted(2), 
                        provisioned(3) 
                      } 
     MAX-ACCESS  not-accessible 
     STATUS      current 
     DESCRIPTION 
        "This key represents the QoS Parameter Set Type of the 
        Service Flow. 
        The following values are defined:  
        'active'  
        Indicates the Active QOS parameter set, describing 
        the service currently being provided by the DOCSIS MAC 
        domain to the service flow.  
        'admitted'  
        Indicates the Admitted QOS Parameter Set, describing 
        services reserved by the DOCSIS MAC domain for use 
        by the service flow.  
        'provisioned'  
        Indicates the QOS Parameter Set defined in the DOCSIS 
        CM Configuration file for the service flow." 
     REFERENCE 
        "DOCSIS 3.0 MAC and Upper Layer Protocols Interface 
        Specification CM-SP-MULPIv3.0-I05-070803, Service Flow 
        Scheduling Type section in the Common Radio Frequency  
        Interface Encodings Annex; [RFC 4323]." 
     ::= { docsQos3ParamSetEntry 23 } 
 
docsQos3ParamSetRequestPolicyOct OBJECT-TYPE 
     SYNTAX      OCTET STRING (SIZE (4)) 
                 -- A 32-bit mask represented most significant byte 
                 -- first.  The 32-bit integer represented in this 
                 -- manner equals the binary value of the referenced 
                 -- integer parameter of the DOCSIS RFI 
                 -- specification. 
                 -- The BITS syntax is not used in order to avoid 
                 -- the confusion caused by different bit-numbering 
                 -- conventions. 
     MAX-ACCESS  read-only 
     STATUS      current 
     DESCRIPTION 
        "This attribute specifies which transmit interval 
        opportunities the CM omits for upstream transmission 
        requests and packet transmissions. This object 
        takes its default value for downstream Service Flows. 
        Unless otherwise indicated, a bit value of 1 means 
        that a CM must not use that opportunity for upstream transmission. 
         
        The format of this string enumerated the bits from 0 to 
        31 from left to right, for example bit 0 corresponds 
        to the left most bit of the fourth octet. (octets numbered 
        from right to left). The bit positions are defined 
        as follows: 
           'broadcastReqOpp' 
               all CMs broadcast request opportunities 
           'priorityReqMulticastReq'  
               priority request multicast request opportunities 
           'reqDataForReq'  
               request/data opportunities for requests 
           'reqDataForData'  
               request/data opportunities for data  
           'piggybackReqWithData'  
               piggyback requests with data 
           'concatenateData' 
               concatenate data 
           'fragmentData' 
               fragment data 
           'suppressPayloadHeaders'  
               suppress payload headers 
           'dropPktsExceedUGSize' 
               A value of 1 means that the service flow must drop 
               packets that do not fit in the Unsolicited Grant size. 
         
        If the referenced parameter is not present in a QOS Parameter 
        Set, the value of this object is reported as '00000000'H." 
     REFERENCE 
        "DOCSIS 3.0 MAC and Upper Layer Protocols Interface 
        Specification CM-SP-MULPIv3.0-I05-070803, Request/  
        Transmission Policy section in the Common Radio Frequency  
        Interface Encodings Annex." 
     ::= { docsQos3ParamSetEntry 24 } 
 
docsQos3ParamSetBitMap OBJECT-TYPE 
     SYNTAX      BITS { 
 
                        trafficPriority(0), 
                        maxTrafficRate(1), 
                        maxTrafficBurst(2), 
                        minReservedRate(3), 
                        minReservedPkt(4), 
                        activeTimeout(5), 
                        admittedTimeout(6), 
                        maxConcatBurst(7), 
                        schedulingType(8), 
                        requestPolicy(9), 
                        nomPollInterval(10), 
                        tolPollJitter(11), 
                        unsolicitGrantSize(12), 
                        nomGrantInterval(13), 
                        tolGrantJitter(14), 
                        grantsPerInterval(15), 
                        tosOverwrite(16), 
                        maxLatency(17), 
                        requiredAttrMask(18), 
                        forbiddenAttrMask(19), 
                        attrAggrMask(20), 
                        applicationId(21), 
                        multipCntnReqWindow(22), 
                        multipBytesReq(23), 
                        maxReqPerSidCluster(24), 
                        maxOutstandingBytesPerSidCluster(25), 
                        maxTotalBytesReqPerSidCluster(26), 
                        maximumTimeInSidCluster(27), 
                        peakTrafficRate(28), 
                        dsResequencing(29) 
                      } 
     MAX-ACCESS  read-only 
     STATUS      current 
     DESCRIPTION 
        "This attribute indicates the set of QOS Parameter 
        Set parameters actually signaled in the DOCSIS registration 
        or dynamic service request message that created 
        or modified the QOS Parameter Set. A bit is set to 
        1 when the associated parameter is present in the original 
        request as follows: 
         'trafficPriority'  Traffic Priority 
         'maxTrafficRate'  Maximum Sustained Traffic Rate 
         
         'maxTrafficBurst'  Maximum Traffic Burst 
         'minReservedRate'  Minimum Reserved Traffic Rate 
         
         'minReservedPkt'  Assumed Minimum Reserved Rate Packet 
        Size 
         'activeTimeout'  Timeout for Active QoS Parameters 
         
         'admittedTimeout'  Timeout for Admitted QoS Parameters 
         
         'maxConcatBurst'  Maximum Concatenated Burst 
         'schedulingType'  Service Flow Scheduling Type 
         'requestPolicy'  Request/Transmission Policy 
         'nomPollInterval'  Nominal Polling Interval 
         'tolPollJitter'  Tolerated Poll Jitter 
         'unsolicitGrantSize'  Unsolicited Grant Size 
         'nomGrantInterval'  Nominal Grant Interval 
         'tolGrantJitter'  Tolerated Grant Jitter 
         'grantsPerInterval'  Grants per Interval 
         'tosOverwrite'  IP Type of Service (DSCP) Overwrite 
         'maxLatency'  Maximum Downstream Latency 
         'requiredAttrMask'  Service Flow Required Attribute 
                              Mask 
         'forbiddenAttrMask  Service Flow Forbidden Attribute 
                              Mask 
         'attrAggrMask'  Service Flow Attribute Aggregation 
                          Mask 
         'applicationId'  Application Identifier 
         'multipCntnReqWindow'  Multiplier to Contention 
                                 Request Backoff Window 
         'multipBytesReq'  Multiplier to Number of Bytes Requested 
         'maxReqPerSidCluster'  Maximum Requests per SID Cluster 
         'maxOutstandingBytesPerSidCluster'  Maximum Outstanding 
                                              Bytes per SID Cluster 
         'maxTotalBytesReqPerSidCluster'  Maximum Total 
                                           Bytes Requested per SID 
                                           Cluster 
         'maximumTimeInSidCluster'  Maximum Time in the SID Cluster 
         'peakTrafficRate'  Downstream Peak Traffic Rate 
         'dsResequencing'    Downstream Resequencing 
          
        Note that when Service Class names are expanded, the 
        registration or dynamic response message may contain 
        parameters expanded by the CMTS based on a stored service 
        class. These expanded parameters are not indicated 
        by a 1 bit in this attribute. 
        Note that even though some QOS Parameter Set parameters 
        may not be signaled in a message (so that the parameter's 
        bit in this object is 0), the DOCSIS specification 
        requires that default values be used. These default 
        values are reported as the corresponding attribute." 
     REFERENCE 
        "DOCSIS 3.0 MAC and Upper Layer Protocols Interface 
        Specification CM-SP-MULPIv3.0-I05-070803, Service Flow  
        Encodings section in the Common Radio Frequency Interface  
        Encodings Annex." 
     ::= { docsQos3ParamSetEntry 25 } 
 
docsQos3ParamSetServiceFlowId OBJECT-TYPE 
     SYNTAX      Unsigned32 (1.. 4294967295) 
     MAX-ACCESS  not-accessible 
     STATUS      current 
     DESCRIPTION 
        "This key represents the Service Flow ID for the service 
        flow." 
     REFERENCE 
        "DOCSIS 3.0 MAC and Upper Layer Protocols Interface 
        Specification CM-SP-MULPIv3.0-I05-070803, Service 
        Identifier section in the Common Radio Frequency Interface 
        Encodings Annex." 
     ::= { docsQos3ParamSetEntry 26 } 
 
docsQos3ParamSetRequiredAttrMask OBJECT-TYPE 
     SYNTAX      AttributeMask 
     MAX-ACCESS  read-only 
     STATUS      current 
     DESCRIPTION 
        "This attribute specifies the Required Attribute 
        Mask to compare with the Provisioned Required Attributes 
        when selecting the bonding groups for the service 
        flow.          
        If the referenced parameter is not present in the corresponding 
        DOCSIS QOS Parameter Set, this attribute returns '00000000'H." 
     REFERENCE 
        "DOCSIS 3.0 MAC and Upper Layer Protocols Interface 
        Specification CM-SP-MULPIv3.0-I05-070803, Service Flow Required  
        Attribute Mask section in the Common Radio Frequency Interface  
        Encodings Annex." 
     ::= { docsQos3ParamSetEntry 27 } 
 
docsQos3ParamSetForbiddenAttrMask OBJECT-TYPE 
     SYNTAX      AttributeMask 
     MAX-ACCESS  read-only 
     STATUS      current 
     DESCRIPTION 
        "This attribute specifies the Forbidden Attribute 
        Mask to compare with the Provisioned Forbidden Attributes 
        when selecting the bonding groups for the service 
        flow. 
        If the referenced parameter is not present in the corresponding 
        DOCSIS QOS Parameter Set, this attribute returns '00000000'H." 
     REFERENCE 
        "DOCSIS 3.0 MAC and Upper Layer Protocols Interface 
        Specification CM-SP-MULPIv3.0-I05-070803, Service Flow Forbidden 
        Attribute Mask section in the Common Radio Frequency Interface 
        Encodings Annex." 
     ::= { docsQos3ParamSetEntry 28 } 
 
docsQos3ParamSetAttrAggrRuleMask OBJECT-TYPE 
     SYNTAX      AttrAggrRuleMask 
     MAX-ACCESS  read-only 
     STATUS      current 
     DESCRIPTION 
        "This attribute specifies the Attribute Aggregation 
        Mask to compare the Service Flow Required and Forbidden 
        Attributes with the CMTS dynamically-created 
        bonding group when selecting the bonding groups for 
        the service flow. 
        If the referenced parameter is not present in the corresponding 
        DOCSIS QOS Parameter Set, this attribute returns '00000000'H." 
     REFERENCE 
        "DOCSIS 3.0 MAC and Upper Layer Protocols Interface 
        Specification CM-SP-MULPIv3.0-I05-070803, Service Flow  
        Attribute Aggregation Mask section in the Common Radio  
        Frequency Interface Encodings Annex." 
     ::= { docsQos3ParamSetEntry 29 } 
 
docsQos3ParamSetAppId OBJECT-TYPE 
     SYNTAX      Unsigned32 
     MAX-ACCESS  read-only 
     STATUS      current 
     DESCRIPTION 
        "This attribute represents the Application Identifier  
        associated with the service flow for purposes beyond the  
        scope of this specification. 
        If the referenced parameter is not present in the corresponding 
        DOCSIS QOS Parameter Set, this attribute returns 0." 
     REFERENCE 
        "DOCSIS 3.0 MAC and Upper Layer Protocols Interface 
        Specification CM-SP-MULPIv3.0-I05-070803, Application  
        Identifier section in the Common Radio Frequency Interface 
        Encodings Annex." 
     ::= { docsQos3ParamSetEntry 30 } 
 
docsQos3ParamSetMultiplierContentionReqWindow OBJECT-TYPE 
     SYNTAX      Unsigned32 (4..12) 
     UNITS       "eighths" 
     MAX-ACCESS  read-only 
     STATUS      current 
     DESCRIPTION 
        "This attribute specifies the multiplier to be applied by a 
        CM when performing contention request backoff for data requests. 
        This attribute only applies to upstream Service Flows in 3.0  
        operation. If the referenced parameter is not present in the 
        upstream DOCSIS QOS Parameter Set or is not applicable, this  
        attribute returns 8." 
     REFERENCE 
        "DOCSIS 3.0 MAC and Upper Layer Protocols Interface 
        Specification CM-SP-MULPIv3.0-I05-070803, Multiplier to 
        Contention Request Backoff Window section in the Common 
        Radio Frequency Interface Encodings Annex." 
     ::= { docsQos3ParamSetEntry 31 } 
 
docsQos3ParamSetMultiplierBytesReq OBJECT-TYPE 
     SYNTAX      Unsigned32 (1 | 2 | 4 | 8 | 16) 
     UNITS       "requests" 
     MAX-ACCESS  read-only 
     STATUS      current 
     DESCRIPTION 
        "This attribute specifies the assumed bandwidth request  
        multiplier. This attribute only applies to upstream Service  
        Flows in 3.0 operation. If the referenced parameter is not 
        present in the upstream DOCSIS QOS Parameter Set, or is not 
        applicable, this attribute returns 4." 
     REFERENCE 
        "DOCSIS 3.0 MAC and Upper Layer Protocols Interface 
        Specification CM-SP-MULPIv3.0-I05-070803, Multiplier 
        to Number of Bytes Requested section in the Common  
        Radio Frequency Interface Encodings Annex." 
     ::= { docsQos3ParamSetEntry 32 } 
 
docsQos3ParamSetMaxReqPerSidCluster OBJECT-TYPE 
     SYNTAX      Unsigned32 (0..255) 
     UNITS       "bytes" 
     MAX-ACCESS  read-only 
     STATUS      current 
     DESCRIPTION 
        "This attribute specifies the maximum number of requests  
        that a CM can make within a given SID Cluster before it must 
        switch to a different SID Cluster to make further requests. 
        A value of 0 indicates there is no limit.  
         
        This attribute only applies to upstream Service Flows in 3.0 
        operation, in other cases it is reported as 0. If the  
        referenced parameter is not present in the DOCSIS QOS  
        Parameter Set, this attribute returns 0." 
     REFERENCE 
        "DOCSIS 3.0 MAC and Upper Layer Protocols Interface 
     Specification CM-SP-MULPIv3.0-I05-070803, Maximum Requests 
        per SID Cluster section in the Common Radio Frequency 
        Interface Encodings Annex." 
     ::= { docsQos3ParamSetEntry 33 } 
 
docsQos3ParamSetMaxOutstandingBytesPerSidCluster OBJECT-TYPE 
     SYNTAX      Unsigned32 
     UNITS       "bytes" 
     MAX-ACCESS  read-only 
     STATUS      current 
     DESCRIPTION 
        "This attribute specifies the maximum number of bytes 
        for which a CM can have requests outstanding on a given 
        SID Cluster. If defined number of bytes are outstanding  
        and further requests are required, the CM must switch to 
        a different SID Cluster if one is available. A value of 0 
        indicates there is no limit. 
         
        This attribute only applies to upstream Service Flows in 3.0 
        operation, in other cases it is reported as 0.  
        If the referenced parameter is not present in the DOCSIS QOS 
        Parameter Set, this attribute returns 0." 
     REFERENCE 
        "DOCSIS 3.0 MAC and Upper Layer Protocols Interface 
        Specification CM-SP-MULPIv3.0-I05-070803, Maximum  
        Outstanding Bytes per SID Cluster section in the Common 
        Radio Frequency Interface Encodings Annex." 
     ::= { docsQos3ParamSetEntry 34 } 
 
docsQos3ParamSetMaxTotBytesReqPerSidCluster OBJECT-TYPE 
     SYNTAX      Unsigned32 
     UNITS       "bytes" 
     MAX-ACCESS  read-only 
     STATUS      current 
     DESCRIPTION 
        "This attribute specifies the maximum total number of bytes 
        a CM can have requested using a given SID Cluster before it 
        must switch to a different SID Cluster to make further  
        requests. A value of 0 indicates there is no limit.  
         
        This attribute only applies to upstream Service Flows in 3.0 
        operation, in other cases it is reported as 0.  
        If the referenced parameter is not present in the DOCSIS QOS 
        Parameter Set, this attribute returns 0." 
     REFERENCE 
        "DOCSIS 3.0 MAC and Upper Layer Protocols Interface 
        Specification CM-SP-MULPIv3.0-I05-070803, Maximum Total Bytes 
        Requested per SID Cluster section in the Common Radio  
        Frequency Interface Encodings Annex." 
     ::= { docsQos3ParamSetEntry 35 } 
 
docsQos3ParamSetMaxTimeInSidCluster OBJECT-TYPE 
     SYNTAX      Unsigned32 (0..65535) 
     UNITS       "milliseconds" 
     MAX-ACCESS  read-only 
     STATUS      current 
     DESCRIPTION 
        "This attribute specifies the maximum time in milliseconds 
        that a CM may use a particular SID Cluster before it must 
        switch to a different SID Cluster to make further requests. 
        A value of 0 indicates there is no limit. 
         
        This attribute only applies to upstream Service Flows in 3.0 
        operation, in other cases it is reported as 0.  
        If the referenced parameter is not present in the DOCSIS QOS  
        Parameter Set, this attribute returns 0." 
     REFERENCE 
        "DOCSIS 3.0 MAC and Upper Layer Protocols Interface 
        Specification CM-SP-MULPIv3.0-I05-070803, Maximum Time in 
        the SID Cluster section in the Common Radio Frequency  
        Interface Encodings Annex." 
     ::= { docsQos3ParamSetEntry 36 } 
 
docsQos3ParamSetPeakTrafficRate OBJECT-TYPE 
     SYNTAX      Unsigned32 
     UNITS       "bps" 
     MAX-ACCESS  read-only 
     STATUS      current 
     DESCRIPTION 
        "This attribute specifies the rate parameter 'P' of a 
        token-bucket-based peak rate limiter for packets of a  
        downstream service flow. A value of 0 signifies no  
        Downstream Peak Traffic Rate is enforced. 
         
        This attribute only applies to downstream Service Flows. 
        If the referenced parameter is not present in the  
        corresponding downstream DOCSIS QOS Parameter Set,  
        this attribute returns 0. 
        This parameter is not applicable to upstream DOCSIS QOS 
        Parameter Sets, so its value is reported as 0 in that case." 
     REFERENCE 
        "DOCSIS 3.0 MAC and Upper Layer Protocols Interface 
        Specification CM-SP-MULPIv3.0-I05-070803, Downstream 
        Peak Traffic Rage section in the Common Radio Frequency 
        Interface Encodings Annex." 
     ::= { docsQos3ParamSetEntry 37 } 
 
docsQos3ParamSetDsResequencing OBJECT-TYPE 
     SYNTAX      INTEGER {  
                          resequencingDsid(0), 
                          noResequencingDsid(1) 
                         } 
     MAX-ACCESS  read-only 
     STATUS      current 
     DESCRIPTION 
        "This attribute specifies if a resequending DSID need to be 
        allocated to the service flow.  
        The value 'resequencingDsid'  indicates that a resequencing DSID 
        is required if the service flow is assigned to a downstream 
        bonding group. 
        The value 'noResequencingDsid' indicates no resequencing DSID 
        is associated with the service flow. 
         
        This attribute only applies to downstream Service Flows in 3.0  
        operation. If the referenced parameter is not present in the 
        corresponding downstream DOCSIS QOS Parameter Set, this  
        attribute returns 0. This parameter is not applicable to  
        upstream DOCSIS QOS Parameter Sets, so its value is reported 
        as 0 in that case." 
     REFERENCE 
        "DOCSIS 3.0 MAC and Upper Layer Protocols Interface 
        Specification CM-SP-MULPIv3.0-I05-070803, Downstream 
        Peak Traffic Rage section in the Common Radio Frequency 
        Interface Encodings Annex." 
     ::= { docsQos3ParamSetEntry 38 } 
      
docsQos3ServiceFlowTable OBJECT-TYPE 
     SYNTAX      SEQUENCE OF DocsQos3ServiceFlowEntry 
     MAX-ACCESS  not-accessible 
     STATUS      current 
     DESCRIPTION 
        "This object describes the set of DOCSIS-QOS Service 
        Flows in a managed device." 
     REFERENCE 
        "DOCSIS 3.0 MAC and Upper Layer Protocols Interface 
        Specification CM-SP-MULPIv3.0-I05-070803,  Service  
        lows and Classifiers section." 
     ::= { docsQos3MibObjects 3} 
 
docsQos3ServiceFlowEntry OBJECT-TYPE 
     SYNTAX      DocsQos3ServiceFlowEntry 
     MAX-ACCESS  not-accessible 
     STATUS      current 
     DESCRIPTION 
        "The conceptual row of docsQos3ServiceFlowTable. 
        The ifIndex key corresponds to the MAC Domain interface 
        of this service flow." 
     INDEX { ifIndex,docsQos3ServiceFlowId } 
     ::= { docsQos3ServiceFlowTable 1 } 
 
DocsQos3ServiceFlowEntry ::= SEQUENCE { 
     docsQos3ServiceFlowId 
                  Unsigned32, 
     docsQos3ServiceFlowSID 
                  Unsigned32, 
     docsQos3ServiceFlowDirection 
                  IfDirection, 
     docsQos3ServiceFlowPrimary 
                  TruthValue, 
     docsQos3ServiceFlowParamSetTypeStatus 
                  BITS, 
     docsQos3ServiceFlowChSetId 
                  ChSetId, 
     docsQos3ServiceFlowAttrAssignSuccess 
                  TruthValue, 
     docsQos3ServiceFlowDsid 
                  Dsid 
     } 
 
docsQos3ServiceFlowId OBJECT-TYPE 
     SYNTAX      Unsigned32 
     MAX-ACCESS  not-accessible 
     STATUS      current 
     DESCRIPTION 
        "This key represents an identifier assigned to a Service 
        Flow by CMTS within a MAC Domain. 
        The value 0 is used only for the purpose of reporting instances 
        of the PktClass object pertaining UDCs and 
        not used for association of QOS classifiers to service 
        flows." 
     REFERENCE 
        "DOCSIS 3.0 MAC and Upper Layer Protocols Interface 
        Specification CM-SP-MULPIv3.0-I05-070803, Service Flow  
        Identifier section in the Common Radio Frequency Interface 
        Encodings Annex." 
     ::= { docsQos3ServiceFlowEntry 1 } 
 
docsQos3ServiceFlowSID OBJECT-TYPE 
     SYNTAX      Unsigned32 (0..16383) 
     MAX-ACCESS  read-only 
     STATUS      current 
     DESCRIPTION 
        "Service Identifier (SID) assigned to an admitted 
        or active Service Flow.  This attribute 
        reports a value of 0 if a Service ID is not associated with 
        the Service Flow.  Only active 
        or admitted upstream Service Flows will have a Service 
        ID (SID)." 
     REFERENCE 
        "DOCSIS 3.0 MAC and Upper Layer Protocols Interface 
        Specification CM-SP-MULPIv3.0-I05-070803, Service  
        Identifier section in the Common Radio Frequency Interface 
        Encodings Annex." 
     ::= { docsQos3ServiceFlowEntry 6 } 
 
docsQos3ServiceFlowDirection OBJECT-TYPE 
     SYNTAX      IfDirection 
     MAX-ACCESS  read-only 
     STATUS      current 
     DESCRIPTION 
        "This attribute represents the direction of the Service 
        Flow." 
     ::= { docsQos3ServiceFlowEntry 7 } 
 
docsQos3ServiceFlowPrimary OBJECT-TYPE 
     SYNTAX      TruthValue 
     MAX-ACCESS  read-only 
     STATUS      current 
     DESCRIPTION 
        "This attribute reflects whether Service Flow is the 
        primary 
        or a secondary Service Flow." 
     ::= { docsQos3ServiceFlowEntry 8 } 
 
docsQos3ServiceFlowParamSetTypeStatus OBJECT-TYPE 
     SYNTAX      BITS { 
 
                        active(0), 
                        admitted(1), 
                        provisioned(2) 
                      } 
     MAX-ACCESS  read-only 
     STATUS      current 
     DESCRIPTION 
        "This attribute represents the status of the service 
        flow based on the admission state. 
        'active' bit set to '1' indicates that the service flow 
        is active and that the corresponding QOS ParamSet 
        is stored in the CMTS. 
        'admitted' bit set to '1' indicates that the service 
        flow resources were reserved  and that the corresponding 
        QOS ParamSet is stored in the CMTS. 
        'provisioned' bit set to '1' indicates that the service 
        flow was defined in the CM config file and that the 
        corresponding QOS ParamSet is stored in the CMTS." 
     REFERENCE 
        "DOCSIS 3.0 MAC and Upper Layer Protocols Interface 
        Specification CM-SP-MULPIv3.0-I05-070803, Service  
        Flow Section." 
     ::= { docsQos3ServiceFlowEntry 9 } 
 
docsQos3ServiceFlowChSetId OBJECT-TYPE 
     SYNTAX      ChSetId 
     MAX-ACCESS  read-only 
     STATUS      current 
     DESCRIPTION 
        "This attribute represents the Channel Set Id associated 
        with the service flow." 
     ::= { docsQos3ServiceFlowEntry 10 } 
 
docsQos3ServiceFlowAttrAssignSuccess OBJECT-TYPE 
     SYNTAX      TruthValue 
     MAX-ACCESS  read-only 
     STATUS      current 
     DESCRIPTION 
        "If set to 'true', this attribute indicates that the 
        current channel set associated with the service flow 
        meets the Required and Forbidden Attribute Mask encodings." 
     REFERENCE 
        "DOCSIS 3.0 MAC and Upper Layer Protocols Interface 
        Specification CM-SP-MULPIv3.0-I05-070803, Service Flow 
        section." 
     ::= { docsQos3ServiceFlowEntry 11 } 
 
docsQos3ServiceFlowDsid OBJECT-TYPE 
     SYNTAX      Dsid 
     MAX-ACCESS  read-only 
     STATUS      current 
     DESCRIPTION 
        "This attribute indicates the DSID associated with 
        the downstream service flow. downstream service flows 
        without a DSID or upstream Service Flows report 
        the value zero." 
     ::= { docsQos3ServiceFlowEntry 12 } 
 
docsQos3ServiceFlowStatsTable OBJECT-TYPE 
     SYNTAX      SEQUENCE OF DocsQos3ServiceFlowStatsEntry 
     MAX-ACCESS  not-accessible 
     STATUS      current 
     DESCRIPTION 
        "This object describes statistics associated with 
        the  Service Flows in a managed device." 
     ::= { docsQos3MibObjects 4} 
 
docsQos3ServiceFlowStatsEntry OBJECT-TYPE 
     SYNTAX      DocsQos3ServiceFlowStatsEntry 
     MAX-ACCESS  not-accessible 
     STATUS      current 
     DESCRIPTION 
        "The conceptual row of docsQos3ServiceFlowStatsTable. 
        The ifIndex key corresponds to the MAC Domain interface 
        of the service flow." 
     INDEX { ifIndex,docsQos3ServiceFlowId } 
     ::= { docsQos3ServiceFlowStatsTable 1 } 
 
DocsQos3ServiceFlowStatsEntry ::= SEQUENCE { 
     docsQos3ServiceFlowPkts 
                  Counter64, 
     docsQos3ServiceFlowOctets 
                  Counter64, 
     docsQos3ServiceFlowTimeCreated 
                  TimeStamp, 
     docsQos3ServiceFlowTimeActive 
                  Counter32, 
     docsQos3ServiceFlowPHSUnknowns 
                  Counter32, 
     docsQos3ServiceFlowPolicedDropPkts 
                  Counter32, 
     docsQos3ServiceFlowPolicedDelayPkts 
                  Counter32 
     } 
 
docsQos3ServiceFlowPkts OBJECT-TYPE 
     SYNTAX      Counter64 
     UNITS       "packets" 
     MAX-ACCESS  read-only 
     STATUS      current 
     DESCRIPTION 
        "For outgoing Service Flows, this attribute counts 
        the number of Packet Data PDUs forwarded to this Service 
        Flow.  For incoming upstream CMTS service flows, 
        this attribute counts the number of Packet Data PDUs 
        actually received on the Service Flow identified by 
        the SID for which the packet was scheduled.  CMs not classifying 
        downstream packets may report this attribute's 
        value as 0 for downstream Service Flows.  This 
        attribute does not count MAC-specific management 
        messages. 
         
        Particularly for UGS flows, packets sent on the primary 
        Service Flow in violation of the UGS grant size should 
        be counted only by the instance of this attribute 
        that is associated with the primary service flow. 
         
        Unclassified upstream user data packets (i.e., non- 
        MAC-management) forwarded to the primary upstream 
        Service Flow should be counted by the instance of this 
        attribute that is associated with the primary service 
        flow. 
         
        This attribute does include packets counted by  
        ServiceFlowPolicedDelayPkts, but does not include packets 
        counted by ServiceFlowPolicedDropPkts and  
        ServiceFlowPHSUnknowns. 
         
         
        This counter's last discontinuity is the  
        ifCounterDiscontinuityTime for of the associated MAC Domain 
        interface index." 
     ::= { docsQos3ServiceFlowStatsEntry 1 } 
 
docsQos3ServiceFlowOctets OBJECT-TYPE 
     SYNTAX      Counter64 
     UNITS       "bytes" 
     MAX-ACCESS  read-only 
     STATUS      current 
     DESCRIPTION 
        "This attribute indicates the count of the number of 
        octets from the byte after the MAC header HCS to the end 
        of the CRC for all packets counted in the ServiceFlowPkts 
        attribute for this row.  Note that this counts 
        the octets after payload header suppression and before 
        payload header expansion have been applied. 
         
        This counter's last discontinuity is the  
        ifCounterDiscontinuityTime for of the associated MAC Domain 
        interface index." 
     ::= { docsQos3ServiceFlowStatsEntry 2 } 
 
docsQos3ServiceFlowTimeCreated OBJECT-TYPE 
     SYNTAX      TimeStamp 
     MAX-ACCESS  read-only 
     STATUS      current 
     DESCRIPTION 
        "This attribute indicates the value of sysUpTime when 
        the service flow was created." 
     ::= { docsQos3ServiceFlowStatsEntry 3 } 
 
docsQos3ServiceFlowTimeActive OBJECT-TYPE 
     SYNTAX      Counter32 
     UNITS       "seconds" 
     MAX-ACCESS  read-only 
     STATUS      current 
     DESCRIPTION 
        "This attribute indicates the number of seconds that 
        the service flow has been active. 
         
        This counter's last discontinuity is the  
        ifCounterDiscontinuityTime for of the associated MAC Domain 
        interface index." 
     ::= { docsQos3ServiceFlowStatsEntry 4 } 

docsQos3ServiceFlowPHSUnknowns OBJECT-TYPE 
     SYNTAX      Counter32 
     UNITS       "packets" 
     MAX-ACCESS  read-only 
     STATUS      current 
     DESCRIPTION 
        "For incoming upstream CMTS service flows, this attribute 
        counts the number of packets received with an 
        unknown payload header suppression index. 
        The service flow is identified by the SID for which the 
        packet was scheduled. 
        On a CM, only this attribute's instance for the primary 
        downstream service flow counts packets received 
        with an unknown payload header suppression index.  All 
        other downstream service flows on CM report this attributes 
        value as 0. 
        All outgoing service flows report this attribute's 
        value as 0. 
         
        This counter's last discontinuity is the  
        ifCounterDiscontinuityTime for of the associated MAC Domain 
        interface index." 
     ::= { docsQos3ServiceFlowStatsEntry 5 } 
 
docsQos3ServiceFlowPolicedDropPkts OBJECT-TYPE 
     SYNTAX      Counter32 
     UNITS       "packets" 
     MAX-ACCESS  read-only 
     STATUS      current 
     DESCRIPTION 
        "For outgoing service flows, this attribute counts 
        the number of Packet Data PDUs classified to this service 
        flow dropped due to: 
        (1) implementation-dependent excessive delay while 
        enforcing the Maximum Sustained Traffic Rate; or 
         
        (2) UGS packets dropped due to exceeding the Unsolicited 
        Grant Size with a Request/Transmission policy 
        that requires such packets to be dropped. 
         
        Classified packets dropped due to other reasons must 
        be counted in ifOutDiscards for the interface of this 
        service flow.  This attribute reports 0 for incoming 
        service flows. 
         
        This counter's last discontinuity is the  
        ifCounterDiscontinuityTime for of the associated MAC Domain 
        interface index." 
     ::= { docsQos3ServiceFlowStatsEntry 6 } 
 
docsQos3ServiceFlowPolicedDelayPkts OBJECT-TYPE 
     SYNTAX      Counter32 
     UNITS       "packets" 
     MAX-ACCESS  read-only 
     STATUS      current 
     DESCRIPTION 
        "This attribute counts only outgoing packets delayed 
        in order to maintain the Maximum Sustained Traffic 
        Rate.  This attribute will always report a value of 
        0 for UGS flows because the Maximum Sustained Traffic 
        Rate does not apply.  This attribute is 0 for incoming 
        service flows. 
         
        This counter's last discontinuity is the  
        ifCounterDiscontinuityTime for of the associated MAC Domain 
        interface index." 
     ::= { docsQos3ServiceFlowStatsEntry 7 } 

docsQos3UpstreamStatsTable OBJECT-TYPE 
     SYNTAX      SEQUENCE OF DocsQos3UpstreamStatsEntry 
     MAX-ACCESS  not-accessible 
     STATUS      current 
     DESCRIPTION 
        "This object describes statistics associated with 
        upstream service flows.  All counted frames must be 
        received without a Frame Check Sequence (FCS) error." 
     ::= { docsQos3MibObjects 5} 
 
docsQos3UpstreamStatsEntry OBJECT-TYPE 
     SYNTAX      DocsQos3UpstreamStatsEntry 
     MAX-ACCESS  not-accessible 
     STATUS      current 
     DESCRIPTION 
        "The conceptual row of docsQos3UpstreamStatsTable. 
        The ifIndex key corresponds to the upstream logical channel  
        interface of the service flow." 
     INDEX { ifIndex,docsQos3SID } 
     ::= { docsQos3UpstreamStatsTable 1 } 
 
DocsQos3UpstreamStatsEntry ::= SEQUENCE { 
     docsQos3SID 
                  Unsigned32, 
     docsQos3UpstreamFragments 
                  Counter32, 
     docsQos3UpstreamFragDiscards 
                  Counter32, 
     docsQos3UpstreamConcatBursts 
                  Counter32 
     } 
 
docsQos3SID OBJECT-TYPE 
     SYNTAX      Unsigned32 (1..16383) 
     MAX-ACCESS  not-accessible 
     STATUS      current 
     DESCRIPTION 
        "This key identifies a service ID for an admitted 
        or active upstream service flow." 
     ::= { docsQos3UpstreamStatsEntry 1 } 
 
docsQos3UpstreamFragments OBJECT-TYPE 
     SYNTAX      Counter32 
     UNITS       "fragments" 
     MAX-ACCESS  read-only 
     STATUS      current 
     DESCRIPTION 
        "This attribure indicates the number of fragmentation 
        headers received on an upstream service flow, regardless 
        of whether the fragment was correctly reassembled 
        into a valid packet. 
         
        This counter's last discontinuity is the  
        ifCounterDiscontinuityTime for of the associated MAC Domain 
        interface index." 
     ::= { docsQos3UpstreamStatsEntry 2 } 
 
docsQos3UpstreamFragDiscards OBJECT-TYPE 
     SYNTAX      Counter32 
     UNITS       "fragments" 
     MAX-ACCESS  read-only 
     STATUS      current 
     DESCRIPTION 
        "This attribute indicates the number of upstream fragments 
        discarded and not assembled into a valid upstream 
        packet.  
        This counter's last discontinuity is the  
        ifCounterDiscontinuityTime for of the associated MAC Domain 
        interface index." 
     ::= { docsQos3UpstreamStatsEntry 3 } 
 
docsQos3UpstreamConcatBursts OBJECT-TYPE 
     SYNTAX      Counter32 
     UNITS       "headers" 
     MAX-ACCESS  read-only 
     STATUS      current 
     DESCRIPTION 
        "This attribute indicates the number of concatenation 
        headers received on an upstream service flow. 
        This counter's last discontinuity is the  
        ifCounterDiscontinuityTime for of the associated MAC Domain 
        interface index." 
     ::= { docsQos3UpstreamStatsEntry 4 } 
 
docsQos3DynamicServiceStatsTable OBJECT-TYPE 
     SYNTAX      SEQUENCE OF DocsQos3DynamicServiceStatsEntry 
     MAX-ACCESS  not-accessible 
     STATUS      current 
     DESCRIPTION 
        "This object describes statistics associated with 
        the Dynamic Service Flows, Dynamic Channel Changes 
        and Dynamic Bonding Changes in a managed device within 
        a MAC Domain. 
        For each MAC Domain there are two instances for the for 
        the upstream and downstream 
        direction. 
        On the CMTS, the downstream direction instance indicates 
        messages transmitted or transactions originated 
        by the CMTS.  The upstream direction intance indicates 
        messages received or transaction originated 
        by the CM. 
        On the CM, the downstream direction instance indicates 
        messages received or transactions originated by 
        the CMTS.  The upstream direction instance indicates 
        messages transmitted by the CM or transactions originated 
        by the CM." 
     ::= { docsQos3MibObjects 6} 
 
docsQos3DynamicServiceStatsEntry OBJECT-TYPE 
     SYNTAX      DocsQos3DynamicServiceStatsEntry 
     MAX-ACCESS  not-accessible 
     STATUS      current 
     DESCRIPTION 
        "The conceptual row of docsQos3DynamicServiceStatsTable. 
        The ifIndex key corresponds to the MAC Domain interface 
        of the service flow." 
     INDEX { ifIndex,docsQos3IfDirection } 
     ::= { docsQos3DynamicServiceStatsTable 1 } 
 
DocsQos3DynamicServiceStatsEntry ::= SEQUENCE { 
     docsQos3IfDirection 
                  IfDirection, 
     docsQos3DSAReqs 
                  Counter32, 
     docsQos3DSARsps 
                  Counter32, 
     docsQos3DSAAcks 
                  Counter32, 
     docsQos3DSCReqs 
                  Counter32, 
     docsQos3DSCRsps 
                  Counter32, 
     docsQos3DSCAcks 
                  Counter32, 
     docsQos3DSDReqs 
                  Counter32, 
     docsQos3DSDRsps 
                  Counter32, 
     docsQos3DynamicAdds 
                  Counter32, 
     docsQos3DynamicAddFails 
                  Counter32, 
     docsQos3DynamicChanges 
                  Counter32, 
     docsQos3DynamicChangeFails 
                  Counter32, 
     docsQos3DynamicDeletes 
                  Counter32, 
     docsQos3DynamicDeleteFails 
                  Counter32, 
     docsQos3DCCReqs 
                  Counter32, 
     docsQos3DCCRsps 
                  Counter32, 
     docsQos3DCCAcks 
                  Counter32, 
     docsQos3DCCs 
                  Counter32, 
     docsQos3DCCFails 
                  Counter32, 
     docsQos3DCCRspDeparts 
                  Counter32, 
     docsQos3DCCRspArrives 
                  Counter32, 
     docsQos3DbcReqs 
                  Counter32, 
     docsQos3DbcRsps 
                  Counter32, 
     docsQos3DbcAcks 
                  Counter32, 
     docsQos3DbcSuccesses 
                  Counter32, 
     docsQos3DbcFails 
                  Counter32, 
     docsQos3DbcPartial 
                  Counter32 
     } 
 
docsQos3IfDirection OBJECT-TYPE 
     SYNTAX      IfDirection 
     MAX-ACCESS  not-accessible 
     STATUS      current 
     DESCRIPTION 
        "This attribute indicates the interface direction 
        for the instance the statistics are collected." 
     ::= { docsQos3DynamicServiceStatsEntry 1 } 
 
docsQos3DSAReqs OBJECT-TYPE 
     SYNTAX      Counter32 
     MAX-ACCESS  read-only 
     STATUS      current 
     DESCRIPTION 
        "This attribute indicates the number of Dynamic Service 
        Addition Requests, including retries. 
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Addition section; [RFC 2863]." 
     ::= { docsQos3DynamicServiceStatsEntry 2 } 
 
docsQos3DSARsps OBJECT-TYPE 
     SYNTAX      Counter32 
     MAX-ACCESS  read-only 
     STATUS      current 
     DESCRIPTION 
        "The number of Dynamic Service Addition Responses, 
        including retries. 
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Addition section; [RFC 2863]." 
     ::= { docsQos3DynamicServiceStatsEntry 3 } 
 
docsQos3DSAAcks OBJECT-TYPE 
     SYNTAX      Counter32 
     MAX-ACCESS  read-only 
     STATUS      current 
     DESCRIPTION 
        "The number of Dynamic Service Addition Acknowledgements, 
        including retries. 
        Discontinuities in the value of this counter can occur 
        at reinitialization of the managed system, and at 
        other times as indicated by the value of  
        ifCounterDiscontinuityTime of the associated MAC Domain  
        interface index." 
     REFERENCE 
        "DOCSIS 3.0 MAC and Upper Layer Protocols Interface 
        Specification CM-SP-MULPIv3.0-I05-070803, Dynamic Service 
        Addition section; [RFC 2863]." 
     ::= { docsQos3DynamicServiceStatsEntry 4 } 
 
docsQos3DSCReqs OBJECT-TYPE 
     SYNTAX      Counter32 
     MAX-ACCESS  read-only 
     STATUS      current 
     DESCRIPTION 
        "The number of Dynamic Service Change Requests, including 
        retries. 
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Change section; [RFC 2863]." 
     ::= { docsQos3DynamicServiceStatsEntry 5 } 
 
docsQos3DSCRsps OBJECT-TYPE 
     SYNTAX      Counter32 
     MAX-ACCESS  read-only 
     STATUS      current 
     DESCRIPTION 
        "The number of Dynamic Service Change Responses, including 
        retries. 
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Change section; [RFC 2863]." 
     ::= { docsQos3DynamicServiceStatsEntry 6 } 
 
docsQos3DSCAcks OBJECT-TYPE 
     SYNTAX      Counter32 
     MAX-ACCESS  read-only 
     STATUS      current 
     DESCRIPTION 
        "The number of Dynamic Service Change Acknowledgements, 
        including retries. 
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Change section; [RFC 2863]." 
     ::= { docsQos3DynamicServiceStatsEntry 7 } 
 
docsQos3DSDReqs OBJECT-TYPE 
     SYNTAX      Counter32 
     MAX-ACCESS  read-only 
     STATUS      current 
     DESCRIPTION 
        "The number of Dynamic Service Delete Requests, including 
        retries. 
        Discontinuities in the value of this counter can occur 
        at reinitialization of the managed system, and at 
        other times as indicated by the value of  
        ifCounterDiscontinuityTime of the associated MAC Domain  
        interface index." 
     REFERENCE 
        "DOCSIS 3.0 MAC and Upper Layer Protocols Interface 
        Specification CM-SP-MULPIv3.0-I05-070803, Dynamic Service 
        Delete section; [RFC 2863]." 
     ::= { docsQos3DynamicServiceStatsEntry 8 } 
 
docsQos3DSDRsps OBJECT-TYPE 
     SYNTAX      Counter32 
     MAX-ACCESS  read-only 
     STATUS      current 
     DESCRIPTION 
        "The number of Dynamic Service Delete Responses, including 
        retries. 
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Delete section; [RFC 2863]." 
     ::= { docsQos3DynamicServiceStatsEntry 9 } 
 
docsQos3DynamicAdds OBJECT-TYPE 
     SYNTAX      Counter32 
     MAX-ACCESS  read-only 
     STATUS      current 
     DESCRIPTION 
        "The number of successful Dynamic Service Addition 
        transactions. 
        Discontinuities in the value of this counter can occur 
        at reinitialization of the managed system, and at 
        other times as indicated by the value of 
        ifCounterDiscontinuityTime of the associated MAC Domain 
        interface index." 
     REFERENCE 
        "DOCSIS 3.0 MAC and Upper Layer Protocols Interface 
        Specification CM-SP-MULPIv3.0-I05-070803, Dynamic Service 
        Addition section; [RFC 2863]." 
     ::= { docsQos3DynamicServiceStatsEntry 10 } 
 
docsQos3DynamicAddFails OBJECT-TYPE 
     SYNTAX      Counter32 
     MAX-ACCESS  read-only 
     STATUS      current 
     DESCRIPTION 
        "The number of failed Dynamic Service Addition transactions. 
         
        Discontinuities in the value of this counter can occur 
        at reinitialization of the managed system, and at 
        other times as indicated by the value of 
        ifCounterDiscontinuityTime of the associated MAC Domain 
        interface index." 
     REFERENCE 
        "DOCSIS 3.0 MAC and Upper Layer Protocols Interface 
        Specification CM-SP-MULPIv3.0-I05-070803, Dynamic Service 
        Addition section; [RFC 2863]." 
     ::= { docsQos3DynamicServiceStatsEntry 11 } 
 
docsQos3DynamicChanges OBJECT-TYPE 
     SYNTAX      Counter32 
     MAX-ACCESS  read-only 
     STATUS      current 
     DESCRIPTION 
        "The number of successful Dynamic Service Change transactions. 
         
        Discontinuities in the value of this counter can occur 
        at reinitialization of the managed system, and at 
        other times as indicated by the value of 
        ifCounterDiscontinuityTime of the associated MAC Domain 
        interface index." 
     REFERENCE 
        "DOCSIS 3.0 MAC and Upper Layer Protocols Interface 
        Specification CM-SP-MULPIv3.0-I05-070803, Dynamic Service 
        Change section; [RFC 2863]." 
     ::= { docsQos3DynamicServiceStatsEntry 12 } 
 
docsQos3DynamicChangeFails OBJECT-TYPE 
     SYNTAX      Counter32 
     MAX-ACCESS  read-only 
     STATUS      current 
     DESCRIPTION 
        "The number of failed Dynamic Service Change transactions. 
         
        Discontinuities in the value of this counter can occur 
        at reinitialization of the managed system, and at 
        other times as indicated by the value of  
        ifCounterDiscontinuityTime of the associated MAC Domain  
        interface index." 
     REFERENCE 
        "DOCSIS 3.0 MAC and Upper Layer Protocols Interface 
        Specification CM-SP-MULPIv3.0-I05-070803, Dynamic Service 
        Change section; [RFC 2863]." 
        ::= { docsQos3DynamicServiceStatsEntry 13 } 
 
docsQos3DynamicDeletes OBJECT-TYPE 
     SYNTAX      Counter32 
     MAX-ACCESS  read-only 
     STATUS      current 
     DESCRIPTION 
        "The number of successful Dynamic Service Delete transactions. 
         
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Delete section; [RFC 2863]." 
     ::= { docsQos3DynamicServiceStatsEntry 14 } 
 
docsQos3DynamicDeleteFails OBJECT-TYPE 
     SYNTAX      Counter32 
     MAX-ACCESS  read-only 
     STATUS      current 
     DESCRIPTION 
        "The number of failed Dynamic Service Delete transactions. 
         
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Service 
        Delete section; [RFC 2863]." 
     ::= { docsQos3DynamicServiceStatsEntry 15 } 
 
docsQos3DCCReqs OBJECT-TYPE 
     SYNTAX      Counter32 
     MAX-ACCESS  read-only 
     STATUS      current 
     DESCRIPTION 
        "The number of Dynamic Channel Change Request messages 
        traversing an interface.  This count is nonzero 
        only on downstream direction rows. This count should 
        include the number of retries. 
        Discontinuities in the value of this counter can occur 
        at reinitialization of the managed system, and at 
        other times as indicated by the value of  
        ifCounterDiscontinuityTime of the associated MAC Domain 
        interface index." 
     REFERENCE 
        "DOCSIS 3.0 MAC and Upper Layer Protocols Interface 
        Specification CM-SP-MULPIv3.0-I05-070803, Dynamic Downstream 
        and/or Upstream Channel Changes section; [RFC 2863]." 
     ::= { docsQos3DynamicServiceStatsEntry 16 } 
 
docsQos3DCCRsps OBJECT-TYPE 
     SYNTAX      Counter32 
     MAX-ACCESS  read-only 
     STATUS      current 
     DESCRIPTION 
        "The number of Dynamic Channel Change Response messages 
        traversing an interface. This count is nonzero 
        only on upstream direction rows.  This count should 
        include the number of retries. 
        Discontinuities in the value of this counter can occur 
        at reinitialization of the managed system, and at 
        other times as indicated by the value of 
        ifCounterDiscontinuityTime of the associated MAC Domain 
        interface index." 
     REFERENCE 
        "DOCSIS 3.0 MAC and Upper Layer Protocols Interface 
        Specification CM-SP-MULPIv3.0-I05-070803, Dynamic Downstream 
        and/or Upstream Channel Changes section; [RFC 2863]." 
     ::= { docsQos3DynamicServiceStatsEntry 17 } 
 
docsQos3DCCAcks OBJECT-TYPE 
     SYNTAX      Counter32 
     MAX-ACCESS  read-only 
     STATUS      current 
     DESCRIPTION 
        "The number of Dynamic Channel Change Acknowledgement 
        messages traversing an interface.  This count is 
        nonzero only on downstream direction rows. This count 
        should include the number of retries. 
        Discontinuities in the value of this counter can occur 
        at reinitialization of the managed system, and at 
        other times as indicated by the value of 
        ifCounterDiscontinuityTime of the associated MAC Domain 
        interface index." 
     REFERENCE 
        "DOCSIS 3.0 MAC and Upper Layer Protocols Interface 
        Specification CM-SP-MULPIv3.0-I05-070803, Dynamic Downstream 
        and/or Upstream Channel Changes section; [RFC 2863]." 
     ::= { docsQos3DynamicServiceStatsEntry 18 } 
 
docsQos3DCCs OBJECT-TYPE 
     SYNTAX      Counter32 
     MAX-ACCESS  read-only 
     STATUS      current 
     DESCRIPTION 
        "The number of successful Dynamic Channel Change transactions. 
        This count is nonzero only on downstream 
        direction rows. 
        Discontinuities in the value of this counter can occur 
        at reinitialization of the managed system, and at 
        other times as indicated by the value of 
        ifCounterDiscontinuityTime of the associated MAC Domain 
        interface index." 
     REFERENCE 
        "DOCSIS 3.0 MAC and Upper Layer Protocols Interface 
        Specification CM-SP-MULPIv3.0-I05-070803, Dynamic Downstream 
        and/or Upstream Channel Changes section; [RFC 2863]." 
     ::= { docsQos3DynamicServiceStatsEntry 19 } 
 
docsQos3DCCFails OBJECT-TYPE 
     SYNTAX      Counter32 
     MAX-ACCESS  read-only 
     STATUS      current 
     DESCRIPTION 
        "The number of failed Dynamic Channel Change transactions. 
        This count is nonzero only on downstream direction 
        rows. 
        Discontinuities in the value of this counter can occur 
        at reinitialization of the managed system, and at 
        other times as indicated by the value of 
        ifCounterDiscontinuityTime of the associated MAC Domain 
        interface index." 
     REFERENCE 
        "DOCSIS 3.0 MAC and Upper Layer Protocols Interface 
        Specification CM-SP-MULPIv3.0-I05-070803, Dynamic Downstream 
        and/or Upstream Channel Changes section; [RFC 2863]." 
     ::= { docsQos3DynamicServiceStatsEntry 20 } 
 
docsQos3DCCRspDeparts OBJECT-TYPE 
     SYNTAX      Counter32 
     MAX-ACCESS  read-only 
     STATUS      current 
     DESCRIPTION 
        "This attribute contains the number of Dynamic Channel 
        Change Response (depart) messages. It only applies 
        to upstream direction. Discontinuities in the 
        value of this counter can occur at reinitialization 
        of the managed system, and at other times as indicated 
        by the value of ifCounterDiscontinuityTime of the 
        associated MAC Domain interface index." 
     REFERENCE 
        "DOCSIS 3.0 MAC and Upper Layer Protocols Interface 
        Specification CM-SP-MULPIv3.0-I05-070803, Dynamic Downstream 
        and/or Upstream Channel Changes section; [RFC 2863]." 
     ::= { docsQos3DynamicServiceStatsEntry 21 } 
 
docsQos3DCCRspArrives OBJECT-TYPE 
     SYNTAX      Counter32 
     MAX-ACCESS  read-only 
     STATUS      current 
     DESCRIPTION 
        "This attribute contains the number of Dynamic Channel 
        Change Response (arrive) messages and should include 
        retries. It only applies to the upstream direction. 
        Discontinuities in the value of this counter 
        can occur at reinitialization of the managed system, 
        and at other times as indicated by the value of  
        ifCounterDiscontinuityTime of the associated MAC Domain 
        interface index." 
     REFERENCE 
        "DOCSIS 3.0 MAC and Upper Layer Protocols Interface 
        Specification CM-SP-MULPIv3.0-I05-070803, Dynamic Downstream 
        and/or Upstream Channel Changes section; [RFC 2863]." 
     ::= { docsQos3DynamicServiceStatsEntry 22 } 
 
docsQos3DbcReqs OBJECT-TYPE 
     SYNTAX      Counter32 
     MAX-ACCESS  read-only 
     STATUS      current 
     DESCRIPTION 
        "This attribute contains the number of Dynamic Bonding 
        Change Requests, including retries. It only applies 
        to the upstream direction. Discontinuities in 
        the value of this counter can occur at reinitialization 
        of the managed system, and at other times as indicated 
        by the value of ifCounterDiscontinuityTime of 
        the associated MAC Domain interface index." 
     REFERENCE 
        "DOCSIS 3.0 MAC and Upper Layer Protocols Interface 
        Specification CM-SP-MULPIv3.0-I05-070803, Dynamic Bonding 
        Change (DBC) section; [RFC 2863]." 
     ::= { docsQos3DynamicServiceStatsEntry 23 } 
 
docsQos3DbcRsps OBJECT-TYPE 
     SYNTAX      Counter32 
     MAX-ACCESS  read-only 
     STATUS      current 
     DESCRIPTION 
        "This attribute contains the number of Dynamic Bonding 
        Change Responses, including retries. It only applies 
        to the upstream direction. Discontinuities 
        in the value of this counter can occur at reinitialization 
        of the managed system, and at other times as indicated 
        by the value of ifCounterDiscontinuityTime 
        of the associated MAC Domain interface index." 
     REFERENCE 
        "DOCSIS 3.0 MAC and Upper Layer Protocols Interface 
        Specification CM-SP-MULPIv3.0-I05-070803, Dynamic Bonding 
        Change (DBC) section; [RFC 2863]." 
     ::= { docsQos3DynamicServiceStatsEntry 24 } 
 
docsQos3DbcAcks OBJECT-TYPE 
     SYNTAX      Counter32 
     MAX-ACCESS  read-only 
     STATUS      current 
     DESCRIPTION 
        "This attribute contains the number of Dynamic Bonding 
        Change Acknowledgements, including retries. 
        It only applies to the downstream direction. Discontinuities 
        in the value of this counter can occur at reinitialization 
        of the managed system, and at other times 
        as indicated by the value of ifCounterDiscontinuityTime 
        of the associated MAC Domain interface index." 
     REFERENCE 
        "DOCSIS 3.0 MAC and Upper Layer Protocols Interface 
        Specification CM-SP-MULPIv3.0-I05-070803, Dynamic Bonding 
        Change (DBC) section; [RFC 2863]." 
     ::= { docsQos3DynamicServiceStatsEntry 25 } 
 
docsQos3DbcSuccesses OBJECT-TYPE 
     SYNTAX      Counter32 
     MAX-ACCESS  read-only 
     STATUS      current 
     DESCRIPTION 
        "This attribute contains the number of fully successful 
        Dynamic Bonding Change transactions. It only 
        applies to the downstream direction and does not include 
        DBC transactions that result in Partial Service. 
        Discontinuities in the value of this counter can occur 
        at reinitialization of the managed system, and 
        at other times as indicated by the value of  
        ifCounterDiscontinuityTime of the associated MAC Domain 
        interface index." 
     REFERENCE 
        "DOCSIS 3.0 MAC and Upper Layer Protocols Interface 
        Specification CM-SP-MULPIv3.0-I05-070803, Dynamic Bonding 
        Change (DBC) section; [RFC 2863]." 
     ::= { docsQos3DynamicServiceStatsEntry 26 } 
 
docsQos3DbcFails OBJECT-TYPE 
     SYNTAX      Counter32 
     MAX-ACCESS  read-only 
     STATUS      current 
     DESCRIPTION 
        "This attribute contains the number of failed Dynamic 
        Bonding Change transactions. It only applies to 
        the downstream direction. Note that Partial Service 
        is not considered a failed transaction. Discontinuities 
        in the value of this counter can occur at reinitialization 
        of the managed system, and at other times 
        as indicated by the value of ifCounterDiscontinuityTime 
        of the associated MAC Domain interface index." 
     REFERENCE 
        "DOCSIS 3.0 MAC and Upper Layer Protocols Interface 
        Specification CM-SP-MULPIv3.0-I05-070803, Dynamic Bonding 
        Change (DBC) section; [RFC 2863]." 
     ::= { docsQos3DynamicServiceStatsEntry 27 } 
 
docsQos3DbcPartial OBJECT-TYPE 
     SYNTAX      Counter32 
     MAX-ACCESS  read-only 
     STATUS      current 
     DESCRIPTION 
        "This attribute contains the number of unsuccessful 
        Dynamic Bonding Change transactions that result 
        in Partial Service. IT only applies to the downstream 
        direction. Discontinuities in the value of this counter 
        can occur at reinitialization of the managed system, 
        and at other times as indicated by the value of 
        ifCounterDiscontinuityTime of the associated MAC 
        Domain interface index." 
     REFERENCE 
        "DOCSIS 3.0 MAC and Upper Layer Protocols Interface 
        Specification CM-SP-MULPIv3.0-I05-070803, Dynamic Bonding 
        Change (DBC) section; [RFC 2863]." 
     ::= { docsQos3DynamicServiceStatsEntry 28 } 
 
docsQos3ServiceFlowLogTable OBJECT-TYPE 
     SYNTAX      SEQUENCE OF DocsQos3ServiceFlowLogEntry 
     MAX-ACCESS  not-accessible 
     STATUS      current 
     DESCRIPTION 
        "This object contains a log of the disconnected Service 
        Flows in a managed device." 
     ::= { docsQos3MibObjects 7} 
 
docsQos3ServiceFlowLogEntry OBJECT-TYPE 
     SYNTAX      DocsQos3ServiceFlowLogEntry 
     MAX-ACCESS  not-accessible 
     STATUS      current 
     DESCRIPTION 
        "The conceptual row of docsQos3ServiceFlowLogTable." 
     INDEX { docsQos3ServiceFlowLogIndex } 
     ::= { docsQos3ServiceFlowLogTable 1 } 
 
DocsQos3ServiceFlowLogEntry ::= SEQUENCE { 
     docsQos3ServiceFlowLogIndex 
                  Unsigned32, 
     docsQos3ServiceFlowLogIfIndex 
                  InterfaceIndex, 
     docsQos3ServiceFlowLogSFID 
                  Unsigned32, 
     docsQos3ServiceFlowLogCmMac 
                  MacAddress, 
     docsQos3ServiceFlowLogPkts 
                  Counter64, 
     docsQos3ServiceFlowLogOctets 
                  Counter64, 
     docsQos3ServiceFlowLogTimeDeleted 
                  TimeStamp, 
     docsQos3ServiceFlowLogTimeCreated 
                  TimeStamp, 
     docsQos3ServiceFlowLogTimeActive 
                  Counter32, 
     docsQos3ServiceFlowLogDirection 
                  IfDirection, 
     docsQos3ServiceFlowLogPrimary 
                  TruthValue, 
     docsQos3ServiceFlowLogServiceClassName 
                  SnmpAdminString, 
     docsQos3ServiceFlowLogPolicedDropPkts 
                  Counter32, 
     docsQos3ServiceFlowLogPolicedDelayPkts 
                  Counter32, 
     docsQos3ServiceFlowLogControl 
                  INTEGER 
     } 

docsQos3ServiceFlowLogIndex OBJECT-TYPE 
     SYNTAX      Unsigned32 (1..4294967295) 
     MAX-ACCESS  not-accessible 
     STATUS      current 
     DESCRIPTION 
        "This key indicates an unique index for a logged service 
        flow." 
     ::= { docsQos3ServiceFlowLogEntry 1 } 
 
docsQos3ServiceFlowLogIfIndex OBJECT-TYPE 
     SYNTAX      InterfaceIndex 
     MAX-ACCESS  read-only 
     STATUS      current 
     DESCRIPTION 
        "This attribute indicates the MAC Domain Interface 
        index where the service flow was present." 
     ::= { docsQos3ServiceFlowLogEntry 2 } 
 
docsQos3ServiceFlowLogSFID OBJECT-TYPE 
     SYNTAX      Unsigned32 (1..4294967295) 
     MAX-ACCESS  read-only 
     STATUS      current 
     DESCRIPTION 
        "This attribute indicates the identifier assigned 
        to the service flow." 
     ::= { docsQos3ServiceFlowLogEntry 3 } 
 
docsQos3ServiceFlowLogCmMac OBJECT-TYPE 
     SYNTAX      MacAddress 
     MAX-ACCESS  read-only 
     STATUS      current 
     DESCRIPTION 
        "This attribute indicates the MAC address of the cable 
        modem associated with the service flow." 
     ::= { docsQos3ServiceFlowLogEntry 4 } 
 
docsQos3ServiceFlowLogPkts OBJECT-TYPE 
     SYNTAX      Counter64 
     UNITS       "packets" 
     MAX-ACCESS  read-only 
     STATUS      current 
     DESCRIPTION 
        "This attribute indicates the final value of the Pkts 
        attribute in the ServiceFlowStats object for the 
        service flow." 
     ::= { docsQos3ServiceFlowLogEntry 5 } 
 
docsQos3ServiceFlowLogOctets OBJECT-TYPE 
     SYNTAX      Counter64 
     UNITS       "bytes" 
     MAX-ACCESS  read-only 
     STATUS      current 
     DESCRIPTION 
        "This attribute indicates the final value of the Pkts 
        attribute in the ServiceFlowStats object for the 
        service flow." 
     ::= { docsQos3ServiceFlowLogEntry 6 } 
 
docsQos3ServiceFlowLogTimeDeleted OBJECT-TYPE 
     SYNTAX      TimeStamp 
     MAX-ACCESS  read-only 
     STATUS      current 
     DESCRIPTION 
        "This attribute indicates the value of sysUpTime when 
        the service flow was deleted." 
     ::= { docsQos3ServiceFlowLogEntry 7 } 

docsQos3ServiceFlowLogTimeCreated OBJECT-TYPE 
     SYNTAX      TimeStamp 
     MAX-ACCESS  read-only 
     STATUS      current 
     DESCRIPTION 
        "This attribute indicates the value of sysUpTime when 
        the service flow was created." 
     ::= { docsQos3ServiceFlowLogEntry 8 } 
 
docsQos3ServiceFlowLogTimeActive OBJECT-TYPE 
     SYNTAX      Counter32 
     UNITS       "seconds" 
     MAX-ACCESS  read-only 
     STATUS      current 
     DESCRIPTION 
        "This attribute indicates the total time that the service 
        flow was active." 
     ::= { docsQos3ServiceFlowLogEntry 9 } 
 
docsQos3ServiceFlowLogDirection OBJECT-TYPE 
     SYNTAX      IfDirection 
     MAX-ACCESS  read-only 
     STATUS      current 
     DESCRIPTION 
        "This attribute indicates the value of Service Flow 
        direction for the service flow." 
     ::= { docsQos3ServiceFlowLogEntry 11 } 
 
docsQos3ServiceFlowLogPrimary OBJECT-TYPE 
     SYNTAX      TruthValue 
     MAX-ACCESS  read-only 
     STATUS      current 
     DESCRIPTION 
        "If set to 'true', this attribute indicates that the 
        Service Flow in the log was a Primary Service Flow, otherwise, 
        a Secondary Service Flow." 
     ::= { docsQos3ServiceFlowLogEntry 12 } 
 
docsQos3ServiceFlowLogServiceClassName OBJECT-TYPE 
     SYNTAX      SnmpAdminString (SIZE(0..15)) 
     MAX-ACCESS  read-only 
     STATUS      current 
     DESCRIPTION 
        "This attribute indicates the value of ServiceClassName 
        for the provisioned QOS Parameter Set of the service 
        flow." 
     ::= { docsQos3ServiceFlowLogEntry 13 } 
 
docsQos3ServiceFlowLogPolicedDropPkts OBJECT-TYPE 
     SYNTAX      Counter32 
     UNITS       "packets" 
     MAX-ACCESS  read-only 
     STATUS      current 
     DESCRIPTION 
        "This attribute indicates the final value of PolicedDropPkts 
        attribute of the ServiceFlowStats object 
        for the service flow." 
     ::= { docsQos3ServiceFlowLogEntry 14 } 
 
docsQos3ServiceFlowLogPolicedDelayPkts OBJECT-TYPE 
     SYNTAX      Counter32 
     UNITS       "packets" 
     MAX-ACCESS  read-only 
     STATUS      current 
     DESCRIPTION 
        "This attribute indicates the final value of PolicedDelayPkts 
        attribute of the ServiceFlowStats object 
        for the service flow." 
     ::= { docsQos3ServiceFlowLogEntry 15 } 
 
docsQos3ServiceFlowLogControl OBJECT-TYPE 
     SYNTAX      INTEGER { 
 
                        active(1), 
                        destroy(6) 
                      } 
     MAX-ACCESS  read-write 
     STATUS      current 
     DESCRIPTION 
        "This attribute when set to 'destroy' removes this 
        instance from the object. 
        Reading this attribute returns the value 'active'." 
     ::= { docsQos3ServiceFlowLogEntry 16 } 
 
docsQos3ServiceClassTable OBJECT-TYPE 
     SYNTAX      SEQUENCE OF DocsQos3ServiceClassEntry 
     MAX-ACCESS  not-accessible 
     STATUS      current 
     DESCRIPTION 
        "This object describes a provisioned service class 
        on a CMTS. 
        Each object instance defines a template for certain 
        DOCSIS QOS Parameter Set values.  When a CM creates or 
        modifies an Admitted QOS Parameter Set for a Service 
        Flow, it may reference a Service Class Name instead of 
        providing explicit QOS Parameter 
        Set values.  In this case, the CMTS populates the QOS Parameter 
        Set with the applicable 
        corresponding values from the named Service Class. 
        Subsequent changes to a Service Class row do not affect 
        the QOS Parameter Set values of any service flows already 
        admitted.  
        A service class template applies to only a single direction, 
        as indicated in the ServiceClassDirection 
        attribute." 
     ::= { docsQos3MibObjects 8} 
 
docsQos3ServiceClassEntry OBJECT-TYPE 
     SYNTAX      DocsQos3ServiceClassEntry 
     MAX-ACCESS  not-accessible 
     STATUS      current 
     DESCRIPTION 
        "The conceptual row of docsQos3ServiceClassTable." 
     INDEX { docsQos3ServiceClassName } 
     ::= { docsQos3ServiceClassTable 1 } 
 
DocsQos3ServiceClassEntry ::= SEQUENCE { 
     docsQos3ServiceClassName 
                  SnmpAdminString, 
     docsQos3ServiceClassStatus 
                  RowStatus, 
     docsQos3ServiceClassPriority 
                  Unsigned32, 
     docsQos3ServiceClassMaxTrafficRate 
                  BitRate, 
     docsQos3ServiceClassMaxTrafficBurst 
                  Unsigned32, 
     docsQos3ServiceClassMinReservedRate 
                  BitRate, 
     docsQos3ServiceClassMinReservedPkt 
                  Unsigned32, 
     docsQos3ServiceClassMaxConcatBurst 
                  Unsigned32, 
     docsQos3ServiceClassNomPollInterval 
                  Unsigned32, 
     docsQos3ServiceClassTolPollJitter 
                  Unsigned32, 
     docsQos3ServiceClassUnsolicitGrantSize 
                  Unsigned32, 
     docsQos3ServiceClassNomGrantInterval 
                  Unsigned32, 
     docsQos3ServiceClassTolGrantJitter 
                  Unsigned32, 
     docsQos3ServiceClassGrantsPerInterval 
                  Unsigned32, 
     docsQos3ServiceClassMaxLatency 
                  Unsigned32, 
     docsQos3ServiceClassActiveTimeout 
                  Unsigned32, 
     docsQos3ServiceClassAdmittedTimeout 
                  Unsigned32, 
     docsQos3ServiceClassSchedulingType 
                  SchedulingType, 
     docsQos3ServiceClassRequestPolicy 
                  OCTET STRING, 
     docsQos3ServiceClassTosAndMask 
                  OCTET STRING, 
     docsQos3ServiceClassTosOrMask 
                  OCTET STRING, 
     docsQos3ServiceClassDirection 
                  IfDirection, 
     docsQos3ServiceClassStorageType 
                  StorageType, 
     docsQos3ServiceClassDSCPOverwrite 
                  DscpOrAny, 
     docsQos3ServiceClassRequiredAttrMask 
                  AttributeMask, 
     docsQos3ServiceClassForbiddenAttrMask 
                  AttributeMask, 
     docsQos3ServiceClassAttrAggrRuleMask 
                  AttrAggrRuleMask, 
     docsQos3ServiceClassAppId 
                  Unsigned32, 
     docsQos3ServiceClassMultiplierContentionReqWindow 
                  Unsigned32, 
     docsQos3ServiceClassMultiplierBytesReq 
                  Unsigned32, 
     docsQos3ServiceClassMaxReqPerSidCluster 
                  Unsigned32, 
     docsQos3ServiceClassMaxOutstandingBytesPerSidCluster 
                  Unsigned32, 
     docsQos3ServiceClassMaxTotBytesReqPerSidCluster 
                  Unsigned32, 
     docsQos3ServiceClassMaxTimeInSidCluster 
                  Unsigned32, 
     docsQos3ServiceClassPeakTrafficRate 
                  Unsigned32, 
     docsQos3ServiceClassDsResequencing 
                  INTEGER                   
     } 
 
docsQos3ServiceClassName OBJECT-TYPE 
     SYNTAX      SnmpAdminString (SIZE(1..15)) 
     MAX-ACCESS  not-accessible 
     STATUS      current 
     DESCRIPTION 
        "This key indicates the Service Class Name associated 
        with this object instance.  DOCSIS specifies 
        that the maximum size is 16 ASCII characters including 
        a terminating zero.  The terminating zero is not 
        represented in this SnmpAdminString syntax attribute." 
     REFERENCE 
        "DOCSIS 3.0 MAC and Upper Layer Protocols Interface 
        Specification CM-SP-MULPIv3.0-I05-070803, Service Class 
        Name section in the Common Radio Frequency Interface  
        Encodings Annex." 
     ::= { docsQos3ServiceClassEntry 1 } 
 
docsQos3ServiceClassStatus OBJECT-TYPE 
     SYNTAX      RowStatus 
     MAX-ACCESS  read-create 
     STATUS      current 
     DESCRIPTION 
        "The conceptual row status of this object." 
     ::= { docsQos3ServiceClassEntry 3 } 
 
docsQos3ServiceClassPriority OBJECT-TYPE 
     SYNTAX      Unsigned32 (0..7) 
     MAX-ACCESS  read-create 
     STATUS      current 
     DESCRIPTION 
        "This attribute is the template for the Priority attribute 
        of the QoS Parameter Set." 
     DEFVAL { 0 } 
     ::= { docsQos3ServiceClassEntry 4 } 
 
docsQos3ServiceClassMaxTrafficRate OBJECT-TYPE 
     SYNTAX      BitRate 
     UNITS       "bps" 
     MAX-ACCESS  read-create 
     STATUS      current 
     DESCRIPTION 
        "This attribute is the template for the MaxTrafficRate 
        attribute of the QoS Parameter Set." 
     DEFVAL { 0 } 
     ::= { docsQos3ServiceClassEntry 5 } 
 
docsQos3ServiceClassMaxTrafficBurst OBJECT-TYPE 
     SYNTAX      Unsigned32 
     UNITS       "bytes" 
     MAX-ACCESS  read-create 
     STATUS      current 
     DESCRIPTION 
        "This attribute is the template for the MaxTrafficBurst 
        attribute of the QoS Parameter Set." 
     DEFVAL { 3044 } 
     ::= { docsQos3ServiceClassEntry 6 } 
 
docsQos3ServiceClassMinReservedRate OBJECT-TYPE 
     SYNTAX      BitRate 
     UNITS       "bps" 
     MAX-ACCESS  read-create 
     STATUS      current 
     DESCRIPTION 
        "This attribute is the template for the MinReservedRate 
        attribute of the QoS Parameter Set." 
     DEFVAL { 0 } 
     ::= { docsQos3ServiceClassEntry 7 } 
 
docsQos3ServiceClassMinReservedPkt OBJECT-TYPE 
     SYNTAX      Unsigned32 (0..65535) 
     UNITS       "bytes" 
     MAX-ACCESS  read-create 
     STATUS      current 
     DESCRIPTION 
        "This attribute is the template for the MinReservedPkt 
        attribute of the QoS Parameter Set." 
        ::= { docsQos3ServiceClassEntry 8 } 
 
docsQos3ServiceClassMaxConcatBurst OBJECT-TYPE 
     SYNTAX      Unsigned32 (0..65535) 
     UNITS       "bytes" 
     MAX-ACCESS  read-create 
     STATUS      current 
     DESCRIPTION 
        "This attribute is the template for the MaxConcatBurst 
        attribute of the QoS Parameter Set." 
     DEFVAL { 1522 } 
     ::= { docsQos3ServiceClassEntry 9 } 
 
docsQos3ServiceClassNomPollInterval OBJECT-TYPE 
     SYNTAX      Unsigned32 
     UNITS       "microseconds" 
     MAX-ACCESS  read-create 
     STATUS      current 
     DESCRIPTION 
        "This attribute is the template for the NomPollInterval 
        attribute of the QoS Parameter Set." 
     DEFVAL { 0 } 
     ::= { docsQos3ServiceClassEntry 10 } 
 
docsQos3ServiceClassTolPollJitter OBJECT-TYPE 
     SYNTAX      Unsigned32 
     UNITS       "microseconds" 
     MAX-ACCESS  read-create 
     STATUS      current 
     DESCRIPTION 
        "This attribute is the template for the TolPolJitter 
        attribute of the QoS Parameter Set." 
     DEFVAL { 0 } 
     ::= { docsQos3ServiceClassEntry 11 } 
 
docsQos3ServiceClassUnsolicitGrantSize OBJECT-TYPE 
     SYNTAX      Unsigned32 (0..65535) 
     UNITS       "bytes" 
     MAX-ACCESS  read-create 
     STATUS      current 
     DESCRIPTION 
        "This attribute is the template for the UnsolicitGrantSize 
        attribute of the QoS Parameter Set." 
     DEFVAL { 0 } 
     ::= { docsQos3ServiceClassEntry 12 } 
 
docsQos3ServiceClassNomGrantInterval OBJECT-TYPE 
     SYNTAX      Unsigned32 
     UNITS       "microseconds" 
     MAX-ACCESS  read-create 
     STATUS      current 
     DESCRIPTION 
        "This attribute is the template for the NomGrantInterval 
        attribute of the QoS Parameter Set." 
     DEFVAL { 0 } 
     ::= { docsQos3ServiceClassEntry 13 } 
 
docsQos3ServiceClassTolGrantJitter OBJECT-TYPE 
     SYNTAX      Unsigned32 
     UNITS       "microseconds" 
     MAX-ACCESS  read-create 
     STATUS      current 
     DESCRIPTION 
        "This attribute is the template for the TolGrantJitter 
        attribute of the QoS Parameter Set." 
     DEFVAL { 0 } 
     ::= { docsQos3ServiceClassEntry 14 } 

docsQos3ServiceClassGrantsPerInterval OBJECT-TYPE 
     SYNTAX      Unsigned32 (0..127) 
     UNITS       "dataGrants" 
     MAX-ACCESS  read-create 
     STATUS      current 
     DESCRIPTION 
        "This attribute is the template for the GrantsPerInterval 
        attribute of the QoS Parameter Set." 
     DEFVAL { 0 } 
     ::= { docsQos3ServiceClassEntry 15 } 
 
docsQos3ServiceClassMaxLatency OBJECT-TYPE 
     SYNTAX      Unsigned32 
     UNITS       "microseconds" 
     MAX-ACCESS  read-create 
     STATUS      current 
     DESCRIPTION 
        "This attribute is the template for the MaxLatency 
        attribute of the QoS Parameter Set." 
     DEFVAL { 0 } 
     ::= { docsQos3ServiceClassEntry 16 } 
 
docsQos3ServiceClassActiveTimeout OBJECT-TYPE 
     SYNTAX      Unsigned32 (0..65535) 
     UNITS           "seconds" 
     MAX-ACCESS  read-create 
     STATUS      current 
     DESCRIPTION 
        "This attribute is the template for the ActiveTimeout 
        attribute of the QoS Parameter Set." 
     DEFVAL { 0 } 
     ::= { docsQos3ServiceClassEntry 17 } 
 
docsQos3ServiceClassAdmittedTimeout OBJECT-TYPE 
     SYNTAX      Unsigned32 (0..65535) 
     UNITS           "seconds" 
     MAX-ACCESS  read-create 
     STATUS      current 
     DESCRIPTION 
        "This attribute is the template for the AddmitedTimeout 
        attribute of the QoS Parameter Set." 
     DEFVAL { 200 } 
     ::= { docsQos3ServiceClassEntry 18 } 
 
docsQos3ServiceClassSchedulingType OBJECT-TYPE 
     SYNTAX      SchedulingType 
     MAX-ACCESS  read-create 
     STATUS      current 
     DESCRIPTION 
        "This attribute is the template for the SchedulingType 
        attribute of the QoS Parameter Set." 
     DEFVAL { bestEffort } 
     ::= { docsQos3ServiceClassEntry 19 } 
 
docsQos3ServiceClassRequestPolicy OBJECT-TYPE 
     SYNTAX      OCTET STRING (SIZE(4)) 
     MAX-ACCESS  read-create 
     STATUS      current 
     DESCRIPTION 
        "This attribute is the template for the ReqPolicyOct 
        attribute of the QoS Parameter Set." 
    DEFVAL       { '00000000'H }          
     ::= { docsQos3ServiceClassEntry 20 } 
 
docsQos3ServiceClassTosAndMask OBJECT-TYPE 
     SYNTAX      OCTET STRING (SIZE(1)) 
     MAX-ACCESS  read-create 
     STATUS      current 
     DESCRIPTION 
        "This attribute is the template for the TosAndMask 
        attribute of the QoS Parameter Set." 
     ::= { docsQos3ServiceClassEntry 21 } 
 
docsQos3ServiceClassTosOrMask OBJECT-TYPE 
     SYNTAX      OCTET STRING (SIZE(1)) 
     MAX-ACCESS  read-create 
     STATUS      current 
     DESCRIPTION 
        "This attribute is the template for the TosOrMask attribute 
        of the QoS Parameter Set." 
     ::= { docsQos3ServiceClassEntry 22 } 
 
docsQos3ServiceClassDirection OBJECT-TYPE 
     SYNTAX      IfDirection 
     MAX-ACCESS  read-create 
     STATUS      current 
     DESCRIPTION 
        "This attribute is the template for the Direction attribute 
        of the QoS Parameter Set." 
     DEFVAL { upstream } 
     ::= { docsQos3ServiceClassEntry 23 } 
 
docsQos3ServiceClassStorageType OBJECT-TYPE 
     SYNTAX      StorageType 
     MAX-ACCESS  read-create 
     STATUS      current 
     DESCRIPTION 
        "This attribute defines whether this row is kept in 
        volatile storage and lost upon reboot or whether 
        it is backed up by non-volatile or permanent storage. 
        'permanent' entries need not allow writable access to 
        any instance attribute." 
     DEFVAL { nonVolatile } 
     ::= { docsQos3ServiceClassEntry 24 } 
 
docsQos3ServiceClassDSCPOverwrite OBJECT-TYPE 
     SYNTAX      DscpOrAny 
     MAX-ACCESS  read-create 
     STATUS      current 
     DESCRIPTION 
        "This attribute allows the overwrite of the DSCP field 
        per RFC 3260. 
        If this attribute is -1, then the corresponding TosAndMask 
        value is set to be 'FF'H and TosOrMask is set to 
        '00'H.  Otherwise, this attribute is in the range of                     
0..63, 
        and the corresponding TosAndMask value is '03'H 
        and TosOrMaskvalue is this attribute value shifted 
        left by two bit positions." 
     DEFVAL { -1 } 
     ::= { docsQos3ServiceClassEntry 25 } 
 
docsQos3ServiceClassRequiredAttrMask OBJECT-TYPE 
     SYNTAX      AttributeMask 
     MAX-ACCESS  read-create 
     STATUS      current 
     DESCRIPTION 
        "This attribute is the template for the RequiredAttrMask 
        attribute of the QoS Parameter Set." 
     DEFVAL { { } }
     ::= { docsQos3ServiceClassEntry 26 } 
 
docsQos3ServiceClassForbiddenAttrMask OBJECT-TYPE 
     SYNTAX      AttributeMask 
     MAX-ACCESS  read-create 
     STATUS      current 
     DESCRIPTION 
        "This attribute is the template for the ForbiddenAttrMask 
        attribute of the QoS Parameter Set." 
     DEFVAL { { } }
     ::= { docsQos3ServiceClassEntry 27 } 
 
docsQos3ServiceClassAttrAggrRuleMask OBJECT-TYPE 
     SYNTAX      AttrAggrRuleMask 
     MAX-ACCESS  read-create 
     STATUS      current 
     DESCRIPTION 
        "This attribute is the template for the AttrAggregationMask 
        attribute of the QoS Parameter Set." 
     DEFVAL { resequencingDsid }
     ::= { docsQos3ServiceClassEntry 28 } 
 
docsQos3ServiceClassAppId OBJECT-TYPE 
     SYNTAX      Unsigned32 
     MAX-ACCESS  read-create 
     STATUS      current 
     DESCRIPTION 
        "This attribute is the template for the AppId attribute 
        of the QoS Parameter Set." 
     ::= { docsQos3ServiceClassEntry 29 } 
 
docsQos3ServiceClassMultiplierContentionReqWindow OBJECT-TYPE 
     SYNTAX      Unsigned32 (4..12) 
     UNITS       "eighths" 
     MAX-ACCESS  read-create 
     STATUS      current 
     DESCRIPTION 
        "This attribute is the template for the MultiplierContentionReqWindow 
        attribute of the QoS Parameter 
        Set." 
     DEFVAL { 8 } 
     ::= { docsQos3ServiceClassEntry 30 } 
 
docsQos3ServiceClassMultiplierBytesReq OBJECT-TYPE 
     SYNTAX      Unsigned32 (1 | 2 | 4 | 8 | 16) 
     MAX-ACCESS  read-create 
     STATUS      current 
     DESCRIPTION 
        "This attribute is the template for the MultiplierBytesReq 
        attribute of the QoS Parameter Set." 
     DEFVAL { 4 } 
     ::= { docsQos3ServiceClassEntry 31 } 
 
docsQos3ServiceClassMaxReqPerSidCluster OBJECT-TYPE 
     SYNTAX      Unsigned32 (0..255) 
     UNITS       "requests" 
     MAX-ACCESS  read-create 
     STATUS      current 
     DESCRIPTION 
        "This attribute is the template for the MaxReqPerSidCluster 
        attribute of the QoS Parameter Set." 
     DEFVAL { 0 } 
     ::= { docsQos3ServiceClassEntry 32 } 
 
docsQos3ServiceClassMaxOutstandingBytesPerSidCluster OBJECT-TYPE 
     SYNTAX      Unsigned32 
     UNITS       "bytes" 
     MAX-ACCESS  read-create 
     STATUS      current 
     DESCRIPTION 
        "This attribute is the template for the MaxOutstandingBytesPerSidCluster 
        attribute of the QoS Parameter 
        Set." 
     DEFVAL { 0 } 
     ::= { docsQos3ServiceClassEntry 33 } 
 
docsQos3ServiceClassMaxTotBytesReqPerSidCluster OBJECT-TYPE 
     SYNTAX      Unsigned32 
     UNITS       "bytes" 
     MAX-ACCESS  read-create 
     STATUS      current 
     DESCRIPTION 
        "This attribute is the template for the MaxTotBytesReqPerSidCluster 
        attribute of the QoS Parameter Set." 
         
     DEFVAL { 0 } 
     ::= { docsQos3ServiceClassEntry 34 } 
 
docsQos3ServiceClassMaxTimeInSidCluster OBJECT-TYPE 
     SYNTAX      Unsigned32 (0..65535) 
     UNITS       "milliseconds" 
     MAX-ACCESS  read-create 
     STATUS      current 
     DESCRIPTION 
        "This attribute is the template for the MaxTimeInSidCluster 
        attribute of the QoS Parameter Set." 
     DEFVAL { 0 } 
     ::= { docsQos3ServiceClassEntry 35 } 
 
docsQos3ServiceClassPeakTrafficRate OBJECT-TYPE 
     SYNTAX      Unsigned32 
     UNITS       "bps" 
     MAX-ACCESS  read-create 
     STATUS      current 
     DESCRIPTION 
        "This attribute is the template for the PeakTrafficRate 
        attribute of the QoS Parameter Set." 
     DEFVAL { 0 } 
     ::= { docsQos3ServiceClassEntry 36 } 
 
docsQos3ServiceClassDsResequencing OBJECT-TYPE 
     SYNTAX      INTEGER {  
                          resequencingDsid(0), 
                          noResequencingDsid(1) 
                         } 
     MAX-ACCESS  read-create 
     STATUS      current 
     DESCRIPTION 
        "This attribute is the template for the DsResequencing 
        attribute of the QoS Parameter Set." 
     DEFVAL { 0 } 
     ::= { docsQos3ServiceClassEntry 37 } 
      
      
docsQos3PHSTable OBJECT-TYPE 
     SYNTAX      SEQUENCE OF DocsQos3PHSEntry 
     MAX-ACCESS  not-accessible 
     STATUS      current 
     DESCRIPTION 
        "This object describes the set of payload header suppression 
        of Service Flows." 
     REFERENCE 
        "DOCSIS 3.0 MAC and Upper Layer Protocols Interface 
        Specification CM-SP-MULPIv3.0-I05-070803, Payload Header 
        Suppression section in the Common Radio Frequency Interface 
        Encodings Annex." 
     ::= { docsQos3MibObjects 10} 

docsQos3PHSEntry OBJECT-TYPE 
     SYNTAX      DocsQos3PHSEntry 
     MAX-ACCESS  not-accessible 
     STATUS      current 
     DESCRIPTION 
        "The conceptual row of docsQos3PHSTable. 
        The ifIndex key corresponds to the MAC Domain interface 
        of the service flow of the classifier that includes this 
        PHS rule." 
     INDEX { ifIndex,docsQos3ServiceFlowId,docsQos3PktClassId } 
     ::= { docsQos3PHSTable 1 } 
 
DocsQos3PHSEntry ::= SEQUENCE { 
     docsQos3PHSField 
                  OCTET STRING, 
     docsQos3PHSMask 
                  OCTET STRING, 
     docsQos3PHSSize 
                  Unsigned32, 
     docsQos3PHSVerify 
                  TruthValue, 
     docsQos3PHSIndex 
                  Unsigned32 
     } 
 
docsQos3PHSField OBJECT-TYPE 
     SYNTAX      OCTET STRING (SIZE (0..255)) 
     MAX-ACCESS  read-only 
     STATUS      current 
     DESCRIPTION 
        "This attribute indicates the Payload Header suppression 
        field defines the bytes of the header that must 
        be suppressed/restored by the sending/receiving 
        device. 
        The number of octets in this attribute should be the same 
        as the value of PHSSize." 
     REFERENCE 
        "DOCSIS 3.0 MAC and Upper Layer Protocols Interface 
        Specification CM-SP-MULPIv3.0-I05-070803, Payload Header 
        Suppression Field (PHSF) section in the Common Radio  
        Frequency Interface Encodings Annex." 
     ::= { docsQos3PHSEntry 2 } 
 
docsQos3PHSMask OBJECT-TYPE 
     SYNTAX      OCTET STRING (SIZE (0..32)) 
     MAX-ACCESS  read-only 
     STATUS      current 
     DESCRIPTION 
        "This attribute defines the bit mask that is used in 
        combination with the PHSField.  It defines which bytes 
        in the header must be suppressed/restored by the sending 
        or receiving device. 
         
        Each bit of this bit mask corresponds to a byte in the PHSField, 
        with the least 
        significant bit corresponding to the first byte of the 
        PHSField. 
         
        Each bit of the bit mask specifies whether the corresponding 
        byte should be suppressed in the packet.  A bit 
        value of '1' indicates that the byte should be suppressed 
        by the sending device and restored by the receiving 
        device. 
        A bit value of '0' indicates that the byte should not be 
        suppressed by the sending device or restored by the 
        receiving device. 
        If the bit mask does not contain a bit for each byte in the 
        PHSField, then the bit mask is extended with bit values 
        of '1' to be the necessary length." 
     REFERENCE 
        "DOCSIS 3.0 MAC and Upper Layer Protocols Interface 
        Specification CM-SP-MULPIv3.0-I05-070803, Payload Header  
        Suppression Mask (PHSM) section in the Common Radio Frequency 
        Interface Encodings Annex." 
     ::= { docsQos3PHSEntry 3 } 
 
docsQos3PHSSize OBJECT-TYPE 
     SYNTAX      Unsigned32 (0..255) 
     UNITS       "bytes" 
     MAX-ACCESS  read-only 
     STATUS      current 
     DESCRIPTION 
        "This attribute specifies the number of bytes in the 
        header to be suppressed  and restored. 
        The value of this attribute matches the numberof bytes 
        in the Field attribute." 
     REFERENCE 
        "DOCSIS 3.0 MAC and Upper Layer Protocols Interface 
        Specification CM-SP-MULPIv3.0-I05-070803, Payload Header Suppression 
        Size (PHSS) section in the Common Radio Frequency Interface  
        Encodings Annex." 
     ::= { docsQos3PHSEntry 4 } 
 
docsQos3PHSVerify OBJECT-TYPE 
     SYNTAX      TruthValue 
     MAX-ACCESS  read-only 
     STATUS      current 
     DESCRIPTION 
        "If 'true', this attribute indicates that the sender 
        must verify that the PHS Field 
        is the same as the content in the packet to be suppressed." 
     REFERENCE 
        "DOCSIS 3.0 MAC and Upper Layer Protocols Interface 
        Specification CM-SP-MULPIv3.0-I05-070803, Payload Header 
        Suppression Verification (PHSV) section in the Common Radio 
        Frequency Interface Encodings Annex." 
     ::= { docsQos3PHSEntry 5 } 
 
docsQos3PHSIndex OBJECT-TYPE 
     SYNTAX      Unsigned32 (1..255) 
     MAX-ACCESS  read-only 
     STATUS      current 
     DESCRIPTION 
        "This attribute uniquely references the PHS rule for 
        a given service flow." 
     REFERENCE 
        "DOCSIS 3.0 MAC and Upper Layer Protocols Interface 
        Specification CM-SP-MULPIv3.0-I05-070803, Payload Header  
        Suppression Index (PHSI) section in the Common Radio  
        Frequency Interface Encodings Annex." 
     ::= { docsQos3PHSEntry 7 } 
 
docsQos3CmtsMacToSrvFlowTable OBJECT-TYPE 
     SYNTAX      SEQUENCE OF DocsQos3CmtsMacToSrvFlowEntry 
     MAX-ACCESS  not-accessible 
     STATUS      current 
     DESCRIPTION 
        "This object provides the mapping of unicast service 
        flows with the cable modem the service flows belongs 
        to." 
     ::= { docsQos3MibObjects 11} 
 
docsQos3CmtsMacToSrvFlowEntry OBJECT-TYPE 
     SYNTAX      DocsQos3CmtsMacToSrvFlowEntry 
     MAX-ACCESS  not-accessible 
     STATUS      current 
     DESCRIPTION 
        "The conceptual row of docsQos3CmtsMacToSrvFlowTable." 
     INDEX { docsQos3CmtsCmMac,docsQos3CmtsServiceFlowId } 
     ::= { docsQos3CmtsMacToSrvFlowTable 1 } 
 
DocsQos3CmtsMacToSrvFlowEntry ::= SEQUENCE { 
     docsQos3CmtsCmMac 
                  MacAddress, 
     docsQos3CmtsServiceFlowId 
                  Unsigned32, 
     docsQos3CmtsIfIndex 
                  InterfaceIndex 
     } 
 
docsQos3CmtsCmMac OBJECT-TYPE 
     SYNTAX      MacAddress 
     MAX-ACCESS  not-accessible 
     STATUS      current 
     DESCRIPTION 
        "This key represents the MAC address for the referenced 
        CM." 
     ::= { docsQos3CmtsMacToSrvFlowEntry 1 } 
 
docsQos3CmtsServiceFlowId OBJECT-TYPE 
     SYNTAX      Unsigned32 (1..4294967295) 
     MAX-ACCESS  not-accessible 
     STATUS      current 
     DESCRIPTION 
        "This key represents the identifier of the Service 
        Flow." 
     ::= { docsQos3CmtsMacToSrvFlowEntry 2 } 
 
docsQos3CmtsIfIndex OBJECT-TYPE 
     SYNTAX      InterfaceIndex 
     MAX-ACCESS  read-only 
     STATUS      current 
     DESCRIPTION 
        "This attribute represents the interface index of 
        the MAC domain of the Service Flow and where the CableModem 
        is registered." 
     ::= { docsQos3CmtsMacToSrvFlowEntry 3 } 
 
docsQos3ServiceFlowSidClusterTable OBJECT-TYPE 
     SYNTAX      SEQUENCE OF DocsQos3ServiceFlowSidClusterEntry 
     MAX-ACCESS  not-accessible 
     STATUS      current 
     DESCRIPTION 
        "This object defines the SID clusters associated with 
        an upstream service flow." 
     REFERENCE 
        "DOCSIS 3.0 MAC and Upper Layer Protocols Interface 
        Specification CM-SP-MULPIv3.0-I05-070803,  Service Flow SID 
        Cluster Assignments section in the Common Radio Frequency 
        Interface Encodings Annex." 
     ::= { docsQos3MibObjects 12} 
 
docsQos3ServiceFlowSidClusterEntry OBJECT-TYPE 
     SYNTAX      DocsQos3ServiceFlowSidClusterEntry 
     MAX-ACCESS  not-accessible 
     STATUS      current 
     DESCRIPTION 
        "The conceptual row of docsQos3ServiceFlowSidClusterTable. 
        The ifIndex key corresponds to the MAC Domain interface 
        of the service flow." 
     INDEX { 
ifIndex,docsQos3ServiceFlowId,docsQos3ServiceFlowSidClusterId,docsQos3ServiceFlowSidClusterUcid }
     ::= { docsQos3ServiceFlowSidClusterTable 1 } 
 
DocsQos3ServiceFlowSidClusterEntry ::= SEQUENCE { 
     docsQos3ServiceFlowSidClusterId 
                  Unsigned32, 
     docsQos3ServiceFlowSidClusterUcid 
                  ChId, 
     docsQos3ServiceFlowSidClusterSid 
                  Unsigned32 
     } 
 
docsQos3ServiceFlowSidClusterId OBJECT-TYPE 
     SYNTAX      Unsigned32 (0..7) 
     MAX-ACCESS  not-accessible 
     STATUS      current 
     DESCRIPTION 
        "This key represents the SID Cluster ID of the SID Cluster." 
     REFERENCE 
        "DOCSIS 3.0 MAC and Upper Layer Protocols Interface 
        Specification CM-SP-MULPIv3.0-I05-070803, SID Cluster ID 
        section in the Common Radio Frequency Interface Encodings 
        Annex." 
     ::= { docsQos3ServiceFlowSidClusterEntry 1 } 
 
docsQos3ServiceFlowSidClusterUcid OBJECT-TYPE 
     SYNTAX      ChId (1..255) 
     MAX-ACCESS  not-accessible 
     STATUS      current 
     DESCRIPTION 
        "This key represents the upstream Channel ID mapped 
        to the corresponding SID." 
     ::= { docsQos3ServiceFlowSidClusterEntry 2 } 
 
docsQos3ServiceFlowSidClusterSid OBJECT-TYPE 
     SYNTAX      Unsigned32 (1..16383) 
     MAX-ACCESS  read-only 
     STATUS      current 
     DESCRIPTION 
        "This attribute represents the SID assigned to the 
        upstream channel in this SID Cluster." 
     ::= { docsQos3ServiceFlowSidClusterEntry 3 } 
 
docsQos3GrpServiceFlowTable OBJECT-TYPE 
     SYNTAX      SEQUENCE OF DocsQos3GrpServiceFlowEntry 
     MAX-ACCESS  not-accessible 
     STATUS      current 
     DESCRIPTION 
        "This object provides extensions to the service flow 
        information for Group Service Flows (GSFs)." 
     REFERENCE 
        "DOCSIS 3.0 MAC and Upper Layer Protocols Interface 
        Specification CM-SP-MULPIv3.0-I05-070803, QoS Support 
        for Joined IP Multicast Traffic section." 
     ::= { docsQos3MibObjects 13} 
 
docsQos3GrpServiceFlowEntry OBJECT-TYPE 
     SYNTAX      DocsQos3GrpServiceFlowEntry 
     MAX-ACCESS  not-accessible 
     STATUS      current 
     DESCRIPTION 
        "The conceptual row of docsQos3GrpServiceFlowTable. 
        The ifIndex key corresponds to the MAC Domain interface 
        of the group service flow." 
     INDEX { ifIndex,docsQos3ServiceFlowId } 
     ::= { docsQos3GrpServiceFlowTable 1 } 
 
DocsQos3GrpServiceFlowEntry ::= SEQUENCE { 
     docsQos3GrpServiceFlowIsDef 
                  TruthValue, 
     docsQos3GrpServiceFlowQosConfigId 
                  Unsigned32, 
     docsQos3GrpServiceFlowNumSess 
                  Unsigned32 
     } 
 
docsQos3GrpServiceFlowIsDef OBJECT-TYPE 
     SYNTAX      TruthValue 
     MAX-ACCESS  read-only 
     STATUS      current 
     DESCRIPTION 
        "This attribute indicates whether the GSF QOS Parameter 
        Set corresponds to the Default Group Service Flow." 
     REFERENCE 
        "DOCSIS 3.0 Operations Support System Interface Specification 
        CM-SP-OSSIv3.0-I04-070803, Multicast Requirements Annex." 
     ::= { docsQos3GrpServiceFlowEntry 1 } 
 
docsQos3GrpServiceFlowQosConfigId OBJECT-TYPE 
     SYNTAX      Unsigned32 (0..65535) 
     MAX-ACCESS  read-only 
     STATUS      current 
     DESCRIPTION 
        "This attribute indicates the Group QoS Configuration 
        (GQC) identifier used of the creation of this GSF. 
        The value zero indicates that the Service Flow is using 
        the default service flow." 
     REFERENCE 
        "DOCSIS 3.0 Operations Support System Interface Specification 
        CM-SP-OSSIv3.0-I04-070803, Multicast Requirements Annex." 
     ::= { docsQos3GrpServiceFlowEntry 2 } 
 
docsQos3GrpServiceFlowNumSess OBJECT-TYPE 
     SYNTAX      Unsigned32 (1..65535) 
     UNITS       "sessions" 
     MAX-ACCESS  read-only 
     STATUS      current 
     DESCRIPTION 
        "This attribute indicates the number of sessions that 
        are configured in an aggregated Service Flow.  If 
        this is a single session replication, the value of this 
        attribute is 1." 
     REFERENCE 
        "DOCSIS 3.0 Operations Support System Interface Specification 
        CM-SP-OSSIv3.0-I04-070803, Multicast Requirements Annex." 
     ::= { docsQos3GrpServiceFlowEntry 3 } 
 
docsQos3GrpPktClassTable OBJECT-TYPE 
     SYNTAX      SEQUENCE OF DocsQos3GrpPktClassEntry 
     MAX-ACCESS  not-accessible 
     STATUS      current 
     DESCRIPTION 
        "This object provides additional packet classification 
        information for Group Classifier References 
        (GCRs) in a Group Service Flow (GSF)." 
     REFERENCE 
        "DOCSIS 3.0 MAC and Upper Layer Protocols Interface 
        Specification CM-SP-MULPIv3.0-I05-070803, QoS Support for  
        Joined IP Multicast Traffic section." 
     ::= { docsQos3MibObjects 14} 
 
docsQos3GrpPktClassEntry OBJECT-TYPE 
     SYNTAX      DocsQos3GrpPktClassEntry 
     MAX-ACCESS  not-accessible 
     STATUS      current 
     DESCRIPTION 
        "The conceptual row of docsQos3GrpPktClassTable. 
        The ifIndex key corresponds to the MAC Domain interface of the  
        service flow of this group classifier." 
     INDEX { ifIndex,docsQos3ServiceFlowId,docsQos3PktClassId } 
     ::= { docsQos3GrpPktClassTable 1 } 
 
DocsQos3GrpPktClassEntry ::= SEQUENCE { 
     docsQos3GrpPktClassGrpConfigId 
                  Unsigned32 
     } 
 
docsQos3GrpPktClassGrpConfigId OBJECT-TYPE 
     SYNTAX      Unsigned32 (1..4294967295) 
     MAX-ACCESS  read-only 
     STATUS      current 
     DESCRIPTION 
        "This attribute indicates the GC identifier used of 
        the creation of this GSF." 
     REFERENCE 
        "DOCSIS 3.0 Operations Support System Interface Specification 
        CM-SP-OSSIv3.0-I04-070803, Multicast Requirements Annex." 
     ::= { docsQos3GrpPktClassEntry 1 } 
 
docsQos3UpChCounterExtTable OBJECT-TYPE 
     SYNTAX      SEQUENCE OF DocsQos3UpChCounterExtEntry 
     MAX-ACCESS  not-accessible 
     STATUS      current 
     DESCRIPTION 
        "This object provides extensions for service flow 
        statistics for fragmentation for channel bonding." 
     REFERENCE 
        "DOCSIS 3.0 MAC and Upper Layer Protocols Interface 
        Specification CM-SP-MULPIv3.0-I05-070803, Channel  
        Bonding section." 
     ::= { docsQos3MibObjects 15} 
 
docsQos3UpChCounterExtEntry OBJECT-TYPE 
     SYNTAX      DocsQos3UpChCounterExtEntry 
     MAX-ACCESS  not-accessible 
     STATUS      current 
     DESCRIPTION 
        "The conceptual row of docsQos3UpChCounterExtTable. 
        The ifIndex key corresponds to the upstream Channel Interface 
        of the service flow." 
     INDEX { ifIndex } 
     ::= { docsQos3UpChCounterExtTable 1 } 
 
DocsQos3UpChCounterExtEntry ::= SEQUENCE { 
     docsQos3UpChCounterExtSgmtValids 
                  Counter32, 
     docsQos3UpChCounterExtSgmtDiscards 
                  Counter32 
     } 
 
docsQos3UpChCounterExtSgmtValids OBJECT-TYPE 
     SYNTAX      Counter32 
     UNITS       "segments" 
     MAX-ACCESS  read-only 
     STATUS      current 
     DESCRIPTION 
        "This attribute represents the total number segments 
        processed on this channel. Discontinuities in the 
        value of this counter can occur at reinitialization 
     of the managed system, and at other times as indicated 
        by the value of ifCounterDiscontinuityTime of the 
        associated MAC Domain interface index." 
     REFERENCE 
        "DOCSIS 3.0 MAC and Upper Layer Protocols Interface 
        Specification CM-SP-MULPIv3.0-I05-070803, Upstream and 
        Downstream Common Aspects section; [RFC 2863]." 
     ::= { docsQos3UpChCounterExtEntry 1 } 
 
docsQos3UpChCounterExtSgmtDiscards OBJECT-TYPE 
     SYNTAX      Counter32 
     UNITS       "segments" 
     MAX-ACCESS  read-only 
     STATUS      current 
     DESCRIPTION 
        "This attribute represents the total number of discarded 
        segments on this channel due to segment HCS problems. 
        Discontinuities in the value of this counter 
        can occur at reinitialization of the managed system, 
        and at other times as indicated by the value of  
        ifCounterDiscontinuityTime of the associated MAC Domain 
        interface index." 
     REFERENCE 
        "DOCSIS 3.0 MAC and Upper Layer Protocols Interface 
        Specification CM-SP-MULPIv3.0-I05-070803, Continuous  
        Concatenation and Fragmentation section;[RFC 2863]." 
     ::= { docsQos3UpChCounterExtEntry 2 } 
 
docsQos3ServiceFlowCcfStatsTable OBJECT-TYPE 
     SYNTAX      SEQUENCE OF DocsQos3ServiceFlowCcfStatsEntry 
     MAX-ACCESS  not-accessible 
     STATUS      current 
     DESCRIPTION 
        "This object provides upstream service flow statistics 
        for Continous Concatenation and Fragmentation 
        (CCF). 
        The CMTS MAY not instantate this object for service flows 
        that do not use CCF or return the zero value on individual 
        counter's statistics." 
     REFERENCE 
        "DOCSIS 3.0 MAC and Upper Layer Protocols Interface 
        Specification CM-SP-MULPIv3.0-I05-070803, Continuous  
        Concatenation and Fragmentation section." 
     ::= { docsQos3MibObjects 16} 
 
docsQos3ServiceFlowCcfStatsEntry OBJECT-TYPE 
     SYNTAX      DocsQos3ServiceFlowCcfStatsEntry 
     MAX-ACCESS  not-accessible 
     STATUS      current 
     DESCRIPTION 
        "The conceptual row of docsQos3ServiceFlowCcfStatsTable. 
        The ifIndex key corresponds to the MAC Domain interface  
        of the service flow." 
     INDEX { ifIndex,docsQos3ServiceFlowId } 
     ::= { docsQos3ServiceFlowCcfStatsTable 1 } 
 
DocsQos3ServiceFlowCcfStatsEntry ::= SEQUENCE { 
     docsQos3ServiceFlowCcfStatsSgmtValids 
                  Counter32, 
     docsQos3ServiceFlowCcfStatsSgmtLost 
                  Counter32 
     } 
 
docsQos3ServiceFlowCcfStatsSgmtValids OBJECT-TYPE 
     SYNTAX      Counter32 
     UNITS       "segments" 
     MAX-ACCESS  read-only 
     STATUS      current 
     DESCRIPTION 
        "This attribute contains the number of segments counted 
        on this service flow regardless of whether the 
        fragment was correctly reassembled into valid packets. 
        Discontinuities in the value of this counter can 
        occur at reinitialization of the managed system, and 
        at other times as indicated by the value of  
        ifCounterDiscontinuityTime of the associated MAC Domain 
        interface index." 
     REFERENCE 
        "DOCSIS 3.0 MAC and Upper Layer Protocols Interface 
        Specification CM-SP-MULPIv3.0-I05-070803, Continuous  
        Concatenation and Fragmentation section; [RFC 2863]."  
     ::= { docsQos3ServiceFlowCcfStatsEntry 1 } 
 
docsQos3ServiceFlowCcfStatsSgmtLost OBJECT-TYPE 
     SYNTAX      Counter32 
     UNITS       "segments" 
     MAX-ACCESS  read-only 
     STATUS      current 
     DESCRIPTION 
        "This attribute counts the number of segments which 
        the CMTS segment reassembly function determines were 
        lost. Discontinuities in the value of this counter 
        can occur at reinitialization of the managed system, 
        and at other times as indicated by the value of  
        ifCounterDiscontinuityTime of the associated MAC Domain 
        interface index." 
     REFERENCE 
        "DOCSIS 3.0 MAC and Upper Layer Protocols Interface 
        Specification CM-SP-MULPIv3.0-I05-070803, Continuous 
        Concatenation and Fragmentation section; [RFC 2863]." 
     ::= { docsQos3ServiceFlowCcfStatsEntry 2 } 
 
docsQos3CmServiceUsStatsTable OBJECT-TYPE 
     SYNTAX      SEQUENCE OF DocsQos3CmServiceUsStatsEntry 
     MAX-ACCESS  not-accessible 
     STATUS      current 
     DESCRIPTION 
        "This object defines DOCSIS MAC services primitive 
        statistics of upstream service flows. In pre-3.0 DOCSIS 
        devices this statistics exists per SID for either 
        Cos or Qos services in the SNMP table docsIfCmServiceTable. 
         
        A 3.0 CM with CoS configuration (DOCSIS 1.0 mode) reports 
        the statistics defined in the SNMP table docsIfCmServiceTable. 
        A 3.0 CM with QoS configuration reports 
        this object regardless of whether Multiple Transmit 
        Channel is enabled or disabled." 
     REFERENCE 
        "DOCSIS 3.0 MAC and Upper Layer Protocols Interface 
        Specification CM-SP-MULPIv3.0-I05-070803, Upstream Data  
        Transmission section." 
     ::= { docsQos3MibObjects 17} 
 
docsQos3CmServiceUsStatsEntry OBJECT-TYPE 
     SYNTAX      DocsQos3CmServiceUsStatsEntry 
     MAX-ACCESS  not-accessible 
     STATUS      current 
     DESCRIPTION 
        "The conceptual row of docsQos3CmServiceUsStatsTable. 
        The ifIndex key corresponds to the MAC Domain interface 
        of the service flow." 
     INDEX { ifIndex,docsQos3ServiceFlowId } 
     ::= { docsQos3CmServiceUsStatsTable 1 } 

DocsQos3CmServiceUsStatsEntry ::= SEQUENCE { 
     docsQos3CmServiceUsStatsTxSlotsImmed 
                  Counter32, 
     docsQos3CmServiceUsStatsTxSlotsDed 
                  Counter32, 
     docsQos3CmServiceUsStatsTxRetries 
                  Counter32, 
     docsQos3CmServiceUsStatsTxExceededs 
                  Counter32, 
     docsQos3CmServiceUsStatsRqRetries 
                  Counter32, 
     docsQos3CmServiceUsStatsRqExceededs 
                  Counter32, 
     docsQos3CmServiceUsStatsSgmts 
                  Counter32 
     } 
 
docsQos3CmServiceUsStatsTxSlotsImmed OBJECT-TYPE 
     SYNTAX      Counter32 
     UNITS       "mini-slots" 
     MAX-ACCESS  read-only 
     STATUS      current 
     DESCRIPTION 
        "This attribute contains the number of upstream mini-slots 
        which have been used to transmit data PDUs in 
        immediate (contention) mode. This includes only those 
        PDUs that are presumed to have arrived at the head-end 
        (i.e., those which were explicitly acknowledged.) 
        It does not include retransmission attempts or 
        mini-slots used by Requests.  Discontinuities in the 
        value of this counter can occur at reinitialization 
        of the managed system, and at other times as indicated 
        by the value of ifCounterDiscontinuityTime of the 
        associated MAC Domain interface index." 
     REFERENCE 
        "DOCSIS 3.0 MAC and Upper Layer Protocols Interface 
        Specification CM-SP-MULPIv3.0-I05-070803, Upstream  
        Bandwidth Allocation section; [RFC 2863]." 
     ::= { docsQos3CmServiceUsStatsEntry 1 } 
 
docsQos3CmServiceUsStatsTxSlotsDed OBJECT-TYPE 
     SYNTAX      Counter32 
     UNITS       "mini-slots" 
     MAX-ACCESS  read-only 
     STATUS      current 
     DESCRIPTION 
        "This attribute contains the number of upstream mini-slots 
        which have been used to transmit data PDUs in 
        dedicated mode (i.e., as a result of a unicast Data Grant). 
        Discontinuities in the value of this counter 
        can occur at reinitialization of the managed system, 
        and at other times as indicated by the value of  
        ifCounterDiscontinuityTime of the associated MAC Domain 
        interface index." 
     REFERENCE 
        "DOCSIS 3.0 MAC and Upper Layer Protocols Interface 
        Specification CM-SP-MULPIv3.0-I05-070803, Upstream Data 
        Transmission section; [RFC 2863]."  
     ::= { docsQos3CmServiceUsStatsEntry 2 } 
 
docsQos3CmServiceUsStatsTxRetries OBJECT-TYPE 
     SYNTAX      Counter32 
     UNITS       "attempts" 
     MAX-ACCESS  read-only 
     STATUS      current 
     DESCRIPTION 
        "This attribute contains the number of attempts to 
        transmit data PDUs containing requests for acknowledgment 
        that did not result in acknowledgment. Discontinuities 
        in the value of this counter can occur at 
        reinitialization of the managed system, and at other 
        times as indicated by the value of ifCounterDiscontinuityTime 
        for the associated MAC Domain interface 
        index." 
     REFERENCE 
        "DOCSIS 3.0 MAC and Upper Layer Protocols Interface 
        Specification CM-SP-MULPIv3.0-I05-070803, Upstream Bandwidth 
        Allocation section; [RFC 2863]." 
     ::= { docsQos3CmServiceUsStatsEntry 3 } 
 
docsQos3CmServiceUsStatsTxExceededs OBJECT-TYPE 
     SYNTAX      Counter32 
     UNITS       "attempts" 
     MAX-ACCESS  read-only 
     STATUS      current 
     DESCRIPTION 
        "This attribute contains the number of attempts to 
        transmit bandwidth requests which did not result in 
        acknowledgment. Discontinuities in the value of this 
        counter can occur at reinitialization of the managed 
        system, and at other times as indicated by the value 
        of ifCounterDiscontinuityTime of the associated 
        MAC Domain interface index." 
     REFERENCE 
        "DOCSIS 3.0 MAC and Upper Layer Protocols Interface 
        Specification CM-SP-MULPIv3.0-I05-070803, Upstream Bandwidth 
        Allocation section; [RFC 2863]." 
     ::= { docsQos3CmServiceUsStatsEntry 4 } 
 
docsQos3CmServiceUsStatsRqRetries OBJECT-TYPE 
     SYNTAX      Counter32 
     UNITS       "attempts" 
     MAX-ACCESS  read-only 
     STATUS      current 
     DESCRIPTION 
        "This attribute contains the number of attempts to 
        transmit bandwidth requests which did not result in 
        acknowledgment. Discontinuities in the value of this 
        counter can occur at reinitialization of the managed 
        system, and at other times as indicated by the value 
        of ifCounterDiscontinuityTime of the associated 
        MAC Domain interface index." 
     REFERENCE 
        "DOCSIS 3.0 MAC and Upper Layer Protocols Interface 
        Specification CM-SP-MULPIv3.0-I05-070803, Upstream  
        Bandwidth Allocation section; [RFC 2863]." 
     ::= { docsQos3CmServiceUsStatsEntry 5 } 
 
docsQos3CmServiceUsStatsRqExceededs OBJECT-TYPE 
     SYNTAX      Counter32 
     UNITS       "attempts" 
     MAX-ACCESS  read-only 
     STATUS      current 
     DESCRIPTION 
        "This attribute contains the number of requests for 
        bandwidth which failed due to excessive retries without 
        acknowledgment. Discontinuities in the value 
        of this counter can occur at reinitialization of the 
        managed system, and at other times as indicated by the 
        value of ifCounterDiscontinuityTime of the associated 
        MAC Domain interface index." 
     REFERENCE 
        "DOCSIS 3.0 MAC and Upper Layer Protocols Interface 
        Specification CM-SP-MULPIv3.0-I05-070803, Upstream Bandwidth 
        Allocation section; [RFC 2863]." 
     ::= { docsQos3CmServiceUsStatsEntry 6 } 
 
docsQos3CmServiceUsStatsSgmts OBJECT-TYPE 
     SYNTAX      Counter32 
     UNITS       "segments" 
     MAX-ACCESS  read-only 
     STATUS      current 
     DESCRIPTION 
        "This attribute contains the number of segments sent 
        on this service flow. Discontinuities in the value 
        of this counter can occur at reinitialization of the 
        managed system, and at other times as indicated by the 
        value of ifCounterDiscontinuityTime of the associated 
        MAC Domain interface index." 
     REFERENCE 
        "DOCSIS 3.0 MAC and Upper Layer Protocols Interface 
        Specification CM-SP-MULPIv3.0-I05-070803, Upstream and 
        Downstream Common Aspects section; RFC 2863." 
     ::= { docsQos3CmServiceUsStatsEntry 7 } 
 
docsQos3CmtsDsidTable OBJECT-TYPE 
     SYNTAX      SEQUENCE OF DocsQos3CmtsDsidEntry 
     MAX-ACCESS  not-accessible 
     STATUS      current 
     DESCRIPTION 
        "This object describes DSID information stored in 
        the CMTS. 
        The CMTS reports the current status of existing DSIDs. 
        When a DSID is created during the registration process 
        or a DBC transaction, a corresponding object instance 
        is created.   If a DSID is deleted or changed via 
        a DBC message the corresponding object instance is deleted 
        or updated respectively." 
     ::= { docsQos3MibObjects 18} 
 
docsQos3CmtsDsidEntry OBJECT-TYPE 
     SYNTAX      DocsQos3CmtsDsidEntry 
     MAX-ACCESS  not-accessible 
     STATUS      current 
     DESCRIPTION 
        "The conceptual row of docsQos3CmtsDsidTable. 
        The ifIndex key corresponds to the MAC Domain interface 
        of the DSID." 
     INDEX { ifIndex,docsQos3CmtsDsidDsid } 
     ::= { docsQos3CmtsDsidTable 1 } 
 
DocsQos3CmtsDsidEntry ::= SEQUENCE { 
     docsQos3CmtsDsidDsid 
                  Dsid, 
     docsQos3CmtsDsidUsage 
                  BITS, 
     docsQos3CmtsDsidDsChSet 
                  ChSetId, 
     docsQos3CmtsDsidReseqWaitTime 
                  Unsigned32, 
     docsQos3CmtsDsidReseqWarnThrshld 
                  Unsigned32, 
     docsQos3CmtsDsidStatusHldoffTimerSeqOutOfRng 
                  Unsigned32, 
     docsQos3CmtsDsidCurrentSeqNum 
                  Unsigned32 
     } 
 
docsQos3CmtsDsidDsid OBJECT-TYPE 
     SYNTAX      Dsid 
     MAX-ACCESS  not-accessible 
     STATUS      current 
     DESCRIPTION 
        "This key represents the DSID." 
     ::= { docsQos3CmtsDsidEntry 1 } 
 
docsQos3CmtsDsidUsage OBJECT-TYPE 
     SYNTAX      BITS { 
 
                        resequencing(0), 
                        multicastCapable(1), 
                        multicastReplication(2), 
                        bonding(3) 
                      } 
     MAX-ACCESS  read-only 
     STATUS      current 
     DESCRIPTION 
        "This attribute indicates the properties of the DSID. 
        The bits are defined as follows: 
        'resequencing' This bit is set to 1 for a Resequencing 
        DSID. 
        'multicastCapable'  This bit is set to 1 for a DSID that 
        is capable of transporting multicast traffic (i.e., 
        the DSID has multicast forwarding attributes).   
        'multicastReplication' This bit is set to 1 for a DSID 
        that is used for transporting a multicast replication 
        (i.e. there is a corresponding instance of the MulticastRepl 
        object). 
        'bonding' This bit is set to a 1 for a DSID that is associated 
        with a bonding group." 
     REFERENCE 
        "DOCSIS 3.0 Operations Support System Interface Specification 
        CM-SP-OSSIv3.0-I04-070803, Multicast Requirements Annex. 
        DOCSIS 3.0 MAC and Upper Layer Protocols Interface 
        Specification CM-SP-MULPIv3.0-I05-070803, DSID Encodings section 
        in the Common Radio Frequency Interface Encodings Annex." 
     ::= { docsQos3CmtsDsidEntry 2 } 
 
docsQos3CmtsDsidDsChSet OBJECT-TYPE 
     SYNTAX      ChSetId 
     MAX-ACCESS  read-only 
     STATUS      current 
     DESCRIPTION 
        "This attribute represents the Downstream Channel 
        Set over which the DSID is being resequenced." 
     ::= { docsQos3CmtsDsidEntry 3 } 
 
docsQos3CmtsDsidReseqWaitTime OBJECT-TYPE 
     SYNTAX      Unsigned32 (1..180) 
     UNITS       "hundredMicroseconds" 
     MAX-ACCESS  read-only 
     STATUS      current 
     DESCRIPTION 
        "This attribute represents the DSID Resequencing 
        Wait Time that is used for this DSID. This attribute is 
        only valid when the Usage attribute has the resequencing 
        bit set to 1. This attribute returns a value of 0 
        when the Usage attribute has the resequencing bit set 
        to 0." 
     ::= { docsQos3CmtsDsidEntry 4 } 
 
docsQos3CmtsDsidReseqWarnThrshld OBJECT-TYPE 
     SYNTAX      Unsigned32 (0..179) 
     UNITS       "hundredMicroseconds" 
     MAX-ACCESS  read-only 
     STATUS      current 
     DESCRIPTION 
        "This attribute represents the DSID Resequencing 
        Warning Threshold that is used for this DSID. The value 
        of 0 indicates that the threshold warnings are disabled. 
        This attribute is only valid when the Usage attribute 
        has the resequencing bit set to 1. This attribute 
        returns a value of 0 when the Usage attribute has 
        the resequencing bit set to 0." 
     ::= { docsQos3CmtsDsidEntry 5 } 
 
docsQos3CmtsDsidStatusHldoffTimerSeqOutOfRng OBJECT-TYPE 
     SYNTAX      Unsigned32 (0..65535) 
     UNITS       "20milliseconds" 
     MAX-ACCESS  read-only 
     STATUS      current 
     DESCRIPTION 
        "This attribute represents the hold-off timer for 
        reporting Out-of-Range Events via the CM-STATUS MAC 
        Management message. This attribute is only valid when 
        the Usage attribute has the resequencing bit set 
        to 1. This attribute returns a value of 0 when the Usage 
        attribute has the resequencing bit set to 0." 
     ::= { docsQos3CmtsDsidEntry 6 } 
 
docsQos3CmtsDsidCurrentSeqNum OBJECT-TYPE 
     SYNTAX      Unsigned32 (0..65535) 
     MAX-ACCESS  read-only 
     STATUS      current 
     DESCRIPTION 
        "This attribute reports the value of the most recent 
        sequence number assigned by the CMTS for this DSID. 
        This attribute is only valid when the Usage attribute 
        has the resequencing bit set to 1. This attribute returns 
        a value of 0 when the Usage attribute has the resequencing 
        bit set to 0." 
     ::= { docsQos3CmtsDsidEntry 7 } 
 
docsQos3CmtsDebugDsidTable OBJECT-TYPE 
     SYNTAX      SEQUENCE OF DocsQos3CmtsDebugDsidEntry 
     MAX-ACCESS  not-accessible 
     STATUS      current 
     DESCRIPTION 
        "The CMTS Debug DSID object contains the control of 
        DSID debug statistics reporting  
        An instance in this object defines the DSID and MAC domain 
        to which the CmtsDebugDsidStats collects statistics 
        for the downstream channel associated with that 
        DSID and MAC Domain. The deletion of an instance stops 
        the reporting of statistics for the specified DSID. 
         
        This object supports instance creation and deletion. 
         
        The CMTS MUST support at least one instance of this object." 
     ::= { docsQos3MibObjects 19} 
 
docsQos3CmtsDebugDsidEntry OBJECT-TYPE 
     SYNTAX      DocsQos3CmtsDebugDsidEntry 
     MAX-ACCESS  not-accessible 
     STATUS      current 
     DESCRIPTION 
        "The conceptual row of docsQos3CmtsDebugDsidTable. 
        The ifIndex key corresponds to the MAC Domain interface 
        of the DSID." 
     INDEX { ifIndex,docsQos3CmtsDebugDsidDsid } 
     ::= { docsQos3CmtsDebugDsidTable 1 } 
 
DocsQos3CmtsDebugDsidEntry ::= SEQUENCE { 
     docsQos3CmtsDebugDsidDsid 
                  Dsid, 
     docsQos3CmtsDebugDsidRowStatus 
                  RowStatus 
     } 
 
docsQos3CmtsDebugDsidDsid OBJECT-TYPE 
     SYNTAX      Dsid 
     MAX-ACCESS  not-accessible 
     STATUS      current 
     DESCRIPTION 
        "This attribute represents the DSID value to be debugged, 
        identified by the IfIndex attribute of this object." 
     ::= { docsQos3CmtsDebugDsidEntry 1 } 
 
docsQos3CmtsDebugDsidRowStatus OBJECT-TYPE 
     SYNTAX      RowStatus 
     MAX-ACCESS  read-create 
     STATUS      current 
     DESCRIPTION 
        "The conceptual row status of this object." 
     ::= { docsQos3CmtsDebugDsidEntry 2 } 
 
docsQos3CmtsDebugDsidStatsTable OBJECT-TYPE 
     SYNTAX      SEQUENCE OF DocsQos3CmtsDebugDsidStatsEntry 
     MAX-ACCESS  not-accessible 
     STATUS      current 
     DESCRIPTION 
        "The CMTS Debug DSID Stats object describes statistics 
        at the CMTS for the forwarding of DSID-labeled downstream 
        packets. 
        The CMTS creates an instance for every combination of 
        MAC Domain, DSID value, and downstream channel on which 
        packets labeled with that DSID are transmitted. 
        The CMTS does not delete such instances while the corresponding 
        CmtsDebug object control instance exists." 
     ::= { docsQos3MibObjects 20} 
 
docsQos3CmtsDebugDsidStatsEntry OBJECT-TYPE 
     SYNTAX      DocsQos3CmtsDebugDsidStatsEntry 
     MAX-ACCESS  not-accessible 
     STATUS      current 
     DESCRIPTION 
        "The conceptual row of docsQos3CmtsDebugDsidStatsTable. 
        The ifIndex key corresponds to the MAC Domain interface 
        of the DSID." 
     INDEX { ifIndex,docsQos3CmtsDebugDsidDsid,docsQos3CmtsDebugDsidStatsDsIfIndex } 
     ::= { docsQos3CmtsDebugDsidStatsTable 1 } 
 
DocsQos3CmtsDebugDsidStatsEntry ::= SEQUENCE { 
     docsQos3CmtsDebugDsidStatsDsIfIndex 
                  InterfaceIndex, 
     docsQos3CmtsDebugDsidStatsDsidPackets 
                  Counter64, 
     docsQos3CmtsDebugDsidStatsDsidOctets 
                  Counter64 
     } 
 
docsQos3CmtsDebugDsidStatsDsIfIndex OBJECT-TYPE 
     SYNTAX      InterfaceIndex 
     MAX-ACCESS  not-accessible 
     STATUS      current 
     DESCRIPTION 
        "This key represents an interface index of a downstream 
        channel that belongs to the DSID" 
     ::= { docsQos3CmtsDebugDsidStatsEntry 1 } 
 
docsQos3CmtsDebugDsidStatsDsidPackets OBJECT-TYPE 
     SYNTAX      Counter64 
     UNITS       "packets" 
     MAX-ACCESS  read-only 
     STATUS      current 
     DESCRIPTION 
        "This attribute is a counter which contains the number 
        of packets transmitted by the CMTS which are labeled 
        with the DSID on the downstream channel. Discontinuities in 
        the value of this counter can occur as indicated by the value 
        of ifCounterDiscontinuityTime of the associated Downstream 
        interface index." 
     ::= { docsQos3CmtsDebugDsidStatsEntry 2 } 
 
docsQos3CmtsDebugDsidStatsDsidOctets OBJECT-TYPE 
     SYNTAX      Counter64 
     UNITS       "octets" 
     MAX-ACCESS  read-only 
     STATUS      current 
     DESCRIPTION 
        "This attribute counts the number of bytes transmitted 
        by the CMTS which are labeled with the DSID on the 
        downstream interface. Discontinuities in the value of 
        this counter can occur as indicated by the value of  
        ifCounterDiscontinuityTime of the associated Downstream 
        interface index." 
     ::= { docsQos3CmtsDebugDsidStatsEntry 3 } 
 
docsQos3CmDsidTable OBJECT-TYPE 
     SYNTAX      SEQUENCE OF DocsQos3CmDsidEntry 
     MAX-ACCESS  not-accessible 
     STATUS      current 
     DESCRIPTION 
        "When a DSID is created, during the registration process 
        or a DBC transaction,. The CM reports the current 
        status of existing DSID, for example, if a DSID  is deleted 
        or changed via DBC messages the corresponding 
        object instance is deleted or updated respectively." 
     ::= { docsQos3MibObjects 21} 
 
docsQos3CmDsidEntry OBJECT-TYPE 
     SYNTAX      DocsQos3CmDsidEntry 
     MAX-ACCESS  not-accessible 
     STATUS      current 
     DESCRIPTION 
        "The conceptual row of docsQos3CmDsidTable 
        The ifIndex key corresponds to the MAC Domain interface 
        of the DSID." 
     INDEX { ifIndex,docsQos3CmDsidDsid } 
     ::= { docsQos3CmDsidTable 1 } 
 
DocsQos3CmDsidEntry ::= SEQUENCE { 
     docsQos3CmDsidDsid 
                  Dsid, 
     docsQos3CmDsidUsage 
                  BITS, 
     docsQos3CmDsidNumReseqChs 
                  Unsigned32, 
     docsQos3CmDsidReseqChList 
                  ChannelList, 
     docsQos3CmDsidReseqWaitTime 
                  Unsigned32, 
     docsQos3CmDsidReseqWarnThrshld 
                  Unsigned32, 
     docsQos3CmDsidStatusHldoffTimerSeqOutOfRng 
                  Unsigned32, 
     docsQos3CmDsidOutOfRangeDiscards 
                  Unsigned32, 
     docsQos3CmDsidNextExpectedSeqNum 
                  Unsigned32, 
     docsQos3CmDsidCmInterfaceMask 
                  DocsL2vpnIfList, 
     docsQos3CmDsidFwdCmInterfaceMask 
                  DocsL2vpnIfList 
     } 
 
docsQos3CmDsidDsid OBJECT-TYPE 
     SYNTAX      Dsid 
     MAX-ACCESS  not-accessible 
     STATUS      current 
     DESCRIPTION 
        "This key represents the DSID." 
     ::= { docsQos3CmDsidEntry 1 } 
 
docsQos3CmDsidUsage OBJECT-TYPE 
     SYNTAX      BITS { 
 
                        resequencing(0), 
                        multicastCapable(1) 
                      } 
     MAX-ACCESS  read-only 
     STATUS      current 
     DESCRIPTION 
        "This attribute indicates the properties of the DSID. 
        The bits are defined as follows: 
        'resequencing' :  This bit is set to 1 for a Resequencing 
        DSID. 
        'multicastCapable' :  This bit is set to 1 for a DSID that 
        is capable of transporting multicast traffic (e.g., 
        the DSID has multicast forwarding attributes)." 
     ::= { docsQos3CmDsidEntry 2 } 
 
docsQos3CmDsidNumReseqChs OBJECT-TYPE 
     SYNTAX      Unsigned32 (1..65535) 
     MAX-ACCESS  read-only 
     STATUS      current 
     DESCRIPTION 
        "This attribute represents the number of channels 
        in the downstream resequencing channel list for this 
        DSID." 
     ::= { docsQos3CmDsidEntry 3 } 
 
docsQos3CmDsidReseqChList OBJECT-TYPE 
     SYNTAX      ChannelList 
     MAX-ACCESS  read-only 
     STATUS      current 
     DESCRIPTION 
        "This attribute represents the Downstream Channel 
        Set over which the DSID is being resequenced." 
     ::= { docsQos3CmDsidEntry 4 } 
 
docsQos3CmDsidReseqWaitTime OBJECT-TYPE 
     SYNTAX      Unsigned32 (1..180) 
     UNITS       "hundredMicroseconds" 
     MAX-ACCESS  read-only 
     STATUS      current 
     DESCRIPTION 
        "This attribute represents the DSID Resequencing 
        Wait Time that is used for this DSID. This attribute is 
        only valid when the Usage attribute has the resequencing 
        bit set to 1. This attribute returns a value of 0 
        when the Usage attribute has the resequencing bit set 
        to 0." 
     ::= { docsQos3CmDsidEntry 5 } 
 
docsQos3CmDsidReseqWarnThrshld OBJECT-TYPE 
     SYNTAX      Unsigned32 (0..179) 
     UNITS       "hundredMicroseconds" 
     MAX-ACCESS  read-only 
     STATUS      current 
     DESCRIPTION 
        "This attribute represents the DSID Resequencing 
        Warning Threshold that is used for this DSID. The value 
        of 0 indicates that the threshold warnings are disabled. 
        This attribute is only valid when the Usage attribute 
        has the resequencing bit set to 1. This attribute 
        returns a value of 0 when the Usage attribute has 
        the resequencing bit set to 0." 
     ::= { docsQos3CmDsidEntry 6 } 
 
docsQos3CmDsidStatusHldoffTimerSeqOutOfRng OBJECT-TYPE 
     SYNTAX      Unsigned32 (0..65535) 
     UNITS       "20milliseconds" 
     MAX-ACCESS  read-only 
     STATUS      current 
     DESCRIPTION 
        "This attribute represents the hold-off timer for 
        reporting Out-of-Range Events via the CM-STATUS MAC 
        Management message. This attribute is only valid when 
        the Usage attribute has the resequencing bit set 
        to 1. This attribute returns a value of 0 when the Usage 
        attribute has the resequencing bit set to 0." 
     ::= { docsQos3CmDsidEntry 7 } 
 
docsQos3CmDsidOutOfRangeDiscards OBJECT-TYPE 
     SYNTAX      Unsigned32 (0..65535) 
     MAX-ACCESS  read-only 
     STATUS      current 
     DESCRIPTION 
        "This attribute represents the current count of out-of-range 
        packets discarded by the CM for a given resequencing context  
        since an in-range packet was received.  When this count exceeds 
        1000 and more than two minutes have elapsed since an in-range  
        packet was received, the CM will reacquire sequence numbers for 
        this resequencing context." 
     ::= { docsQos3CmDsidEntry 8 } 
 
docsQos3CmDsidNextExpectedSeqNum OBJECT-TYPE 
     SYNTAX      Unsigned32 (0..65535) 
     MAX-ACCESS  read-only 
     STATUS      current 
     DESCRIPTION 
        "This attribute represents the Next Expected Packet 
        Sequence Number for a given resequencing context. 
        This attribute is only valid when the Usage attribute 
        has the resequencing bit set to 1. This attribute returns 
        a value of 0 when the Usage attribute has the resequencing 
        bit set to 0." 
     ::= { docsQos3CmDsidEntry 9 } 
 
docsQos3CmDsidCmInterfaceMask OBJECT-TYPE 
     SYNTAX      DocsL2vpnIfList 
     MAX-ACCESS  read-only 
     STATUS      current 
     DESCRIPTION 
        "This attribute represents the bitmap of the interfaces 
        communicated to the CM in a Multicast DSID encoding." 
     ::= { docsQos3CmDsidEntry 10 } 
 
docsQos3CmDsidFwdCmInterfaceMask OBJECT-TYPE 
     SYNTAX      DocsL2vpnIfList 
     MAX-ACCESS  read-only 
     STATUS      current 
     DESCRIPTION 
        "This attribute represents the bitmap of the interfaces 
        to which the CM forwards multicast traffic: a logical 
        OR of interfaces identified in CmInterfaceMask 
        and interfaces associated with the client MAC addresses 
        identified in the docsDevCmDsidMac instances 
        for this DSID." 
     ::= { docsQos3CmDsidEntry 11 } 
 
docsQos3CmDsidStatsTable OBJECT-TYPE 
     SYNTAX      SEQUENCE OF DocsQos3CmDsidStatsEntry 
     MAX-ACCESS  not-accessible 
     STATUS      current 
     DESCRIPTION 
        "This object defines a set of statistics the CM collects 
        per Dsid." 
     ::= { docsQos3MibObjects 22} 
 
docsQos3CmDsidStatsEntry OBJECT-TYPE 
     SYNTAX      DocsQos3CmDsidStatsEntry 
     MAX-ACCESS  not-accessible 
     STATUS      current 
     DESCRIPTION 
        "The conceptual row of docsQos3CmDsidStatsTable." 
     INDEX { docsQos3CmDsidStatsDsid } 
     ::= { docsQos3CmDsidStatsTable 1 } 
 
DocsQos3CmDsidStatsEntry ::= SEQUENCE { 
     docsQos3CmDsidStatsDsid 
                  Dsid, 
     docsQos3CmDsidStatsSeqNumMissing 
                  Counter32, 
     docsQos3CmDsidStatsSkewThreshExceeds 
                  Counter32, 
     docsQos3CmDsidStatsOutOfRangePackets 
                  Counter32, 
     docsQos3CmDsidStatsNumPackets 
                  Counter64 
     } 
 
docsQos3CmDsidStatsDsid OBJECT-TYPE 
     SYNTAX      Dsid 
     MAX-ACCESS  not-accessible 
     STATUS      current 
     DESCRIPTION 
        "This key represents the interface index of the MAC 
        Domain associated with the DSID." 
     ::= { docsQos3CmDsidStatsEntry 1 } 
 
docsQos3CmDsidStatsSeqNumMissing OBJECT-TYPE 
     SYNTAX      Counter32 
     UNITS       "packets" 
     MAX-ACCESS  read-only 
     STATUS      current 
     DESCRIPTION 
        "This attribute counts the number of times the Next Expected 
        Packet Sequence Number is declared lost. In this case one or 
        more data packets are lost. This is generally caused by  
        downstream packet loss." 
     REFERENCE 
        "DOCSIS 3.0 MAC and Upper Layer Protocols Interface 
        Specification CM-SP-MULPIv3.0-I05-070803, Downstream  
        Sequencing section." 
     ::= { docsQos3CmDsidStatsEntry 2 } 
 
docsQos3CmDsidStatsSkewThreshExceeds OBJECT-TYPE 
     SYNTAX      Counter32 
     UNITS       "packets" 
     MAX-ACCESS  read-only 
     STATUS      current 
     DESCRIPTION 
        "This attribute counts in-range sequenced packets 
        which were successfully received by the CM after a wait 
        time longer than the Resequencing Warning Threshold." 
     REFERENCE 
        "DOCSIS 3.0 MAC and Upper Layer Protocols Interface 
        Specification CM-SP-MULPIv3.0-I05-070803, Skew Requirements 
        section." 
     ::= { docsQos3CmDsidStatsEntry 3 } 
 
docsQos3CmDsidStatsOutOfRangePackets OBJECT-TYPE 
     SYNTAX      Counter32 
     UNITS       "packets" 
     MAX-ACCESS  read-only 
     STATUS      current 
     DESCRIPTION 
        "This attribute counts the number of packets Counter 
        received in a DSID reassembly context where the sequence 
        number which is out of range." 
     REFERENCE 
        "DOCSIS 3.0 MAC and Upper Layer Protocols Interface 
        Specification CM-SP-MULPIv3.0-I05-070803, Receive Channels 
        section." 
     ::= { docsQos3CmDsidStatsEntry 4 } 
 
docsQos3CmDsidStatsNumPackets OBJECT-TYPE 
     SYNTAX      Counter64 
     UNITS       "packets" 
     MAX-ACCESS  read-only 
     STATUS      current 
     DESCRIPTION 
        "This attribute counts the total number of data packets 
        of a DSID context forwarded for further processing." 
     ::= { docsQos3CmDsidStatsEntry 5 } 
 
docsQos3CmDsidClientTable OBJECT-TYPE 
     SYNTAX      SEQUENCE OF DocsQos3CmDsidClientEntry 
     MAX-ACCESS  not-accessible 
     STATUS      current 
     DESCRIPTION 
        "This object contains the client MAC addresses that 
        the CMTS requests that the CM uses to replicate Multicast 
        DSIDs during registration or during a DBC transaction. 
         
        When a DSID is created that includes client MAC addresses, 
        or when client MAC addresses are added to a DSID, 
        new rows are created to indicate the added client MAC 
        addresses. When a Client MAC address is deleted from 
        a DSID, the corresponding row is deleted.  When a DSID 
        is deleted, all corresponding rows are deleted, too." 
     REFERENCE 
        "DOCSIS 3.0 MAC and Upper Layer Protocols Interface 
        Specification CM-SP-MULPIv3.0-I05-070803, DSID Encodings 
        section in the Common Radio Frequency Interface Encodings 
        Annex." 
     ::= { docsQos3MibObjects 23} 
 
docsQos3CmDsidClientEntry OBJECT-TYPE 
     SYNTAX      DocsQos3CmDsidClientEntry 
     MAX-ACCESS  not-accessible 
     STATUS      current 
     DESCRIPTION 
        "The conceptual row of docsQos3CmDsidClientTable." 
     INDEX { docsQos3CmDsidClientDsid,docsQos3CmDsidClientClientMacId } 
     ::= { docsQos3CmDsidClientTable 1 } 
 
DocsQos3CmDsidClientEntry ::= SEQUENCE { 
     docsQos3CmDsidClientDsid 
                  Dsid, 
     docsQos3CmDsidClientClientMacId 
                  Unsigned32, 
     docsQos3CmDsidClientClientMacAddr 
                  MacAddress 
     } 
 
docsQos3CmDsidClientDsid OBJECT-TYPE 
     SYNTAX      Dsid 
     MAX-ACCESS  not-accessible 
     STATUS      current 
     DESCRIPTION 
        "This key defines the DSID that the client MAC addresses 
        are associated with." 
     ::= { docsQos3CmDsidClientEntry 1 } 
 
docsQos3CmDsidClientClientMacId OBJECT-TYPE 
     SYNTAX      Unsigned32 (1..65535) 
     MAX-ACCESS  not-accessible 
     STATUS      current 
     DESCRIPTION 
        "This key defines a uniquely identified Client Mac 
        Addresses associated with the DSID." 
     ::= { docsQos3CmDsidClientEntry 2 } 
 
docsQos3CmDsidClientClientMacAddr OBJECT-TYPE 
     SYNTAX      MacAddress 
     MAX-ACCESS  read-only 
     STATUS      current 
     DESCRIPTION 
        "This attribute defines a client MAC address to which 
        Multicast traffic labeled with this DSID should be 
        forwarded." 
     ::= { docsQos3CmDsidClientEntry 3 } 
 
docsQos3MibConformance OBJECT IDENTIFIER ::= { docsQos3Mib 2 } 
docsQos3MibCompliances OBJECT IDENTIFIER ::= { docsQos3MibConformance 1 } 
docsQos3MibGroups         OBJECT IDENTIFIER ::= { docsQos3MibConformance 2 } 
 
docsQos3Compliance MODULE-COMPLIANCE 
STATUS      current 
DESCRIPTION 
        "The compliance statement of managed objects common for Cable Modem 
        Termination Sytems (CMTS) and Cable Modems (CM)." 
 
    MODULE -- this MODULE 
MANDATORY-GROUPS { 
     docsQos3BaseGroup 
     } 
   
GROUP docsQos3CmtsGroup 
        DESCRIPTION 
            "This group is mandatory for Cable Modem Termination 
             Systems (CMTS) and is not implemented for Cable Modems 
             (CM)."      
              
GROUP docsQos3CmGroup 
        DESCRIPTION 
            "This group is mandatory for Cable Modems (CM)TS) and is  
            not implemented for Cable Modems Termination Systems (CMTS)."      
              
::= { docsQos3MibCompliances 1 } 

docsQos3BaseGroup OBJECT-GROUP 
    OBJECTS { 
     docsQos3PktClassDirection, 
     docsQos3PktClassPriority, 
     docsQos3PktClassIpTosLow, 
     docsQos3PktClassIpTosHigh, 
     docsQos3PktClassIpTosMask, 
     docsQos3PktClassIpProtocol, 
     docsQos3PktClassIpSourceAddr, 
     docsQos3PktClassIpSourceMask, 
     docsQos3PktClassIpDestAddr, 
     docsQos3PktClassIpDestMask, 
     docsQos3PktClassSourcePortStart, 
     docsQos3PktClassSourcePortEnd, 
     docsQos3PktClassDestPortStart, 
     docsQos3PktClassDestPortEnd, 
     docsQos3PktClassDestMacAddr, 
     docsQos3PktClassDestMacMask, 
     docsQos3PktClassSourceMacAddr, 
     docsQos3PktClassEnetProtocolType, 
     docsQos3PktClassEnetProtocol, 
     docsQos3PktClassUserPriLow, 
     docsQos3PktClassUserPriHigh, 
     docsQos3PktClassVlanId, 
     docsQos3PktClassState, 
     docsQos3PktClassPkts, 
     docsQos3PktClassBitMap, 
     docsQos3PktClassIpAddrType, 
     docsQos3PktClassFlowLabel, 
     docsQos3PktClassCmInterfaceMask, 
     docsQos3ParamSetServiceClassName, 
     docsQos3ParamSetPriority, 
     docsQos3ParamSetMaxTrafficRate, 
     docsQos3ParamSetMaxTrafficBurst, 
     docsQos3ParamSetMinReservedRate, 
     docsQos3ParamSetMinReservedPkt, 
     docsQos3ParamSetActiveTimeout, 
     docsQos3ParamSetAdmittedTimeout, 
     docsQos3ParamSetMaxConcatBurst, 
     docsQos3ParamSetSchedulingType, 
     docsQos3ParamSetNomPollInterval, 
     docsQos3ParamSetTolPollJitter, 
     docsQos3ParamSetUnsolicitGrantSize, 
     docsQos3ParamSetNomGrantInterval, 
     docsQos3ParamSetTolGrantJitter, 
     docsQos3ParamSetGrantsPerInterval, 
     docsQos3ParamSetTosAndMask, 
     docsQos3ParamSetTosOrMask, 
     docsQos3ParamSetMaxLatency, 
     docsQos3ParamSetRequestPolicyOct, 
     docsQos3ParamSetRequiredAttrMask, 
     docsQos3ParamSetForbiddenAttrMask, 
     docsQos3ParamSetAttrAggrRuleMask, 
     docsQos3ParamSetAppId, 
     docsQos3ParamSetMultiplierContentionReqWindow, 
     docsQos3ParamSetMultiplierBytesReq, 
     docsQos3ParamSetMaxReqPerSidCluster, 
     docsQos3ParamSetMaxOutstandingBytesPerSidCluster, 
     docsQos3ParamSetMaxTotBytesReqPerSidCluster, 
     docsQos3ParamSetMaxTimeInSidCluster, 
     docsQos3ParamSetPeakTrafficRate, 
     docsQos3ParamSetDsResequencing, 
     docsQos3ParamSetBitMap, 
     docsQos3ServiceFlowSID, 
     docsQos3ServiceFlowDirection, 
     docsQos3ServiceFlowPrimary, 
     docsQos3ServiceFlowParamSetTypeStatus, 
     docsQos3ServiceFlowChSetId, 
     docsQos3ServiceFlowAttrAssignSuccess, 
     docsQos3ServiceFlowDsid, 
     docsQos3ServiceFlowPkts, 
     docsQos3ServiceFlowOctets, 
     docsQos3ServiceFlowTimeCreated, 
     docsQos3ServiceFlowTimeActive, 
     docsQos3ServiceFlowPHSUnknowns, 
     docsQos3ServiceFlowPolicedDropPkts, 
     docsQos3ServiceFlowPolicedDelayPkts, 
     docsQos3DSAReqs, 
     docsQos3DSARsps, 
     docsQos3DSAAcks, 
     docsQos3DSCReqs, 
     docsQos3DSCRsps, 
     docsQos3DSCAcks, 
     docsQos3DSDReqs, 
     docsQos3DSDRsps, 
     docsQos3DynamicAdds, 
     docsQos3DynamicAddFails, 
     docsQos3DynamicChanges, 
     docsQos3DynamicChangeFails, 
     docsQos3DynamicDeletes, 
     docsQos3DynamicDeleteFails, 
     docsQos3DCCReqs, 
     docsQos3DCCRsps, 
     docsQos3DCCAcks, 
     docsQos3DCCs, 
     docsQos3DCCFails, 
     docsQos3DCCRspDeparts, 
     docsQos3DCCRspArrives, 
     docsQos3DCCRspDeparts, 
     docsQos3DCCRspArrives, 
     docsQos3DbcReqs, 
     docsQos3DbcRsps, 
     docsQos3DbcAcks, 
     docsQos3DbcSuccesses, 
     docsQos3DbcFails, 
     docsQos3DbcPartial, 
     docsQos3ServiceFlowSidClusterSid 
     } 
    STATUS      current 
    DESCRIPTION 
       "Group of objects implemented in both CM and CMTS." 
    ::= { docsQos3MibGroups 1 } 
 
docsQos3CmtsGroup OBJECT-GROUP 
    OBJECTS { 
     docsQos3UpstreamFragments, 
     docsQos3UpstreamFragDiscards, 
     docsQos3UpstreamConcatBursts, 
     docsQos3ServiceFlowLogIfIndex, 
     docsQos3ServiceFlowLogSFID, 
     docsQos3ServiceFlowLogCmMac, 
     docsQos3ServiceFlowLogPkts, 
     docsQos3ServiceFlowLogOctets, 
     docsQos3ServiceFlowLogTimeDeleted, 
     docsQos3ServiceFlowLogTimeCreated, 
     docsQos3ServiceFlowLogTimeActive, 
     docsQos3ServiceFlowLogDirection, 
     docsQos3ServiceFlowLogPrimary, 
     docsQos3ServiceFlowLogServiceClassName, 
     docsQos3ServiceFlowLogPolicedDropPkts, 
     docsQos3ServiceFlowLogPolicedDelayPkts, 
     docsQos3ServiceFlowLogControl, 
     docsQos3ServiceClassStatus, 
     docsQos3ServiceClassPriority, 
     docsQos3ServiceClassMaxTrafficRate, 
     docsQos3ServiceClassMaxTrafficBurst, 
     docsQos3ServiceClassMinReservedRate, 
     docsQos3ServiceClassMinReservedPkt, 
     docsQos3ServiceClassMaxConcatBurst, 
     docsQos3ServiceClassNomPollInterval, 
     docsQos3ServiceClassTolPollJitter, 
     docsQos3ServiceClassUnsolicitGrantSize, 
     docsQos3ServiceClassNomGrantInterval, 
     docsQos3ServiceClassTolGrantJitter, 
     docsQos3ServiceClassGrantsPerInterval, 
     docsQos3ServiceClassMaxLatency, 
     docsQos3ServiceClassActiveTimeout, 
     docsQos3ServiceClassAdmittedTimeout, 
     docsQos3ServiceClassSchedulingType, 
     docsQos3ServiceClassRequestPolicy, 
     docsQos3ServiceClassTosAndMask, 
     docsQos3ServiceClassTosOrMask, 
     docsQos3ServiceClassDirection, 
     docsQos3ServiceClassStorageType, 
     docsQos3ServiceClassDSCPOverwrite, 
     docsQos3ServiceClassRequiredAttrMask, 
     docsQos3ServiceClassForbiddenAttrMask, 
     docsQos3ServiceClassAttrAggrRuleMask, 
     docsQos3ServiceClassAppId, 
     docsQos3ServiceClassMultiplierContentionReqWindow, 
     docsQos3ServiceClassMultiplierBytesReq, 
     docsQos3ServiceClassMaxReqPerSidCluster, 
     docsQos3ServiceClassMaxOutstandingBytesPerSidCluster, 
     docsQos3ServiceClassMaxTotBytesReqPerSidCluster, 
     docsQos3ServiceClassMaxTimeInSidCluster, 
     docsQos3ServiceClassPeakTrafficRate, 
     docsQos3ServiceClassDsResequencing, 
     docsQos3CmtsIfIndex, 
     docsQos3GrpServiceFlowIsDef, 
     docsQos3GrpServiceFlowQosConfigId, 
     docsQos3GrpServiceFlowNumSess, 
     docsQos3GrpPktClassGrpConfigId, 
     docsQos3UpChCounterExtSgmtValids, 
     docsQos3UpChCounterExtSgmtDiscards, 
     docsQos3ServiceFlowCcfStatsSgmtValids, 
     docsQos3ServiceFlowCcfStatsSgmtLost, 
     docsQos3CmtsDsidUsage, 
     docsQos3CmtsDsidDsChSet, 
     docsQos3CmtsDsidReseqWaitTime, 
     docsQos3CmtsDsidReseqWarnThrshld, 
     docsQos3CmtsDsidStatusHldoffTimerSeqOutOfRng, 
     docsQos3CmtsDsidCurrentSeqNum, 
     docsQos3CmtsDebugDsidRowStatus, 
     docsQos3CmtsDebugDsidStatsDsidPackets, 
     docsQos3CmtsDebugDsidStatsDsidOctets 
     } 
   STATUS      current 
    DESCRIPTION 
       "Group of objects implemented in the CMTS only." 
    ::= { docsQos3MibGroups 2 } 
     
docsQos3CmGroup OBJECT-GROUP 
    OBJECTS { 
     docsQos3CmServiceUsStatsTxSlotsImmed, 
     docsQos3CmServiceUsStatsTxSlotsDed, 
     docsQos3CmServiceUsStatsTxRetries, 
     docsQos3CmServiceUsStatsTxExceededs, 
     docsQos3CmServiceUsStatsRqRetries, 
     docsQos3CmServiceUsStatsRqExceededs, 
     docsQos3CmServiceUsStatsSgmts, 
     docsQos3CmDsidUsage, 
     docsQos3CmDsidNumReseqChs, 
     docsQos3CmDsidReseqChList, 
     docsQos3CmDsidReseqWaitTime, 
     docsQos3CmDsidReseqWarnThrshld, 
     docsQos3CmDsidStatusHldoffTimerSeqOutOfRng, 
     docsQos3CmDsidOutOfRangeDiscards, 
     docsQos3CmDsidNextExpectedSeqNum, 
     docsQos3CmDsidCmInterfaceMask, 
     docsQos3CmDsidFwdCmInterfaceMask, 
     docsQos3CmDsidStatsSeqNumMissing, 
     docsQos3CmDsidStatsSkewThreshExceeds, 
     docsQos3CmDsidStatsOutOfRangePackets, 
     docsQos3CmDsidStatsNumPackets, 
     docsQos3CmDsidClientClientMacAddr 
     } 
   STATUS      current 
    DESCRIPTION 
       "Group of objects implemented in the CM only." 
    ::= { docsQos3MibGroups 3 }     
END
