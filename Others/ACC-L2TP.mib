ACC-L2TP DEFINITIONS ::= BEGIN

    IMPORTS
	 OBJECT-TYPE, IpAddress, TimeTicks, Gauge, Counter FROM RFC1155-SMI
	 TRAP-TYPE FROM RFC-1215
                accTrapLogSeqNum FROM ACC-SYSTEM
		accBRG, DisplayString, RowStatus, IfIndex, SmdsAddress
             FROM ACC-MIB;

-- L2TP Group
    -- ACC L2TP branch
    accL2tp 			OBJECT IDENTIFIER ::= { accBRG 71 }
    accL2tpGeneral		OBJECT IDENTIFIER ::= { accL2tp 1 }
    accL2tpGeneralScalars	OBJECT IDENTIFIER ::= { accL2tpGeneral 1 }
    accL2tpTransport		OBJECT IDENTIFIER ::= { accL2tp 2 }
    -- L2tp Transport branch
    accL2tpTransportUdp		OBJECT IDENTIFIER ::= { accL2tpTransport 1 }
    accL2tpTransportUdpScalars	OBJECT IDENTIFIER ::= { accL2tpTransportUdp 1 }
    --
    --  ACC general L2TP objects
    --
    accL2tpVendorName	OBJECT-TYPE
        SYNTAX  DisplayString
        ACCESS          read-only
        STATUS          mandatory
        DESCRIPTION
	     "Vendor Name"
	::= { accL2tpGeneralScalars 1 }
    accL2tpFirmwareRev	OBJECT-TYPE
        SYNTAX  DisplayString
        ACCESS          read-only
        STATUS          mandatory
        DESCRIPTION
	     "Firmware Revision"
	::= { accL2tpGeneralScalars 2 }
    accL2pAdminState OBJECT-TYPE
        SYNTAX  INTEGER {
                    enabled(1),
                    disabled(2)
                }
        ACCESS  read-write
        STATUS  mandatory
        DESCRIPTION
             "L2TP Adminstrative state."
        DEFVAL { disabled }
	::= { accL2tpGeneralScalars 3 }
    accL2tpProtocolVersion      OBJECT-TYPE
        SYNTAX  DisplayString
        ACCESS  read-only
        STATUS  mandatory
        DESCRIPTION
             "L2TP Protocol Version"
	::= { accL2tpGeneralScalars 4 }
    accL2tpControlRWS	OBJECT-TYPE
        SYNTAX  INTEGER (1..16)
        ACCESS          read-write
        STATUS          mandatory
        DESCRIPTION
	     "Default Control Window Size adopted by Dynamically created L2TP Tunnels"
	DEFVAL { 4 }
	::= { accL2tpGeneralScalars 5 }
    accL2tpPayloadSeq	OBJECT-TYPE
        SYNTAX  INTEGER {
			on(1),
			off(2)
			}
        ACCESS          read-write
        STATUS          mandatory
	DESCRIPTION
	     "If set to ON, the remote peer will wait for an acknowledgement after sending 
	      Payload RWS messages"
	DEFVAL { off }
	::= { accL2tpGeneralScalars 6 }
    accL2tpPayloadRWS	OBJECT-TYPE
	SYNTAX  INTEGER (1..32)
	ACCESS  	read-write
	STATUS		mandatory
        DESCRIPTION
	     "When Payload Sequencing is set to YES, the remote peer will
	     wait for an acknowledgement after sending this many messages"
	DEFVAL { 8 }
	::= { accL2tpGeneralScalars 7 }
    accL2tpKeepAlive	OBJECT-TYPE
        SYNTAX	INTEGER	(0..3600)
        ACCESS          read-write
        STATUS          mandatory
        DESCRIPTION
	     "Default Hello control message interval"
	DEFVAL	{ 60 }
	::= { accL2tpGeneralScalars 8 }
    accL2tpMaxAckTimeout	OBJECT-TYPE
        SYNTAX	INTEGER	(5..120)
        ACCESS          read-write
        STATUS          mandatory
        DESCRIPTION
	     "Timeout interval for both Control and Payload acknowledgements"
	DEFVAL { 30 }
	::= { accL2tpGeneralScalars 9 }
    accL2tpMaxRetrans	OBJECT-TYPE
        SYNTAX	INTEGER (0..64)
        ACCESS          read-write
        STATUS          mandatory
        DESCRIPTION
	     "Maximum number of Retransmissions before assuming a peer is not responding."
	DEFVAL { 16 }
	::= { accL2tpGeneralScalars 10 }
    accL2tpIdleDisconnect	OBJECT-TYPE
        SYNTAX	INTEGER (0..3600)
        ACCESS          read-write
        STATUS          mandatory
        DESCRIPTION
	     "Interval in which to wait after the last payload session within 
	     the tunnel disconnects before tearing down the tunnel itself"
	DEFVAL 	{ 30 }
	::= { accL2tpGeneralScalars 11 }
    accL2tpTunnelAuthentication	OBJECT-TYPE
        SYNTAX	INTEGER	{
			none(1),
			endpointauth(2)
			}
        ACCESS          read-write
        STATUS          mandatory
        DESCRIPTION
	     "Default sevurity method for dynamically created L2TP Tunnels"
	DEFVAL { none }
	::= { accL2tpGeneralScalars 12 }
    accL2tpKeyDistribution	OBJECT-TYPE
        SYNTAX	INTEGER {
			static(1),
			radius(2)
			}
        ACCESS          read-write
        STATUS          mandatory
        DESCRIPTION
	     "Method to obtain it's secrets for the specified security method"
	DEFVAL { static }
	::= { accL2tpGeneralScalars 13 }
    accL2tpProxyAuthentication 	OBJECT-TYPE
	SYNTAX	INTEGER	{
			ignore(1),
			accept(2)
			}
	ACCESS	read-write
	STATUS 	mandatory
	DESCRIPTION
	     "Causes the L2TP protocol to ignore the proxy authentication
	     information obtained by the L2TP access concentrator (LAC) 
	     if the proxy authentication method is CHAP. When L2TP ignores 
	     the proxy authentication, the PPP protocol is forced to 
	     challenge the remote client again."
	DEFVAL { accept }
	::= { accL2tpGeneralScalars 14 }
    accL2tpServerState		OBJECT-TYPE
	SYNTAX	INTEGER {
			enabled(1),
			disabled(2)
			}
	ACCESS	read-write
	STATUS	mandatory
	DESCRIPTION
	     "Enables or disables L2TP UDP Transport Server."
	DEFVAL	{ enabled }						
	::= { accL2tpGeneralScalars 15 }
    accL2tpMessageLevel	OBJECT-TYPE
	SYNTAX	INTEGER	(1..7)
	ACCESS	read-write
	STATUS	mandatory
	DESCRIPTION
	     "L2TP Message Level"
	DEFVAL	{ 1 }
	::= { accL2tpGeneralScalars 16 }
    accL2tpDebugMask	OBJECT-TYPE
	SYNTAX	INTEGER	(0..255)
	ACCESS	read-write
	STATUS	mandatory
	DESCRIPTION
	     "Set in conjunction with L2TP Message Level to filter out messages"
	DEFVAL	{ 255 }
	::=  { accL2tpGeneralScalars 17 }
    accL2tpPayLoadLength	OBJECT-TYPE
	SYNTAX	INTEGER	{
			included(1),
			excluded(2)
			}
	ACCESS	read-write
	STATUS	mandatory
	DESCRIPTION
	     "Used to configure the L2TP default action regarding payload lengths"
	DEFVAL	{ included }
	::=  { accL2tpGeneralScalars 18 }
    accL2tpAttributeHiding	OBJECT-TYPE
	SYNTAX	INTEGER {
			enabled(1),
			disabled(2)
			}
	ACCESS	read-write
	STATUS	mandatory
	DESCRIPTION
	     "Configures the way that L2TP handles attribute value pairs (AVPs).
	     Enabling this option causes L2TP to 'hide' AVPs typically considered
	     sensitive."
	DEFVAL	{ enabled }
	::=  { accL2tpGeneralScalars 19 }
    accL2tpCallConfirm	OBJECT-TYPE
	SYNTAX	INTEGER {
			enabled(1),
			disabled(2)
			}
	ACCESS	read-write
	STATUS	mandatory
	DESCRIPTION
	     "Configures the Call Confirm operation on L2TP LAC.  When enabled it
	     causes the LAC to verify that the LNS will proceed with a particular 
	     call."
	DEFVAL	{ disabled }
	::=  { accL2tpGeneralScalars 20 }
    --
    --          The L2TP Tunnel Configuration Table
    --
    accL2tpTunnelConfigTable OBJECT-TYPE
        SYNTAX  SEQUENCE OF AccL2tpTunnelConfigEntry
        ACCESS          not-accessible
        STATUS          mandatory
        DESCRIPTION
             "Displays all L2TP Tunnel entries configured on the system"
        ::= { accL2tpGeneral 2 }
    accL2tpTunnelConfigEntry OBJECT-TYPE
        SYNTAX  AccL2tpTunnelConfigEntry
        ACCESS  not-accessible
        STATUS  mandatory
	DESCRIPTION
	     ""
        INDEX   { accL2tpTunnelConfigTunnelIfIndex }
        ::= { accL2tpTunnelConfigTable 1 }
    AccL2tpTunnelConfigEntry ::= SEQUENCE {
        accL2tpTunnelConfigTunnelIfIndex	INTEGER,
        accL2tpTunnelConfigControlRWS		INTEGER,
        accL2tpTunnelConfigPayloadSeq		INTEGER,
        accL2tpTunnelConfigPayloadRWS		INTEGER,
        accL2tpTunnelConfigKeepAlive		INTEGER,
        accL2tpTunnelConfigMaxAckTimeout	INTEGER,
        accL2tpTunnelConfigMaxRetrans		INTEGER,
        accL2tpTunnelConfigIdleDisconnect	INTEGER,
        accL2tpTunnelConfigTransportMech	INTEGER,
        accL2tpTunnelConfigTunnelAuthentication	INTEGER,
        accL2tpTunnelConfigProxyAuthentication	INTEGER,
	accL2tpTunnelConfigMessageLevel		INTEGER,
	accL2tpTunnelConfigDebugMask		INTEGER,
	accL2tpTunnelConfigPayLoadLength	INTEGER,
	accL2tpTunnelConfigAttributeHiding	INTEGER,
	accL2tpTunnelConfigCallConfirm		INTEGER,
	accL2tpTunnelConfigEvents		INTEGER,
	accL2tpTunnelConfigCreate		RowStatus,
	accL2tpTunnelConfigStatus		RowStatus
        }
    accL2tpTunnelConfigTunnelIfIndex OBJECT-TYPE
        SYNTAX  INTEGER (0..4294967295)
        ACCESS  read-only
        STATUS  mandatory
        DESCRIPTION
             "Interface index for a tunnel port"
	::= { accL2tpTunnelConfigEntry 1 }
    accL2tpTunnelConfigControlRWS   OBJECT-TYPE
        SYNTAX  INTEGER (1..16)
        ACCESS          read-write
        STATUS          mandatory
        DESCRIPTION
             "Default Control Window Size adopted by Dynamically created L2TP Tunnels"
        DEFVAL { 4 }
	::= { accL2tpTunnelConfigEntry 2 }
    accL2tpTunnelConfigPayloadSeq   OBJECT-TYPE
        SYNTAX  INTEGER {
                        on(1),
                        off(2)
                        }
        ACCESS          read-write
        STATUS          mandatory
        DESCRIPTION
             "If set to ON, the remote peer will wait for an acknowledgement after sending
              Payload RWS messages"
        DEFVAL { off }
	::= { accL2tpTunnelConfigEntry 3 }
    accL2tpTunnelConfigPayloadRWS   OBJECT-TYPE
        SYNTAX  INTEGER (1..32)
        ACCESS          read-write
        STATUS          mandatory
        DESCRIPTION
             "When Payload Sequencing is set to YES, the remote peer 
              will wait for an acknowledgement after sending this many 
              messages"
        DEFVAL { 8 }
	::= { accL2tpTunnelConfigEntry 4 }
    accL2tpTunnelConfigKeepAlive    OBJECT-TYPE
        SYNTAX  INTEGER (0..3600)
        ACCESS          read-write
        STATUS          mandatory
        DESCRIPTION
             "Default Hello control message interval"
	DEFVAL	{ 60 }
	::= { accL2tpTunnelConfigEntry 5 }
    accL2tpTunnelConfigMaxAckTimeout        OBJECT-TYPE
        SYNTAX  INTEGER (5..120)
        ACCESS          read-write
        STATUS          mandatory
        DESCRIPTION
             "Timeout interval for both Control and Payload acknowledgements"
        DEFVAL { 30 }
	::= { accL2tpTunnelConfigEntry 6 }
    accL2tpTunnelConfigMaxRetrans   OBJECT-TYPE
        SYNTAX  INTEGER (0..64)
        ACCESS          read-write
        STATUS          mandatory
        DESCRIPTION
             "Maximum number of Retransmissions before assuming a peer is not 
	     responding."
        DEFVAL { 16 }
	::= { accL2tpTunnelConfigEntry 7 }
    accL2tpTunnelConfigIdleDisconnect       OBJECT-TYPE
        SYNTAX  INTEGER (0..3600)
        ACCESS          read-write
        STATUS          mandatory
        DESCRIPTION
             "Interval in which to wait after the last payload session within the 
	     tunnel disconnects before tearing down the tunnel itself"
        DEFVAL  { 30 }
	::= { accL2tpTunnelConfigEntry 8 }
    accL2tpTunnelConfigTransportMech	OBJECT-TYPE
	SYNTAX	INTEGER	{
			udp(1),
			framerelay(2)
			}
	ACCESS	read-write
	STATUS	mandatory
	DESCRIPTION
	     "Type of Transport layer protocol that L2TP should use for this tunnel"
	DEFVAL	{ udp }
	::= { accL2tpTunnelConfigEntry 9 }
    accL2tpTunnelConfigTunnelAuthentication       OBJECT-TYPE
        SYNTAX  INTEGER {
                        enable(1),
                        disabled(2)
                        }
        ACCESS          read-write
        STATUS          mandatory
        DESCRIPTION
             "Configures the tunnel peer authentication method used for
	     dynamically created L2TP tunnels."
        DEFVAL { disabled }
	::= { accL2tpTunnelConfigEntry 10 }
    accL2tpTunnelConfigProxyAuthentication      OBJECT-TYPE
        SYNTAX  INTEGER {
                        ignore(1),
                        accept(2)
                        }
        ACCESS  read-write
        STATUS  mandatory
        DESCRIPTION
             "Causes the L2TP protocol to ignore the proxy authentication information
	     obtained by the access concentrator if the proxy authentication method
	     is CHAP."
        DEFVAL { accept }
	::= { accL2tpTunnelConfigEntry 11 }
    accL2tpTunnelConfigMessageLevel OBJECT-TYPE
        SYNTAX  INTEGER (1..7)
        ACCESS  read-write
        STATUS  mandatory
        DESCRIPTION
             "L2TP Message Level"
        DEFVAL  { 1 }
	::= { accL2tpTunnelConfigEntry 12 }
    accL2tpTunnelConfigDebugMask    OBJECT-TYPE
        SYNTAX  INTEGER (0..255)
        ACCESS  read-write
        STATUS  mandatory
        DESCRIPTION
             "Set in conjunction with L2TP Message Level to filter out messages"
        DEFVAL  { 255 }
	::= { accL2tpTunnelConfigEntry 13 }
    accL2tpTunnelConfigPayLoadLength    OBJECT-TYPE
        SYNTAX  INTEGER {
			included(1),
			excluded(2)
			}
        ACCESS  read-write
        STATUS  mandatory
        DESCRIPTION
             "Used to configure the L2TP default action regarding payload
	     lengths. Including the payload length in the L2TP payload 
	     L2TP header enables some vendors to avoid recalculating the 
	     payload length. Disabling this option informs L2TP not to
	     include the payload length in the L2TP packet header, reducing
	     the overall L2TP packet size by two bytes. Entering this 
	     command without specifying a setting causes the L2TP tunnel 
	     payload length to return to its default setting."
        DEFVAL  { excluded }
	::=  { accL2tpTunnelConfigEntry 14 }
    accL2tpTunnelConfigAttributeHiding    OBJECT-TYPE
        SYNTAX  INTEGER {
			enabled(1),
			disabled(2)
			}
        ACCESS  read-write
        STATUS  mandatory
        DESCRIPTION
             "Configures the way that L2TP handles attribute value pairs 
	     (AVP's). Disabling this parameter causes all AVPs to be sent
	     without encryption; this might be necessary when tunneling 
	     to a peer that does not support attribute hiding. If this 
	     command is entered without specifying a setting, attribute 
	     hiding returns to its default setting."
        DEFVAL  { enabled }
	::= { accL2tpTunnelConfigEntry 15 }
    accL2tpTunnelConfigCallConfirm    OBJECT-TYPE
        SYNTAX  INTEGER {
			enabled(1),
			disabled(2)
			}
        ACCESS  read-write
        STATUS  mandatory
        DESCRIPTION
	     "Configures the Call Confirm operation on L2TP LAC.  When 
	     enabled it causes the LAC to verify that the LNS will 
	     proceed with a particular call.  If the LNS is not able to 
	     proceed with the call because of missing information in the 
	     call setup message or resource limitations, the LNS rejects 
	     the call.  This, in turn, causes the LAC to disconnect the 
	     remote user. If the LAC is configured to perform called number 
	     tunneling, or the called number authorization mode is 'VPSM,' 
	     the incoming call will not be answered until the LAC has 
	     confirmed the call with the LNS. Enabling this option can 
	     lessen needless call charges. The LAC confirms the call with 
	     the LNS when the LAC sends an initial session setup message, 
	     including called and calling number information, to the LNS."
        DEFVAL  { disabled }
	::= { accL2tpTunnelConfigEntry 16 }
    accL2tpTunnelConfigEvents    OBJECT-TYPE
        SYNTAX  INTEGER {
			open(1),
			close(2)
			}
        ACCESS  read-write
        STATUS  mandatory
        DESCRIPTION
             "This object is used to generate events into the tunnel
	     state machine. For example a 'open' will cause the
	     tunnel to be forced open if it is idle. A 'close' will
	     cause a disconnect of a established tunnel"
        DEFVAL { open }
	::= { accL2tpTunnelConfigEntry 17 }
    accL2tpTunnelConfigCreate    OBJECT-TYPE
        SYNTAX  RowStatus
        ACCESS  read-write
        STATUS  mandatory
        DESCRIPTION
             "The current status of this entry. It can be used to
	     create and delete tunnel entries."
	::= { accL2tpTunnelConfigEntry 18 }
    accL2tpTunnelConfigStatus    OBJECT-TYPE
        SYNTAX  RowStatus
        ACCESS  read-write
        STATUS  mandatory
        DESCRIPTION
             "The current status of this entry."
	::=  { accL2tpTunnelConfigEntry 19 }
    --
    --          The L2TP Tunnel Status Table
    --
    accL2tpTunnelStatusTable OBJECT-TYPE
        SYNTAX  SEQUENCE OF AccL2tpTunnelStatusEntry
        ACCESS          not-accessible
        STATUS          mandatory
        DESCRIPTION
             "Displays status of all L2TP Tunnel entries Configured on the system"
	::= { accL2tpGeneral 3 }
    accL2tpTunnelStatusEntry OBJECT-TYPE
        SYNTAX  AccL2tpTunnelStatusEntry
        ACCESS  not-accessible
        STATUS  mandatory
	DESCRIPTION
	     ""
        INDEX   { accL2tpTunnelStatusTunnelIfIndex }
	::= { accL2tpTunnelStatusTable 1 }
    AccL2tpTunnelStatusEntry ::= SEQUENCE {
        accL2tpTunnelStatusTunnelIfIndex        	INTEGER,
        accL2tpTunnelStatusLocalTunnelId		INTEGER,
        accL2tpTunnelStatusRemTunnelId			INTEGER,
        accL2tpTunnelStatusRemFraming    		INTEGER,
        accL2tpTunnelStatusRemBearerCap			INTEGER,
        accL2tpTunnelStatusRemControlRWS		INTEGER,
        accL2tpTunnelStatusRemKeepAlive			INTEGER,
        accL2tpTunnelStatusRemVendorName		DisplayString,
        accL2tpTunnelStatusRemFirmRev        		DisplayString,
	accL2tpTunnelStatusRemHostName			DisplayString,
	accL2tpTunnelStatusRemProtocolVer		DisplayString,
        accL2tpTunnelStatusTunnelState       		INTEGER,
        accL2tpTunnelStatusKeepAlive            	INTEGER,
        accL2tpTunnelStatusCalcRemRWS           	Gauge,
        accL2tpTunnelStatusCalcRemRetransTimeout        Gauge,
        accL2tpTunnelStatusQueueLength            	Gauge,
        accL2tpTunnelStatusTxOctets            		Counter,
        accL2tpTunnelStatusTxPackets            	Counter,
        accL2tpTunnelStatusRxOctets           		Counter,
        accL2tpTunnelStatusRxPackets            	Counter,
        accL2tpTunnelStatusTotalSessions          	Counter,
        accL2tpTunnelStatusActiveSessions          	Gauge,
        accL2tpTunnelStatusAttemptFails         	Counter,
	accL2tpTunnelStatusRetransTimeouts         	Counter,
        accL2tpTunnelStatusBackwardTransitions          Counter,
        accL2tpTunnelStatusLastTransitions            	TimeTicks,
        accL2tpTunnelStatusLastCause            	DisplayString,
        accL2tpTunnelStatusNextSendSeq            	INTEGER,
        accL2tpTunnelStatusNextSendSeqAck            	INTEGER,
        accL2tpTunnelStatusRecvSeq 	           	INTEGER,
        accL2tpTunnelStatusRecvSeqAck            	INTEGER,
        accL2tpTunnelStatusOutOfSeqs            	Counter,
        accL2tpTunnelStatusOutOfSeqQLen            	Gauge,
        accL2tpTunnelStatusOutOfWindows            	Counter,
        accL2tpTunnelStatusInDiscards            	Counter,
        accL2tpTunnelStatusOutDiscards            	Counter
        }
    accL2tpTunnelStatusTunnelIfIndex	OBJECT-TYPE
	SYNTAX	INTEGER	(0..4294967295)
	ACCESS	read-only
	STATUS	mandatory
	DESCRIPTION
	     "Interface index for a tunnel port"
	::= { accL2tpTunnelStatusEntry 1 }
    accL2tpTunnelStatusLocalTunnelId	OBJECT-TYPE
	SYNTAX	INTEGER	(0..65535)
	ACCESS	read-only
	STATUS	mandatory
	DESCRIPTION
	     "Local Tunnel port Id"
	::= { accL2tpTunnelStatusEntry 2 }
    accL2tpTunnelStatusRemTunnelId	OBJECT-TYPE
	SYNTAX	INTEGER (0..65535)
	ACCESS	read-only
	STATUS	mandatory
	DESCRIPTION
	     "Remote Tunnel port Id"
	::= { accL2tpTunnelStatusEntry 3 }
    accL2tpTunnelStatusRemFraming	OBJECT-TYPE
	SYNTAX	INTEGER	{
			sync(1),
			async(2),
			syncasync(3)
			}
	ACCESS	read-only
	STATUS	mandatory
	DESCRIPTION
	     "Remote Framing"
	::= { accL2tpTunnelStatusEntry 4 }
    accL2tpTunnelStatusRemBearerCap	OBJECT-TYPE
	SYNTAX	INTEGER	{
			digital(1),
			analog(2),
			digitalanalog(3)
			}
	ACCESS	read-only
	STATUS	mandatory
	DESCRIPTION
	     "Remote Bearer Capabilities"
	::= { accL2tpTunnelStatusEntry 5 }
    accL2tpTunnelStatusRemControlRWS	OBJECT-TYPE
	SYNTAX	INTEGER	(1..16)
	ACCESS	read-only
	STATUS	mandatory
	DESCRIPTION
	     "Control Window Size adopted by Remote end of L2TP Tunnels"
	::= { accL2tpTunnelStatusEntry 6 }
    accL2tpTunnelStatusRemKeepAlive	OBJECT-TYPE
	SYNTAX	INTEGER (0..3600)
	ACCESS	read-only
	STATUS	mandatory
	DESCRIPTION
	     "Remote Hello control message interval"
	::= { accL2tpTunnelStatusEntry 7 }
    accL2tpTunnelStatusRemVendorName	OBJECT-TYPE
	SYNTAX	DisplayString
	ACCESS	read-only
	STATUS	mandatory
	DESCRIPTION
	     "Remote Vendor Name"
	::= { accL2tpTunnelStatusEntry 8 }
    accL2tpTunnelStatusRemFirmRev	OBJECT-TYPE
	SYNTAX	DisplayString
	ACCESS	read-only
	STATUS	mandatory
	DESCRIPTION
	     "Remote Firmware Revision"
	::= { accL2tpTunnelStatusEntry 9 }
    accL2tpTunnelStatusRemHostName   OBJECT-TYPE
        SYNTAX  DisplayString
        ACCESS  read-only
        STATUS  mandatory
        DESCRIPTION
             "Remote Host Name"
	::= { accL2tpTunnelStatusEntry 10 }
    accL2tpTunnelStatusRemProtocolVer   OBJECT-TYPE
        SYNTAX  DisplayString
        ACCESS  read-only
        STATUS  mandatory
        DESCRIPTION
             "Remote Protocol Version"
	::= { accL2tpTunnelStatusEntry 11 }
     accL2tpTunnelStatusTunnelState	OBJECT-TYPE
     	SYNTAX	INTEGER	{
     			idle(1),
     			waitreply(2),
     			waitconn(3),
     			established(4),
     			waitstop(5)
     			}
     	ACCESS	read-only
     	STATUS	mandatory
     	DESCRIPTION
     	     "Indicates the current state of the L2TP Tunnel"
	::= { accL2tpTunnelStatusEntry 12 }
    accL2tpTunnelStatusKeepAlive	OBJECT-TYPE
	SYNTAX	INTEGER	(0..3600)
	ACCESS	read-write
	STATUS	mandatory
	DESCRIPTION
	     "Default Hello control message interval"
	DEFVAL	{ 60  }
	::= { accL2tpTunnelStatusEntry 13 }
    accL2tpTunnelStatusCalcRemRWS	OBJECT-TYPE
	SYNTAX	Gauge	--(1..255)
	ACCESS	read-only
	STATUS	mandatory
	DESCRIPTION
	     "Calculated Remote RWS"
	::= { accL2tpTunnelStatusEntry 14 }
    accL2tpTunnelStatusCalcRemRetransTimeout	OBJECT-TYPE
	SYNTAX	Gauge	--(1..65535)
	ACCESS	read-only
	STATUS	mandatory
	DESCRIPTION
	     "Calculated Remote Retransmit Timeout"
	::= { accL2tpTunnelStatusEntry 15 }
    accL2tpTunnelStatusQueueLength	OBJECT-TYPE
	SYNTAX	Gauge  	--(1..65535)
	ACCESS	read-only
	STATUS	mandatory
	DESCRIPTION
	     "Queue Length"
	::= { accL2tpTunnelStatusEntry 16 }
    accL2tpTunnelStatusTxOctets	OBJECT-TYPE
	SYNTAX	Counter
	ACCESS	read-only
	STATUS	mandatory
	DESCRIPTION
	     "Octets Transmitted"
	::= { accL2tpTunnelStatusEntry 17 }
    accL2tpTunnelStatusTxPackets	OBJECT-TYPE
	SYNTAX	Counter
	ACCESS	read-only
	STATUS	mandatory
	DESCRIPTION
	     "Packets Transmitted"
	::= { accL2tpTunnelStatusEntry 18 }
    accL2tpTunnelStatusRxOctets	OBJECT-TYPE
	SYNTAX	Counter
	ACCESS	read-only
	STATUS	mandatory
	DESCRIPTION
	     "Octets Received"
	::= { accL2tpTunnelStatusEntry 19 }
    accL2tpTunnelStatusRxPackets	OBJECT-TYPE
	SYNTAX	Counter
	ACCESS	read-only
	STATUS	mandatory
	DESCRIPTION
	     "Packets Received"
	::= { accL2tpTunnelStatusEntry 20 }
    accL2tpTunnelStatusTotalSessions	OBJECT-TYPE
	SYNTAX	Counter
	ACCESS	read-only
	STATUS	mandatory
	DESCRIPTION
	     "Total Sessions"
	::= { accL2tpTunnelStatusEntry 21 }
    accL2tpTunnelStatusActiveSessions	OBJECT-TYPE
	SYNTAX	Gauge
	ACCESS	read-only
	STATUS	mandatory
	DESCRIPTION
	     "Active Sessions"
	::= { accL2tpTunnelStatusEntry 22 }
    accL2tpTunnelStatusAttemptFails	OBJECT-TYPE
	SYNTAX	Counter
	ACCESS	read-only
	STATUS	mandatory
	DESCRIPTION
	     "Failed Attempts"
	::= { accL2tpTunnelStatusEntry 23 }
    accL2tpTunnelStatusRetransTimeouts	OBJECT-TYPE
	SYNTAX	Counter
	ACCESS	read-only
	STATUS	mandatory
	DESCRIPTION
	     "Retransmit timeouts"
	::= { accL2tpTunnelStatusEntry 24 }
    accL2tpTunnelStatusBackwardTransitions	OBJECT-TYPE
	SYNTAX	Counter
	ACCESS	read-only
	STATUS	mandatory
	DESCRIPTION
	     "Number of Backward transmissions"
	::= { accL2tpTunnelStatusEntry 25 }
    accL2tpTunnelStatusLastTransitions	OBJECT-TYPE
	SYNTAX	TimeTicks 
	ACCESS	read-only
	STATUS	mandatory
	DESCRIPTION
	     "Time since Last Transition"
	::= { accL2tpTunnelStatusEntry 26 }
    accL2tpTunnelStatusLastCause	OBJECT-TYPE
	SYNTAX	DisplayString 
	ACCESS	read-only
	STATUS	mandatory
	DESCRIPTION
	     "Cause for Last Transition"
	::= { accL2tpTunnelStatusEntry 27 }
    accL2tpTunnelStatusNextSendSeq	OBJECT-TYPE
	SYNTAX	INTEGER 
	ACCESS	read-only
	STATUS	mandatory
	DESCRIPTION
	     "Shows the next sequence number to be sent in the 
	     next control packet."
	::= { accL2tpTunnelStatusEntry 28 }
    accL2tpTunnelStatusNextSendSeqAck	OBJECT-TYPE
	SYNTAX	INTEGER 
	ACCESS	read-only
	STATUS	mandatory
	DESCRIPTION
	     "Shows the sequence number acknowledged by the terminal
	     peer."
	::= { accL2tpTunnelStatusEntry 29 }
    accL2tpTunnelStatusRecvSeq	OBJECT-TYPE
	SYNTAX	INTEGER
	ACCESS	read-only
	STATUS	mandatory
	DESCRIPTION
	     "Shows the last sequence number received in a control 
	     packet."
	::= { accL2tpTunnelStatusEntry 30 }
    accL2tpTunnelStatusRecvSeqAck	OBJECT-TYPE
	SYNTAX	INTEGER 
	ACCESS	read-only
	STATUS	mandatory
	DESCRIPTION
	     "Shows the last sequence number this L2TP entity has 
	     acknowledged to the remote peer as received."
	::= { accL2tpTunnelStatusEntry 31 }
    accL2tpTunnelStatusOutOfSeqs	OBJECT-TYPE
	SYNTAX	Counter 
	ACCESS	read-only
	STATUS	mandatory
	DESCRIPTION
	     "Indicates the number of control packets that were 
	     received out of sequence."
	::= { accL2tpTunnelStatusEntry 32 }
    accL2tpTunnelStatusOutOfSeqQLen	OBJECT-TYPE
	SYNTAX	Gauge 
	ACCESS	read-only
	STATUS	mandatory
	DESCRIPTION
	     "Indicates the number of control packets that were
             received out of sequence. These control packets wait
	     for a specified time in the out of sequence queue
	     for the packet with the missing sequence number."
	::= { accL2tpTunnelStatusEntry 33 }
    accL2tpTunnelStatusOutOfWindows	OBJECT-TYPE
	SYNTAX	Counter 
	ACCESS	read-only
	STATUS	mandatory
	DESCRIPTION
	     "The number of control packets that were received
   	     outside of the offered sequence window size."
	::= { accL2tpTunnelStatusEntry 34 }
    accL2tpTunnelStatusInDiscards	OBJECT-TYPE
	SYNTAX	Counter 
	ACCESS	read-only
	STATUS	mandatory
	DESCRIPTION
	     "The number of packets that are discarded coming in."
	::= { accL2tpTunnelStatusEntry 35 }
    accL2tpTunnelStatusOutDiscards	OBJECT-TYPE
	SYNTAX	Counter 
	ACCESS	read-only
	STATUS	mandatory
	DESCRIPTION
	     "The number of packets that are discarded going out."
	::= { accL2tpTunnelStatusEntry 36 }
    --
    --          accL2tpGeneral 4 is reserved
    --
    --
    --          The L2TP Session Table
    --
    accL2tpSessionTable OBJECT-TYPE
        SYNTAX  SEQUENCE OF AccL2tpSessionEntry
        ACCESS  not-accessible
        STATUS  mandatory
        DESCRIPTION
             "Displays all L2TP Tunnel entries configured on the system"
	::= { accL2tpGeneral 5 }
    accL2tpSessionEntry OBJECT-TYPE
        SYNTAX  AccL2tpSessionEntry
        ACCESS  not-accessible
        STATUS  mandatory
       	DESCRIPTION
	     ""
	INDEX   { accL2tpSessionTunnelIfIndex, accL2tpSessionLocalCallId }
	::= { accL2tpSessionTable 1 }
    AccL2tpSessionEntry ::= SEQUENCE {
        accL2tpSessionTunnelIfIndex     INTEGER,
	accL2tpSessionCallType		INTEGER,
        accL2tpSessionLocalCallId	INTEGER,
        accL2tpSessionRemoteCallId      INTEGER,
        accL2tpSessionCallSerialId      DisplayString,
	accL2tpSessionRemoteHostName	DisplayString,
        accL2tpSessionPhysChanId        INTEGER,
        accL2tpSessionBearerCap         INTEGER,
        accL2tpSessionFramingCap        INTEGER,
        accL2tpSessionConnectSpeed      INTEGER,
        accL2tpSessionDNIS              DisplayString,
        accL2tpSessionCLID              DisplayString,
        accL2tpSessionSubAddress        DisplayString,
        accL2tpSessionRemoteRWS         INTEGER,
        accL2tpSessionRemotePPD         INTEGER,
        accL2tpSessionProxyPpp          INTEGER,
        accL2tpSessionAuthMethod        INTEGER,
        accL2tpSessionState             INTEGER,
        accL2tpSessionLocalPort         INTEGER
        }
    accL2tpSessionTunnelIfIndex	OBJECT-TYPE
	SYNTAX	INTEGER	(0..4294967295)
	ACCESS	read-only
	STATUS	mandatory
	DESCRIPTION
	     "Interface index for tunnel port"
	::= { accL2tpSessionEntry 1 }
        accL2tpSessionCallType     OBJECT-TYPE
        SYNTAX  INTEGER {
			incoming(1),
			outgoing(2)
			}
        ACCESS  read-only
        STATUS  mandatory
        DESCRIPTION
             "Call Direction"
	::= { accL2tpSessionEntry 2 }
    accL2tpSessionLocalCallId	OBJECT-TYPE
	SYNTAX	INTEGER	(1..65535)
	ACCESS	read-only
	STATUS	mandatory
	DESCRIPTION
	     "Session Identifier used by Local Tunnel Endpoint for this session"
	::= { accL2tpSessionEntry 3 }
    accL2tpSessionRemoteCallId	OBJECT-TYPE
	SYNTAX	INTEGER	(1..65535)
	ACCESS	read-only
	STATUS	mandatory
	DESCRIPTION
	     "Session Identifier used by Remote Tunnel Endpoint for this session"
	::= { accL2tpSessionEntry 4 }
    accL2tpSessionCallSerialId	OBJECT-TYPE
	SYNTAX	DisplayString
	ACCESS	read-only
	STATUS	mandatory
	DESCRIPTION
	     "Serial ID for this session"
	::= { accL2tpSessionEntry 5 }
        accL2tpSessionRemoteHostName        OBJECT-TYPE
        SYNTAX  DisplayString
        ACCESS  read-only
        STATUS  mandatory
        DESCRIPTION
             "Remote Host Name"
	::= { accL2tpSessionEntry 6 }
    accL2tpSessionPhysChanId	OBJECT-TYPE
	SYNTAX	INTEGER	(0..65535)
	ACCESS	read-only
	STATUS	mandatory
	DESCRIPTION
	     "Port Identifier of the Physical Port being tunneled at the other 
	     end of this tunnel"
	::= { accL2tpSessionEntry 7 }
    accL2tpSessionBearerCap	OBJECT-TYPE
	SYNTAX	INTEGER	{
			digital(1),
			analog(2)
			}
	ACCESS	read-only
	STATUS	mandatory
	DESCRIPTION
	     "Type of call that has been physically terminated at the LAC"
	::= { accL2tpSessionEntry 8 }
    accL2tpSessionFramingCap	OBJECT-TYPE
	SYNTAX	INTEGER	{
			sync(1),
			async(2)
			}
	ACCESS	read-only
	STATUS	mandatory
	DESCRIPTION
	     "Type of call that has been physically terminated at the LAC"
	::= { accL2tpSessionEntry 9 }
    accL2tpSessionConnectSpeed	OBJECT-TYPE
	SYNTAX	INTEGER	(0..4294967295)
	ACCESS	read-only
	STATUS	mandatory
	DESCRIPTION
	     "LAC's Negotiated Modem Speed"
	::= { accL2tpSessionEntry 10 }
    accL2tpSessionDNIS	OBJECT-TYPE
	SYNTAX	DisplayString
	ACCESS	read-only
	STATUS	mandatory
	DESCRIPTION
	     "Phone number dialed by the Remote User"
	DEFVAL	{ "N/A"  }
	::= { accL2tpSessionEntry 11 }
    accL2tpSessionCLID	OBJECT-TYPE
	SYNTAX	DisplayString
	ACCESS	read-only
	STATUS	mandatory
	DESCRIPTION
	     "Phone number that the Remote User is dialing from"
	DEFVAL	{ "N/A"  }
	::= { accL2tpSessionEntry 12 }
    accL2tpSessionSubAddress	OBJECT-TYPE
	SYNTAX	DisplayString
	ACCESS	read-only
	STATUS	mandatory
	DESCRIPTION
	     "Additional Addressing Information"
	::= { accL2tpSessionEntry 13 }
    accL2tpSessionRemoteRWS	OBJECT-TYPE
	SYNTAX	INTEGER	(0..255)
	ACCESS	read-only
	STATUS	mandatory
	DESCRIPTION
	     "Payload Receive Window Size that the remote endpoint has requested 
	     for this session"
	::= { accL2tpSessionEntry 14 }
    accL2tpSessionRemotePPD	OBJECT-TYPE
	SYNTAX	INTEGER	(0..65535)
	ACCESS	read-only
	STATUS	mandatory
	DESCRIPTION
	     "Packet Processing Delay that the remote endpoint expects to incur 
	     for processing a window full of packets received (in 0.1 second units)"
	::= { accL2tpSessionEntry 15 }
    accL2tpSessionProxyPpp	OBJECT-TYPE
	SYNTAX	INTEGER	{
			yes(1),
			no(2)
			}
	ACCESS	read-only
	STATUS	mandatory
	DESCRIPTION
	     "A value of YES indicates that the LAC initiated a PPP session with 
	     the remote client before tunneling was performed"
	::= { accL2tpSessionEntry 16 }
    accL2tpSessionAuthMethod	OBJECT-TYPE
	SYNTAX	INTEGER	{
			none(1),
			pap(2),
			chap(3)
			}
	ACCESS	read-only
	STATUS	mandatory
	DESCRIPTION
	     "If Proxy PPP was performed, then this field may indicate the type 
	     of authentication that was initiated"
	::= { accL2tpSessionEntry 17 }
    accL2tpSessionState	OBJECT-TYPE
	SYNTAX	INTEGER	{
			idle(1),
			waittunnel(2),
			waitreply(3),
			waitconn(4),
			established(5),
			waitnotify(6)
			}
	ACCESS	read-only
	STATUS	mandatory
	DESCRIPTION
	     "Current state of the session"
	::= { accL2tpSessionEntry 18 }
    accL2tpSessionLocalPort	OBJECT-TYPE
	SYNTAX	INTEGER	(0..65535)
	ACCESS	read-only
	STATUS	mandatory
	DESCRIPTION
	     "Local interface that this tunnel has connected to"
	::= { accL2tpSessionEntry 19 }
    --
    --          The L2TP Session Status Table
    --
    accL2tpSessionStatusTable OBJECT-TYPE
        SYNTAX  SEQUENCE OF AccL2tpSessionStatusEntry
        ACCESS          not-accessible
        STATUS          mandatory
        DESCRIPTION
             "Displays all L2TP Tunnel entries configured on the system"
	::= { accL2tpGeneral 6 }
    accL2tpSessionStatusEntry OBJECT-TYPE
        SYNTAX  AccL2tpSessionStatusEntry
        ACCESS  not-accessible
        STATUS  mandatory
	DESCRIPTION
	     ""
        INDEX   { accL2tpSessionStatusTunnelIfIndex, accL2tpSessionStatusLocalCallId }
	::= { accL2tpSessionStatusTable 1 }
    AccL2tpSessionStatusEntry ::= SEQUENCE {
        accL2tpSessionStatusTunnelIfIndex     	INTEGER,
        accL2tpSessionStatusLocalCallId       	INTEGER,
        accL2tpSessionStatusInDiscards		Counter,
        accL2tpSessionStatusTxSequenceResets   	Counter,
        accL2tpSessionStatusCalcRWS           	Gauge,
        accL2tpSessionStatusTxQueueLength      	Gauge,
	accL2tpSessionStatusNextSendSeq     	INTEGER,
	accL2tpSessionStatusNextSendSeqAck	INTEGER,
	accL2tpSessionStatusNextRecvSeq     	INTEGER,
	accL2tpSessionStatusNextRecvSeqAck	INTEGER,
	accL2tpSessionStatusOutOfSeqs     	Counter,
	accL2tpSessionStatusOutOfSeqQLen     	Gauge,
	accL2tpSessionStatusTxOctets     	Counter,
	accL2tpSessionStatusTxPackets     	Counter,
	accL2tpSessionStatusRxOctets     	Counter,
	accL2tpSessionStatusRxPackets     	Counter,
	accL2tpSessionStatusOutDiscards     	Counter,
	accL2tpSessionStatusOutOfWindows     	Counter,
	accL2tpSessionStatusRxSequenceResets   	INTEGER
	}
    accL2tpSessionStatusTunnelIfIndex   	OBJECT-TYPE
        SYNTAX  INTEGER (0..4294967295)
        ACCESS  read-only
        STATUS  mandatory
        DESCRIPTION
             "Interface index for tunnel port"
	::= { accL2tpSessionStatusEntry 1 }
    accL2tpSessionStatusLocalCallId  	OBJECT-TYPE
        SYNTAX  INTEGER (1..65535)
        ACCESS  read-only
        STATUS  mandatory
        DESCRIPTION
             "Session Identifier used by Local Tunnel Endpoint for this session"
	::= { accL2tpSessionStatusEntry 2 }
    accL2tpSessionStatusInDiscards	OBJECT-TYPE
        SYNTAX  Counter	
        ACCESS  read-only
        STATUS  mandatory
        DESCRIPTION
             "Number of Payload packets discarded because transmit queue was full"
	::= { accL2tpSessionStatusEntry 3 }
    accL2tpSessionStatusTxSequenceResets		OBJECT-TYPE
        SYNTAX  Counter
        ACCESS  read-only
        STATUS  mandatory
        DESCRIPTION
             "Shows the number of packets that were sent with the
	     Reset bit (R-bit) set."
	::= { accL2tpSessionStatusEntry 4 }
        accL2tpSessionStatusCalcRWS		OBJECT-TYPE
        SYNTAX  Gauge	
        ACCESS  read-only
        STATUS  mandatory
        DESCRIPTION
             "Calculated Remote RWS"
	::= { accL2tpSessionStatusEntry 5 }
    accL2tpSessionStatusTxQueueLength	OBJECT-TYPE
        SYNTAX  Gauge	
        ACCESS  read-only
        STATUS  mandatory
        DESCRIPTION
             "Queue Length"
	::= { accL2tpSessionStatusEntry 6 }
    accL2tpSessionStatusNextSendSeq	OBJECT-TYPE
        SYNTAX  INTEGER	
        ACCESS  read-only
        STATUS  mandatory
        DESCRIPTION
             "Shows the number of sequenced packets sent from this RAC 
	     at the time the display command was performed. This value 
	     increments sequentially from 0 to 65535.  After the maximum 
	     value of 65535 is reached, the sequence restarts at 0."
	::= { accL2tpSessionStatusEntry 7 }
    accL2tpSessionStatusNextSendSeqAck	OBJECT-TYPE
        SYNTAX  INTEGER	
        ACCESS  read-only
        STATUS  mandatory
        DESCRIPTION
             "Shows the number of sequenced packets sent from this RAC 
	     that have been acknowledged by the remote peer since the 
	     tunnel was established. This value increments sequentially 
	     from 0 to 65535. After the maximum value of 65535 is
	     reached, the sequence restarts at 0."
	::= { accL2tpSessionStatusEntry 8 }
    accL2tpSessionStatusNextRecvSeq	OBJECT-TYPE
        SYNTAX  INTEGER	
        ACCESS  read-only
        STATUS  mandatory
        DESCRIPTION
             "Shows the number of sequenced packets that this RAC 
	     has received and acknowledged back to its tunnel peer
	     since the tunnel was established. This value increments 
	     sequentially from 0 to 65535. After the maximum value of 
	     65535 is reached, the sequence restarts at 0."
	::= { accL2tpSessionStatusEntry 9 }
    accL2tpSessionStatusNextRecvSeqAck	OBJECT-TYPE
        SYNTAX  INTEGER	
        ACCESS  read-only
        STATUS  mandatory
        DESCRIPTION
             "Shows the number of sequenced packets received by this RAC
	     that have been acknowledged to the remote peer since the 
	     tunnel was established. This value increments sequentially 
	     from 0 to 65535. After the maximum value of 65535 is
	     reached, the sequence restarts at 0."
	::= { accL2tpSessionStatusEntry 10 }
    accL2tpSessionStatusOutOfSeqs	OBJECT-TYPE
        SYNTAX  Counter	
        ACCESS  read-only
        STATUS  mandatory
        DESCRIPTION
             "Shows the number of payload packets waiting in the
	     out-of-sequence queue. Packets in this queue are waiting 
	     for the delivery of packets that may be delayed in the 
	     network."
	::= { accL2tpSessionStatusEntry 11 }
    accL2tpSessionStatusOutOfSeqQLen	OBJECT-TYPE
        SYNTAX  Gauge	
        ACCESS  read-only
        STATUS  mandatory
        DESCRIPTION
             "Shows the number of payload packets waiting in the
	     out-of-sequence queue. Packets in this queue are waiting 
	     for the delivery of packets that may be delayed in the 
	     network."
	::= { accL2tpSessionStatusEntry 12 }
    accL2tpSessionStatusTxOctets	OBJECT-TYPE
        SYNTAX  Counter	
        ACCESS  read-only
        STATUS  mandatory
        DESCRIPTION
             "The number of octets that are being transmitted."
	::= { accL2tpSessionStatusEntry 13 }
    accL2tpSessionStatusTxPackets	OBJECT-TYPE
        SYNTAX  Counter	
        ACCESS  read-only
        STATUS  mandatory
        DESCRIPTION
             "The number of packets that are being transmitted."
	::= { accL2tpSessionStatusEntry 14 }
    accL2tpSessionStatusRxOctets	OBJECT-TYPE
        SYNTAX  Counter	
        ACCESS  read-only
        STATUS  mandatory
        DESCRIPTION
             "The number of octets that are being received."
	::= { accL2tpSessionStatusEntry 15 }
    accL2tpSessionStatusRxPackets	OBJECT-TYPE
        SYNTAX  Counter	
        ACCESS  read-only
        STATUS  mandatory
        DESCRIPTION
             "The number of packets that are being received."
	::= { accL2tpSessionStatusEntry 16 }
    accL2tpSessionStatusOutDiscards	OBJECT-TYPE
        SYNTAX  Counter	
        ACCESS  read-only
        STATUS  mandatory
        DESCRIPTION
             "Shows the number of received packets that have
	     been discarded during this session."
	::= { accL2tpSessionStatusEntry 17 }
    accL2tpSessionStatusOutOfWindows	OBJECT-TYPE
        SYNTAX  Counter	
        ACCESS  read-only
        STATUS  mandatory
        DESCRIPTION
             "The number of payload packets that were received
	     outside of the offered sequence window size."
	::= { accL2tpSessionStatusEntry 18 }
    accL2tpSessionStatusRxSequenceResets	OBJECT-TYPE
        SYNTAX  INTEGER	
        ACCESS  read-only
        STATUS  mandatory
        DESCRIPTION
             "The number of payload packets that were received
	     that had the R-bit set."
	::= { accL2tpSessionStatusEntry 19 }
    --
    --          The L2TP Endpoint Domain Table
    --
    accL2tpEndpointDomainTable OBJECT-TYPE
        SYNTAX  SEQUENCE OF AccL2tpEndpointDomainEntry
        ACCESS  not-accessible
        STATUS  mandatory
        DESCRIPTION
             "Displays all L2TP Tunnel entries configured on the system"
	::= { accL2tpGeneral 7 }
    accL2tpEndpointDomainEntry OBJECT-TYPE
        SYNTAX  AccL2tpEndpointDomainEntry
        ACCESS  not-accessible
        STATUS  mandatory
	DESCRIPTION
	     ""
        INDEX   { accL2tpEndpointDomain } 
	::= { accL2tpEndpointDomainTable 1 }
    AccL2tpEndpointDomainEntry ::= SEQUENCE {
	accL2tpEndpointDomain			DisplayString,
	accL2tpEndpointDomainSecret		DisplayString,
	accL2tpEndpointDomainNumberGroup	INTEGER,
	accL2tpEndpointDomainStatus		RowStatus
        }
    accL2tpEndpointDomain     OBJECT-TYPE
        SYNTAX  DisplayString
        ACCESS  read-only
        STATUS  mandatory
        DESCRIPTION
             "A domain typically consist of L2TP tunnel peers. Each of which can
	     serve as an endpoint for a tunnel originating at the local router."
	::= { accL2tpEndpointDomainEntry 1 }
    accL2tpEndpointDomainSecret OBJECT-TYPE
        SYNTAX  DisplayString
        ACCESS  read-write
        STATUS  mandatory
        DESCRIPTION
             "Shared password used by tunnel peers to authenticate each other."
	::= { accL2tpEndpointDomainEntry 2 }
    accL2tpEndpointDomainNumberGroup  OBJECT-TYPE
        SYNTAX  INTEGER
        ACCESS  read-write
        STATUS  mandatory
        DESCRIPTION
             "This object identifies the Called Number Group that
	     is to be associated with this Endpoint Domain."
	::= { accL2tpEndpointDomainEntry 3 }
    accL2tpEndpointDomainStatus  OBJECT-TYPE
        SYNTAX  RowStatus
        ACCESS  read-write
        STATUS  mandatory
        DESCRIPTION
             "The current status of this entry."
	::= { accL2tpEndpointDomainEntry 4 }
    --
    --		L2TP Transport Objects
    --
    --		L2TP Transport UDP Objects
    --
    accL2tpUdpServerPort	OBJECT-TYPE
	SYNTAX	INTEGER	(1..65535)
	ACCESS	read-write
	STATUS	mandatory
	DESCRIPTION
	     "Default UDP Port number L2TP will connect to when passively waiting for 
	      incoming connections"
	DEFVAL	{ 1701 }
	::= { accL2tpTransportUdpScalars 1 }
    accL2tpUdpPayloadCksums	OBJECT-TYPE
	SYNTAX	INTEGER	{
			yes(1),
			no(2)
			}
	ACCESS	read-write
	STATUS	mandatory
	DESCRIPTION
	     "When set to YES, L2TP will inform UDP to checksum L2TP Payload messages.
	      L2TP Control messages are always checksummed"
	DEFVAL	{ no }
	::= { accL2tpTransportUdpScalars 2 }
    accL2tpUdpFixedAddress	OBJECT-TYPE
	SYNTAX	INTEGER	{
			yes(1),
			no(2)
			}
	ACCESS	read-write
	STATUS	mandatory
	DESCRIPTION
	     "Configures the default behavior of the transport driver to support 
	     multihomed or roaming endpoints."
	DEFVAL	{ no }
	::= { accL2tpTransportUdpScalars 3 }
    accL2tpUdpSrcIpAddress	OBJECT-TYPE
	SYNTAX	IpAddress
	ACCESS	read-write
	STATUS	mandatory
	DESCRIPTION
	     "configures the L2TP UDP transport driver to assign the 
	     given address to all L2TP packets trans mitted. Configuring 
	     a fixed interface by assigning an IP address to all L2TP 
	     packets is done to improve L2TP performance; however, limiting
	     this value to a single interface may cause the address to 
	     become unreachable if the network goes down."
	::= { accL2tpTransportUdpScalars 4 }
    accL2tpUdpStatsRsrcFails	OBJECT-TYPE
	SYNTAX	Counter	
	ACCESS	read-write
	STATUS	mandatory
	DESCRIPTION
	     "Shows the number of times that a request for memory has 
	     failed."
	::= { accL2tpTransportUdpScalars 5 }
    accL2tpUdpStatsInDiscards	OBJECT-TYPE
	SYNTAX	Counter	
	ACCESS	read-write
	STATUS	mandatory
	DESCRIPTION
	     "Shows the number of received L2TP packets that were discarded."
	::= { accL2tpTransportUdpScalars 6 }
    accL2tpUdpStatsUnknownTIDs	OBJECT-TYPE
	SYNTAX	Counter	
	ACCESS	read-write
	STATUS	mandatory
	DESCRIPTION
	     "Shows the number of packets received from unknown tunnels."
	::= { accL2tpTransportUdpScalars 7 }
    --
    --          The L2TP UDP Transport Table
    --
    accL2tpUdpTransportTable OBJECT-TYPE
        SYNTAX  SEQUENCE OF AccL2tpUdpTransportEntry
        ACCESS          not-accessible
        STATUS          mandatory
        DESCRIPTION
             "Displays all L2TP Tunnel entries configured on the system"
	::= { accL2tpTransportUdp 2 }
    accL2tpUdpTransportEntry OBJECT-TYPE
        SYNTAX  AccL2tpUdpTransportEntry
        ACCESS  not-accessible
        STATUS  mandatory
	DESCRIPTION
	     ""
        INDEX   { accL2tpUdpTransportTunnelIfIndex }
	::= { accL2tpUdpTransportTable 1 }
    AccL2tpUdpTransportEntry ::= SEQUENCE {
	accL2tpUdpTransportTunnelIfIndex     INTEGER,
	accL2tpUdpTransportEndpointIpAddress IpAddress,
	accL2tpUdpTransportPort              INTEGER,
	accL2tpUdpTransportPayloadCksum      INTEGER,
	accL2tpUdpTransportFixedAddress      INTEGER,
	accL2tpUdpTransportStatus            RowStatus
        }
    accL2tpUdpTransportTunnelIfIndex       OBJECT-TYPE
        SYNTAX  INTEGER (0..4294967295)
        ACCESS  read-only
        STATUS  mandatory
        DESCRIPTION
             "Interface index for tunnel port"
	::= { accL2tpUdpTransportEntry 1 }
    accL2tpUdpTransportEndpointIpAddress    OBJECT-TYPE
        SYNTAX  IpAddress
        ACCESS  read-only
        STATUS  mandatory
        DESCRIPTION
             "Tunnel Remote Endpoint Ip Address"
	::= { accL2tpUdpTransportEntry 2 }
    accL2tpUdpTransportPort OBJECT-TYPE
        SYNTAX  INTEGER (0..65535)
        ACCESS  read-write
        STATUS  mandatory
        DESCRIPTION
             "Value of UDP Port that will be used when establishing a 
	     connection"
        DEFVAL  { 1701 }
	::= { accL2tpUdpTransportEntry 3 }
    accL2tpUdpTransportPayloadCksum OBJECT-TYPE
        SYNTAX  INTEGER {
                        yes(1),
                        no(2)
                        }
        ACCESS  read-write
        STATUS  mandatory
        DESCRIPTION
             "When this is set to YES, UDP will calculate the Payload checksum"
        DEFVAL  { no }
	::= { accL2tpUdpTransportEntry 4 }
    accL2tpUdpTransportFixedAddress   OBJECT-TYPE
        SYNTAX  INTEGER {
			yes(1),
			no(2)
			}
        ACCESS  read-write
        STATUS  mandatory
        DESCRIPTION
             "Configures the L2tp UDP transport layer to support 
	     multihomed or roaming remote clients.Supporting multihomed 
	     remote clients enables the tunnel peer to change its IP 
	     address; this typically occurs if the remote client is 
	     multihomed or has a co-located LAC and roams out of a zone."
        DEFVAL  { no }
	::= { accL2tpUdpTransportEntry 5 }
    accL2tpUdpTransportStatus   OBJECT-TYPE
        SYNTAX  RowStatus
        ACCESS  read-write
        STATUS  mandatory
        DESCRIPTION
             "The current status of this entry."
	::= { accL2tpUdpTransportEntry 6 }
    --
    --          The L2TP UDP Connection Table
    --
    accL2tpUdpConnectionTable OBJECT-TYPE
        SYNTAX  SEQUENCE OF AccL2tpUdpConnectionEntry
        ACCESS          not-accessible
        STATUS          mandatory
        DESCRIPTION
             "Displays all L2TP Tunnel entries configured on the system"
	::= { accL2tpTransportUdp 3 }
    accL2tpUdpConnectionEntry OBJECT-TYPE
        SYNTAX  AccL2tpUdpConnectionEntry
        ACCESS  not-accessible
        STATUS  mandatory
        DESCRIPTION
	     ""
        INDEX   { accL2tpUdpConnectionTunnelIfIndex }
	::= { accL2tpUdpConnectionTable 1 }
    AccL2tpUdpConnectionEntry ::= SEQUENCE {
        accL2tpUdpConnectionTunnelIfIndex     	INTEGER,
        accL2tpUdpConnectionEndpointIpAddress 	IpAddress,
        accL2tpUdpConnectionRxPort            	INTEGER,
        accL2tpUdpConnectionTxPort	      	INTEGER,
        accL2tpUdpConnectionAddressChanges	Counter
        }
    accL2tpUdpConnectionTunnelIfIndex       OBJECT-TYPE
        SYNTAX  INTEGER (0..4294967295)
        ACCESS  read-only
        STATUS  mandatory
        DESCRIPTION
             "Interface index for tunnel port"
	::= { accL2tpUdpConnectionEntry 1 }
    accL2tpUdpConnectionEndpointIpAddress    OBJECT-TYPE
        SYNTAX  IpAddress
        ACCESS  read-only
        STATUS  mandatory
        DESCRIPTION
             "Tunnel Remote Endpoint Ip Address"
	::= { accL2tpUdpConnectionEntry 2 }
    accL2tpUdpConnectionRxPort      OBJECT-TYPE
        SYNTAX  INTEGER	(0..65535)
        ACCESS  read-only
        STATUS  mandatory
        DESCRIPTION
             "Receive Port"
	::= { accL2tpUdpConnectionEntry 3 }
    accL2tpUdpConnectionTxPort      OBJECT-TYPE
        SYNTAX  INTEGER	(0..65535)
        ACCESS  read-only
        STATUS  mandatory
        DESCRIPTION
             "Transmit Port"
	::= { accL2tpUdpConnectionEntry 4 }
    accL2tpUdpConnectionAddressChanges  OBJECT-TYPE
        SYNTAX  Counter
        ACCESS  read-only
        STATUS  mandatory
        DESCRIPTION
             "Number of times User changed his Ip Address"
	::= { accL2tpUdpConnectionEntry 5 }
-- START CFG_TRAP_ENHANCEMENTS
-- L2tp Traps Branch Enterprise
      accL2tpTraps OBJECT IDENTIFIER    ::= { accL2tpTransportUdp 4 }
        accL2tpTrapMsg     OBJECT-TYPE
        SYNTAX          DisplayString
        ACCESS          read-only
        STATUS          mandatory
        DESCRIPTION
                  " Enterprise Trap Message for L2tp"
        ::= { accL2tpTraps 1 }
-- END CFG_TRAP_ENHANCEMENTS 

        accL2tpTunnelDelTrap TRAP-TYPE
        ENTERPRISE   accL2tpTraps 
        VARIABLES  { accL2tpTrapMsg,
                     accL2tpSessionLocalCallId ,
                      accTrapLogSeqNum}
        DESCRIPTION
                "When L2TP resources associated with a tunnel port are
                released and removing any references, if any sessions
                are left., delete action fails. This trap message
                carries this information.
SEVERITY-DEFAULT: Minor 
EVENTTYPE-DEFAULT: 10 
ADDITIONAL-TEXT-VARIABLES: { accTrapLogSeqNum,accL2tpTrapMsg }
PCAUSE-DEFAULT: 46 " 
 
        ::= 1
        accL2tpTrap2 TRAP-TYPE
        ENTERPRISE   accL2tpTraps 
        VARIABLES  { accL2tpTrapMsg,
                     accL2tpUdpTransportTunnelIfIndex ,
                      accTrapLogSeqNum}
        DESCRIPTION
                "While searching the UDP endpoint database to see if
                the EP exists., transport entry can exist without l2tp
                tunnel ports and so tries to create one and generates
                this trap if this creation fails.
SEVERITY-DEFAULT: Minor 
EVENTTYPE-DEFAULT: 10 
ADDITIONAL-TEXT-VARIABLES: { accTrapLogSeqNum,accL2tpTrapMsg }
PCAUSE-DEFAULT: 46 " 
 
        ::= 2
        accL2tpUdpEpTrap TRAP-TYPE
        ENTERPRISE   accL2tpTraps 
        VARIABLES  { accL2tpTrapMsg ,
                      accTrapLogSeqNum}
        DESCRIPTION
                "In the ad hoc L2tp testing, all the tunnels are created
                and brought up. In the process if the L25 UDP end point
                is not found, then this trap is generated. 
SEVERITY-DEFAULT: Minor 
EVENTTYPE-DEFAULT: 10 
ADDITIONAL-TEXT-VARIABLES: { accTrapLogSeqNum,accL2tpTrapMsg }
PCAUSE-DEFAULT: 46 " 
 
        ::= 3
        accL2tpUdpEpCreateTrap TRAP-TYPE
        ENTERPRISE   accL2tpTraps 
        VARIABLES  { accL2tpTrapMsg ,
                      accTrapLogSeqNum}
        DESCRIPTION
                   "In the ad hoc L2tp testing, all the tunnels are
                   created and brought up. In the process if the
                   creation of end point fails then this trap is generated
SEVERITY-DEFAULT: Minor 
EVENTTYPE-DEFAULT: 10 
ADDITIONAL-TEXT-VARIABLES: { accTrapLogSeqNum,accL2tpTrapMsg }
PCAUSE-DEFAULT: 46 " 
 
        ::= 4
        accL2tpTunnelCreateTrap TRAP-TYPE
        ENTERPRISE   accL2tpTraps 
        VARIABLES  { accL2tpTrapMsg ,
                      accTrapLogSeqNum}
        DESCRIPTION
                   "In the ad hoc L2tp testing, all the tunnels are
                    created and brought up. In the process if the
                    creation of a tunnel fails then this trap is
                    generated
SEVERITY-DEFAULT: Warning 
EVENTTYPE-DEFAULT: 10 
ADDITIONAL-TEXT-VARIABLES: { accTrapLogSeqNum,accL2tpTrapMsg }
PCAUSE-DEFAULT: 7 " 
 
        ::= 5
        accL2tpInvIntfAddrTrap TRAP-TYPE
        ENTERPRISE   accL2tpTraps 
        VARIABLES  { accL2tpTrapMsg,
                     accL2tpUdpSrcIpAddress ,
                      accTrapLogSeqNum}
        DESCRIPTION
                   "This trap message indicates that the IP address
                    specified in the 'set L2TP UDP source IP address' is
                    invalid. An address associated with one of the IP
                    network entries must be specified. In the process of
                    Updating the L2tp MIB structure if the invalid interface
                    is referenced with the UDP, this trap is generated
SEVERITY-DEFAULT: Warning 
EVENTTYPE-DEFAULT: 10 
ADDITIONAL-TEXT-VARIABLES: { accTrapLogSeqNum,accL2tpTrapMsg }
PCAUSE-DEFAULT: 7 " 
 
        ::= 6
        accL2tpTunnelAbortCleanUpTrap TRAP-TYPE
        ENTERPRISE   accL2tpTraps 
        VARIABLES  { accL2tpTrapMsg,
                     accL2tpTunnelStatusTunnelState ,
                      accTrapLogSeqNum}
        DESCRIPTION
                   "While doing the tunnel clean up if the tunnel state
                   is not Idle then this trap indicating the abort on
                   tunnel clean up is generated
SEVERITY-DEFAULT: Minor 
EVENTTYPE-DEFAULT: 10 
ADDITIONAL-TEXT-VARIABLES: { accTrapLogSeqNum,accL2tpTrapMsg }
PCAUSE-DEFAULT: 46 " 
 
        ::= 7
        accL2tpTrap8 TRAP-TYPE
        ENTERPRISE   accL2tpTraps 
        VARIABLES  { accL2tpTrapMsg ,
                      accTrapLogSeqNum}
        DESCRIPTION
                " 
SEVERITY-DEFAULT: Minor 
EVENTTYPE-DEFAULT: 10 
ADDITIONAL-TEXT-VARIABLES: { accTrapLogSeqNum,accL2tpTrapMsg }
PCAUSE-DEFAULT: 46 " 
 
        ::= 8
        accL2tpUdpServTrap TRAP-TYPE
        ENTERPRISE   accL2tpTraps 
        VARIABLES  { accL2tpTrapMsg,
                     accL2tpUdpTransportEndpointIpAddress ,
                      accTrapLogSeqNum}
        DESCRIPTION
                   "During Demultiplexing, If the appropriate tunnel
                    is not found, attempt is made to establish a new
                    tunnel. In such a situation, if the promiscous
                    server is not enabled then  this trap is generated
                    indicating the same
SEVERITY-DEFAULT: Major 
EVENTTYPE-DEFAULT: 10 
ADDITIONAL-TEXT-VARIABLES: { accTrapLogSeqNum,accL2tpTrapMsg }
PCAUSE-DEFAULT: 46 " 
 
        ::= 9
        accL2tpTrap10 TRAP-TYPE
        ENTERPRISE   accL2tpTraps 
        VARIABLES  { accL2tpTrapMsg ,
                      accTrapLogSeqNum}
        DESCRIPTION
                   "During Demultiplexing, If the appropriate tunnel is
                    not found, attempt is made to establish a new tunnel.
                    In such a situation,  if the udpt creation fails, 
                    then this trap is generated indicating the same.
                    and increments the failure count
SEVERITY-DEFAULT: Minor 
EVENTTYPE-DEFAULT: 10 
ADDITIONAL-TEXT-VARIABLES: { accTrapLogSeqNum,accL2tpTrapMsg }
PCAUSE-DEFAULT: 46 " 
 
         ::= 10
END
