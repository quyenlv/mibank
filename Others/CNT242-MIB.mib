--
--
--          Computer Network Technology, Corp.
--              6000 Nathan Lane North 
--              Plymouth, Minnesota  55441   
--
--                phone:  (763) 268-8000
--                  fax:  (763) 268-8800
--              support:  1-800-NET-TECH
--                email:  cnt.com
--
--	MIB Version:     2.4
--	Product Family:  CNT Zeus(2) Subagent(4) Escon(2) 
--
-- +------------+ if you change this mib, you increment the version number.
-- | Attention! | Also, this MIB is supported by the escon subagent, and
-- +------------+ that agent must also be compiled with this mib version.
--
--
-- Version 2.4: Changed Counter to Counter32 for SimpleSoft compiler.

CNT242-MIB DEFINITIONS ::= BEGIN

	IMPORTS
		enterprises, Counter
			FROM RFC1065-SMI
		Counter32, MODULE-IDENTITY FROM SNMPv2-SMI
		OBJECT-TYPE
			FROM RFC-1212
		DisplayString
			FROM SNMPv2-TC
		cnt2Subagent
			FROM CNT2-MIB;

        cnt2Escon MODULE-IDENTITY
                LAST-UPDATED "0012110000Z"
                ORGANIZATION "Computer Network Technology Corporation"
                CONTACT-INFO "<intentionaly left out>"
                DESCRIPTION  "This defines the CNT Escon Engine MIB"
                ::= { enterprises cnt(333) cnt2(2) cnt2Subagent(4) 2 }

---     cnt		OBJECT IDENTIFIER ::= { enterprises 333 }
---     cnt2		OBJECT IDENTIFIER ::= { cnt 2 }
---     cnt2Subagent	OBJECT IDENTIFIER ::= { cnt2 4 }


        //cnt2Escon   OBJECT IDENTIFIER ::= { cnt2Subagent 2 }

	-- the Escon Information table
	
	cnt2EsconTable OBJECT-TYPE
		SYNTAX  SEQUENCE OF Cnt2EsconEntry
		ACCESS  not-accessible
		STATUS  mandatory
		DESCRIPTION
			"A list of entries describing an individual
			Escon Adaptor.  A specific escon object is
			terminated with the slot number."
		::= { cnt2Escon 1 }

	cnt2esconEntry OBJECT-TYPE
		SYNTAX  Cnt2EsconEntry
		ACCESS  not-accessible
		STATUS  mandatory
		DESCRIPTION
			"An individual escon adapter entry."
		INDEX { cnt2esconSlot }
		::= { cnt2EsconTable 1 }

	Cnt2EsconEntry ::= SEQUENCE {
		cnt2esconSlot
			INTEGER,
		cnt2esconLuaCount
			INTEGER,
		cnt2esconMibVersion
			DisplayString,
		cnt2esconCpuUtil
			INTEGER,
		cnt2esconTotalLocalMem
			INTEGER,
		cnt2esconFreeLocalMem
			INTEGER,
		cnt2esconTotalGlobalMem
			INTEGER,
		cnt2esconFreeGlobalMem
			INTEGER,
		cnt2esconMdmQlist
			DisplayString
	}

	cnt2esconSlot OBJECT-TYPE
		SYNTAX  INTEGER
		ACCESS  read-only
		STATUS  mandatory
		DESCRIPTION
			"The slot index for this escon adapter.
			 format of slot index = ((slot-1) * 10000 + adapter number)"
		::= { cnt2esconEntry 1 }


	cnt2esconLuaCount OBJECT-TYPE
		SYNTAX  INTEGER
		ACCESS  read-only
		STATUS  mandatory
		DESCRIPTION
			"The number of LUAs supported by this escon
			adapter."
		::= { cnt2esconEntry 2 }

         cnt2esconMibVersion OBJECT-TYPE
                SYNTAX  DisplayString
                ACCESS  read-only
                STATUS  mandatory
                DESCRIPTION
                        "The version of the MIB supported by the adapter."
                ::= { cnt2esconEntry 3 }

	cnt2esconCpuUtil OBJECT-TYPE
		SYNTAX  INTEGER
		ACCESS  read-only
		STATUS  mandatory
		DESCRIPTION
			"The utilization of the CPU represented as
			a percentage (1-100%)."
		::= { cnt2esconEntry 4 }

	cnt2esconTotalLocalMem OBJECT-TYPE
		SYNTAX  INTEGER
		ACCESS  read-only
		STATUS  mandatory
		DESCRIPTION
			"The total amount of local memory represented in
			bytes.  Local memory is used for tasks and stacks."
		::= { cnt2esconEntry 5 }

	cnt2esconFreeLocalMem OBJECT-TYPE
		SYNTAX  INTEGER
		ACCESS  read-only
		STATUS  mandatory
		DESCRIPTION
			"The total amount of local memory available
			represented in bytes.  Local memory is used for
			tasks and stacks."
		::= { cnt2esconEntry 6 }

	cnt2esconTotalGlobalMem OBJECT-TYPE
		SYNTAX  INTEGER
		ACCESS  read-only
		STATUS  mandatory
		DESCRIPTION
			"The total amount of global memory represented in
			bytes.  Global memory is used for buffers."
		::= { cnt2esconEntry 7 }

	cnt2esconFreeGlobalMem OBJECT-TYPE
		SYNTAX  INTEGER
		ACCESS  read-only
		STATUS  mandatory
		DESCRIPTION
			"The total amount of global memory available
			represented in bytes.  Global memory is used for
			buffers."
		::= { cnt2esconEntry 8 }

         cnt2esconMdmQlist OBJECT-TYPE
                SYNTAX  DisplayString
                ACCESS  read-only
                STATUS  mandatory
                DESCRIPTION
                        "The list of MDM (interprocess) queue names."
                ::= { cnt2esconEntry 9 }
 

        -- **********************************************************
        -- * The following table has been deprecated and replaced   *
        -- * by cnt2LuaTable2.  cnt2LuaTable2 has the same objects  *
        -- * but has an additional index that identifies the LUA    *
        -- * for a given interface.  When cnt2LuaTable was created  *
        -- * there was a 1-1 mapping between an LUA and an I/F.     *
        -- * cnt2LuaTable2 allows for multiple LUAs over a single   *
        -- * I/F.                                                   *
        -- **********************************************************

	-- the LUA table
	cnt2LuaTable OBJECT-TYPE
		SYNTAX  SEQUENCE OF Cnt2LuaEntry
		ACCESS  not-accessible
		STATUS  deprecated
		DESCRIPTION
			"A list of entries describing an individual
			Logical Unit Adaptor (LUA).  A specific
			lua object is terminated with the channel
			number."
		::= { cnt2Escon 2 }

	cnt2luaEntry OBJECT-TYPE
		SYNTAX  Cnt2LuaEntry
		ACCESS  not-accessible
		STATUS  deprecated
		DESCRIPTION
			"An individual LUA entry."
		INDEX { cnt2luaSlot, cnt2luaIndex }
		::= { cnt2LuaTable 1 }

	Cnt2LuaEntry ::= SEQUENCE {
		cnt2luaSlot
			INTEGER,
		cnt2luaIndex
			INTEGER,
		cnt2luaNumber
			INTEGER,
		cnt2SubChanCount
			INTEGER
	}

	cnt2luaSlot OBJECT-TYPE
		SYNTAX  INTEGER
		ACCESS  read-only
		STATUS  deprecated
		DESCRIPTION
			"The slot index for this LUA.  It corresponds to the
			slot on which this LUA is supported."
		::= { cnt2luaEntry 1 }

	cnt2luaIndex OBJECT-TYPE
		SYNTAX  INTEGER
		ACCESS  read-only
		STATUS  deprecated
		DESCRIPTION
			"The relative index for this LUA.  It corresponds to
			the ifIndex."
		::= { cnt2luaEntry 2 }

	cnt2luaNumber OBJECT-TYPE
		SYNTAX  INTEGER
		ACCESS  read-only
		STATUS  deprecated
		DESCRIPTION
			"The LUA number (0-255)."
		::= { cnt2luaEntry 3 }

	cnt2SubChanCount OBJECT-TYPE
		SYNTAX  INTEGER
		ACCESS  read-only
		STATUS  deprecated
		DESCRIPTION
			"The number of subchannels on the LUA (0-255)."
		::= { cnt2luaEntry 4 }


        -- **********************************************************
        -- * The following table has been deprecated and replaced   *
        -- * by cnt2SubChanTable2.  cnt2SubChanTable2 has the same  *
        -- * objects but has an additional index that identifies    *
        -- * the LUA for a given interface.  When cnt2SubChanTable  *
        -- * was created there was a 1-1 mapping between an LUA     *
        -- * and an I/F.  cnt2SubChanTable2 allows for multiple     *
        -- * LUAs over a single I/F.                                *
        -- **********************************************************
	
	-- the Subchannel table
	cnt2SubChanTable OBJECT-TYPE
		SYNTAX  SEQUENCE OF Cnt2SubchanEntry
		ACCESS  not-accessible
		STATUS  deprecated
		DESCRIPTION
			"A list of entries describing an individual
			subchannel.  A specific subchannel object is
			referenced from the LUA table with instance
			object identifiers .lua.subchannel."
		::= { cnt2Escon 3 }

	cnt2subchanEntry OBJECT-TYPE
		SYNTAX  Cnt2SubchanEntry
		ACCESS  not-accessible
		STATUS  deprecated
		DESCRIPTION
			"An individual subchannel entry."
		INDEX { cnt2sctSlotIndex, cnt2sctLuaIndex, cnt2sctIndex }
		::= { cnt2SubChanTable 1 }

	Cnt2SubchanEntry ::= SEQUENCE {
		cnt2sctSlotIndex
			INTEGER,
		cnt2sctLuaIndex
			INTEGER,
		cnt2sctIndex
			INTEGER,
		cnt2sctNumber
			INTEGER,
		cnt2sctTxStatus
			INTEGER,
		cnt2sctRxStatus
			INTEGER,
		cnt2sctSubChanStatus
			INTEGER,
		cnt2sctState
			INTEGER,
		cnt2sctRxCredit
			INTEGER,
		cnt2sctRxMsgs
			Counter32,
		cnt2sctRxMsgBytes
			Counter32,
		cnt2sctRxDataBytes
			Counter32,
		cnt2sctTxMsgs
			Counter32,
		cnt2sctTxMsgBytes
			Counter32,
		cnt2sctTxDataBytes
			Counter32,
		cnt2sctTxErrMsgs
			Counter32,
		cnt2sctTotalBytes
			Counter32,
		cnt2sctDrecPid
			DisplayString,
		cnt2sctDrecTask
			DisplayString
	}

	cnt2sctSlotIndex OBJECT-TYPE
		SYNTAX  INTEGER
		ACCESS  read-only
		STATUS  deprecated
		DESCRIPTION
			"The slot index for this subchannel.  It corresponds
			to the slot on which this subchannel is supported."
		::= { cnt2subchanEntry 1 }

	cnt2sctLuaIndex OBJECT-TYPE
		SYNTAX  INTEGER
		ACCESS  read-only
		STATUS  deprecated
		DESCRIPTION
			"The relative Lua index for this subchannel.
			This value corresponds with cnt2luaIndex."
		::= { cnt2subchanEntry 2 }

	cnt2sctIndex OBJECT-TYPE
		SYNTAX  INTEGER
		ACCESS  read-only
		STATUS  deprecated
		DESCRIPTION
			"The relative subchannel index for this lua."
		::= { cnt2subchanEntry 3 }

	cnt2sctNumber OBJECT-TYPE
		SYNTAX  INTEGER
		ACCESS  read-only
		STATUS  deprecated
		DESCRIPTION
			"The sub-channel number (0-255)."
		::= { cnt2subchanEntry 4 }

	cnt2sctTxStatus OBJECT-TYPE
		SYNTAX  INTEGER
		ACCESS  read-only
		STATUS  deprecated
		DESCRIPTION
			"Bit value for the transmit status.
				Bit	Definition
				0	Transmit to be cancelled
				4	Transmit in operation
				8	Buffer available to subchannel
				9	Subchannel ready to accept
					POST-XMITs"
		::= { cnt2subchanEntry 5 }

	cnt2sctRxStatus OBJECT-TYPE
		SYNTAX  INTEGER 
		ACCESS  read-only
		STATUS  deprecated
		DESCRIPTION
			"Bit value for the receive status.
				Bit	Definition
				0	Receive operation begun from
					host
				1	Receive enabled/disabled
				2	Cancel current receive message
					sequence
				3	Pending associated data
					sequence
				4	Request transport error
					notification"
		::= { cnt2subchanEntry 6 }

	cnt2sctSubChanStatus OBJECT-TYPE
		SYNTAX  INTEGER
		ACCESS  read-only
		STATUS  deprecated
		DESCRIPTION
			"Bit value for the device subchannel status.
				Bit	Definition
				0	Subchannel is allocated
				1	Subchannel is established
				2	Subchannel is sharable
				3	Subchannel has dedicated
					buffers
				4	Subchannel has pending
					completion
				5	Subchannel has xmit multiple
					from user
				6	Subchannel has receive multiple
					from user
				7	Subchannel has buffer not
					available condition
				8	Subchannel reason for no buffer
					(0=no credit; 1=no buffers)
				9	Subchannel has network level
					doing flow control
				10	Subchannel has pending connect
				11	Subchannel has transmitted
					disconnect
				12	Subchannel ignores buffer not
					available condition
				13	Subchannel support Bus0 if not
					set, Bus1 if set
				14	Subchannel has possible error
					during data transfer
				15	Subchannel is allocated"
		::= { cnt2subchanEntry 7 }

	cnt2sctState OBJECT-TYPE
		SYNTAX  INTEGER
		ACCESS  read-only
		STATUS  deprecated
		DESCRIPTION
			"Bit value for the subchannel state.
				Bit	Definition
				0	Wait flag
				1	Subchannel busy
				2	Pending command retry
				3	Pending completion status
				4	Pending unsolicited status
				6	Status stacked
				7	Damage control active flag"
		::= { cnt2subchanEntry 8 }

	cnt2sctRxCredit OBJECT-TYPE
		SYNTAX  INTEGER
		ACCESS  read-only
		STATUS  deprecated
		DESCRIPTION
			"Current receive buffer credit."
		::= { cnt2subchanEntry 9 }

	cnt2sctRxMsgs OBJECT-TYPE
		SYNTAX  Counter32
		ACCESS  read-only
		STATUS  deprecated
		DESCRIPTION
			"Receive message count."
		::= { cnt2subchanEntry 10 }

	cnt2sctRxMsgBytes OBJECT-TYPE
		SYNTAX  Counter32
		ACCESS  read-only
		STATUS  deprecated
		DESCRIPTION
			"Receive message byte count."
		::= { cnt2subchanEntry 11 }

	cnt2sctRxDataBytes OBJECT-TYPE
		SYNTAX  Counter32
		ACCESS  read-only
		STATUS  deprecated
		DESCRIPTION
			"Receive data byte count."
		::= { cnt2subchanEntry 12 }

	cnt2sctTxMsgs OBJECT-TYPE
		SYNTAX  Counter32
		ACCESS  read-only
		STATUS  deprecated
		DESCRIPTION
			"Transmit message count."
		::= { cnt2subchanEntry 13 }

	cnt2sctTxMsgBytes OBJECT-TYPE
		SYNTAX  Counter32
		ACCESS  read-only
		STATUS  deprecated
		DESCRIPTION
			"Transmit message byte count."
		::= { cnt2subchanEntry 14 }

	cnt2sctTxDataBytes OBJECT-TYPE
		SYNTAX  Counter32
		ACCESS  read-only
		STATUS  deprecated
		DESCRIPTION
			"Transmit data byte count."
		::= { cnt2subchanEntry 15 }

	cnt2sctTxErrMsgs OBJECT-TYPE
		SYNTAX  Counter32
		ACCESS  read-only
		STATUS  deprecated
		DESCRIPTION
			"Transmit error message count."
		::= { cnt2subchanEntry 16 }

	cnt2sctTotalBytes OBJECT-TYPE
		SYNTAX  Counter32
		ACCESS  read-only
		STATUS  deprecated
		DESCRIPTION
			"Total number of bytes transmitted and 
			received for this subchannel."
		::= { cnt2subchanEntry 17 }

	cnt2sctDrecPid OBJECT-TYPE
		SYNTAX  DisplayString
		ACCESS  read-only
		STATUS  deprecated
		DESCRIPTION
			"Channel PID name."
		::= { cnt2subchanEntry 18 }

	cnt2sctDrecTask OBJECT-TYPE
		SYNTAX  DisplayString
		ACCESS  read-only
		STATUS  deprecated
		DESCRIPTION
			"Device specific driver task name."
		::= { cnt2subchanEntry 19 }


        -- **********************************************************
        -- * The following table replaces cnt2LuaTable.             *
        -- * cnt2LuaTable2 has the same objects as cnt2LuaTable     *
        -- * but has an additional index that identifies the LUA    *
        -- * for a given interface.  When cnt2LuaTable was created  *
        -- * there was a 1-1 mapping between an LUA and an I/F.     *
        -- * cnt2LuaTable2 allows for multiple LUAs over a single   *
        -- * I/F.                                                   *
        -- **********************************************************

	-- the LUA table
	cnt2LuaTable2 OBJECT-TYPE
		SYNTAX  SEQUENCE OF Cnt2LuaEntry2
		ACCESS  not-accessible
		STATUS  mandatory
		DESCRIPTION
			"A list of entries describing an individual
			Logical Unit Adaptor (LUA).  A specific
			lua object is terminated with the channel
			number."
		::= { cnt2Escon 4 }

	cnt2luaEntry2 OBJECT-TYPE
		SYNTAX  Cnt2LuaEntry2
		ACCESS  not-accessible
		STATUS  mandatory
		DESCRIPTION
			"An individual LUA entry."
		INDEX { cnt2luaSlot2, cnt2luaIfIndex2, cnt2luaIndex2 }
		::= { cnt2LuaTable2 1 }

	Cnt2LuaEntry2 ::= SEQUENCE {
		cnt2luaSlot2
			INTEGER,
		cnt2luaIfIndex2
			INTEGER,
		cnt2luaIndex2
			INTEGER,
		cnt2luaNumber2
			INTEGER,
		cnt2SubChanCount2
			INTEGER
	}

	cnt2luaSlot2 OBJECT-TYPE
		SYNTAX  INTEGER
		ACCESS  read-only
		STATUS  mandatory
		DESCRIPTION
			"The slot index for this LUA.  It corresponds to the
			slot on which this LUA is supported."
		::= { cnt2luaEntry2 1 }

	cnt2luaIfIndex2 OBJECT-TYPE
		SYNTAX  INTEGER
		ACCESS  read-only
		STATUS  mandatory
		DESCRIPTION
			"The relative index for this LUA.  It corresponds to
			the ifIndex."
		::= { cnt2luaEntry2 2 }

	cnt2luaIndex2 OBJECT-TYPE
		SYNTAX  INTEGER
		ACCESS  read-only
		STATUS  mandatory
		DESCRIPTION
			"The relative index for the LUA on this interface."
		::= { cnt2luaEntry2 3 }

	cnt2luaNumber2 OBJECT-TYPE
		SYNTAX  INTEGER
		ACCESS  read-only
		STATUS  mandatory
		DESCRIPTION
			"The LUA number (0-255)."
		::= { cnt2luaEntry2 4 }

	cnt2SubChanCount2 OBJECT-TYPE
		SYNTAX  INTEGER
		ACCESS  read-only
		STATUS  mandatory
		DESCRIPTION
			"The number of subchannels on the LUA (0-255)."
		::= { cnt2luaEntry2 5 }


        -- **********************************************************
        -- * The following table replaces cnt2SubChanTable.         *
        -- * cnt2SubChanTable2 has the same objects but has an      *
        -- * additional index that identifies the LUA for a given   *
        -- * interface.  When cnt2SubChanTable was created there    *
        -- * was a 1-1 mapping between an LUA and an I/F.           *
        -- * cnt2SubChanTable2 allows for multiple LUAs over a      *
        -- * single I/F.                                            *
        -- **********************************************************
	
	-- the Subchannel table
	cnt2SubChanTable2 OBJECT-TYPE
		SYNTAX  SEQUENCE OF Cnt2SubchanEntry2
		ACCESS  not-accessible
		STATUS  mandatory
		DESCRIPTION
			"A list of entries describing an individual
			subchannel.  A specific subchannel object is
			referenced from the LUA table with instance
			object identifiers .lua.subchannel."
		::= { cnt2Escon 5 }

	cnt2subchanEntry2 OBJECT-TYPE
		SYNTAX  Cnt2SubchanEntry2
		ACCESS  not-accessible
		STATUS  mandatory
		DESCRIPTION
			"An individual subchannel entry."
		INDEX { cnt2sctSlotIndex2,
                        cnt2sctIfIndex2,
                        cnt2sctLuaIndex2,
                        cnt2sctIndex2 }
		::= { cnt2SubChanTable2 1 }

	Cnt2SubchanEntry2 ::= SEQUENCE {
		cnt2sctSlotIndex2
			INTEGER,
		cnt2sctIfIndex2
			INTEGER,
		cnt2sctLuaIndex2
			INTEGER,
		cnt2sctIndex2
			INTEGER,
		cnt2sctNumber2
			INTEGER,
		cnt2sctTxStatus2
			INTEGER,
		cnt2sctRxStatus2
			INTEGER,
		cnt2sctSubChanStatus2
			INTEGER,
		cnt2sctState2
			INTEGER,
		cnt2sctRxCredit2
			INTEGER,
		cnt2sctRxMsgs2
			Counter32,
		cnt2sctRxMsgBytes2
			Counter32,
		cnt2sctRxDataBytes2
			Counter32,
		cnt2sctTxMsgs2
			Counter32,
		cnt2sctTxMsgBytes2
			Counter32,
		cnt2sctTxDataBytes2
			Counter32,
		cnt2sctTxErrMsgs2
			Counter32,
		cnt2sctTotalBytes2
			Counter32,
		cnt2sctDrecPid2
			DisplayString,
		cnt2sctDrecTask2
			DisplayString
	}

	cnt2sctSlotIndex2 OBJECT-TYPE
		SYNTAX  INTEGER
		ACCESS  read-only
		STATUS  mandatory
		DESCRIPTION
			"The slot index for this subchannel.  It corresponds
			to the slot on which this subchannel is supported."
		::= { cnt2subchanEntry2 1 }

	cnt2sctIfIndex2 OBJECT-TYPE
		SYNTAX  INTEGER
		ACCESS  read-only
		STATUS  mandatory
		DESCRIPTION
			"The I/F index for this subchannel.
			This value corresponds with cnt2luaIfIndex."
		::= { cnt2subchanEntry2 2 }

	cnt2sctLuaIndex2 OBJECT-TYPE
		SYNTAX  INTEGER
		ACCESS  read-only
		STATUS  mandatory
		DESCRIPTION
			"The relative Lua index for this subchannel.
			This value corresponds with cnt2luaIndex2."
		::= { cnt2subchanEntry2 3 }

	cnt2sctIndex2 OBJECT-TYPE
		SYNTAX  INTEGER
		ACCESS  read-only
		STATUS  mandatory
		DESCRIPTION
			"The relative subchannel index for this lua."
		::= { cnt2subchanEntry2 4 }

	cnt2sctNumber2 OBJECT-TYPE
		SYNTAX  INTEGER
		ACCESS  read-only
		STATUS  mandatory
		DESCRIPTION
			"The sub-channel number (0-255)."
		::= { cnt2subchanEntry2 5 }

	cnt2sctTxStatus2 OBJECT-TYPE
		SYNTAX  INTEGER
		ACCESS  read-only
		STATUS  mandatory
		DESCRIPTION
			"Bit value for the transmit status.
				Bit	Definition
				0	Transmit to be cancelled
				4	Transmit in operation
				8	Buffer available to subchannel
				9	Subchannel ready to accept
					POST-XMITs"
		::= { cnt2subchanEntry2 6 }

	cnt2sctRxStatus2 OBJECT-TYPE
		SYNTAX  INTEGER 
		ACCESS  read-only
		STATUS  mandatory
		DESCRIPTION
			"Bit value for the receive status.
				Bit	Definition
				0	Receive operation begun from
					host
				1	Receive enabled/disabled
				2	Cancel current receive message
					sequence
				3	Pending associated data
					sequence
				4	Request transport error
					notification"
		::= { cnt2subchanEntry2 7 }

	cnt2sctSubChanStatus2 OBJECT-TYPE
		SYNTAX  INTEGER
		ACCESS  read-only
		STATUS  mandatory
		DESCRIPTION
			"Bit value for the device subchannel status.
				Bit	Definition
				0	Subchannel is allocated
				1	Subchannel is established
				2	Subchannel is sharable
				3	Subchannel has dedicated
					buffers
				4	Subchannel has pending
					completion
				5	Subchannel has xmit multiple
					from user
				6	Subchannel has receive multiple
					from user
				7	Subchannel has buffer not
					available condition
				8	Subchannel reason for no buffer
					(0=no credit; 1=no buffers)
				9	Subchannel has network level
					doing flow control
				10	Subchannel has pending connect
				11	Subchannel has transmitted
					disconnect
				12	Subchannel ignores buffer not
					available condition
				13	Subchannel support Bus0 if not
					set, Bus1 if set
				14	Subchannel has possible error
					during data transfer
				15	Subchannel is allocated"
		::= { cnt2subchanEntry2 8 }

	cnt2sctState2 OBJECT-TYPE
		SYNTAX  INTEGER
		ACCESS  read-only
		STATUS  mandatory
		DESCRIPTION
			"Bit value for the subchannel state.
				Bit	Definition
				0	Wait flag
				1	Subchannel busy
				2	Pending command retry
				3	Pending completion status
				4	Pending unsolicited status
				6	Status stacked
				7	Damage control active flag"
		::= { cnt2subchanEntry2 9 }

	cnt2sctRxCredit2 OBJECT-TYPE
		SYNTAX  INTEGER
		ACCESS  read-only
		STATUS  mandatory
		DESCRIPTION
			"Current receive buffer credit."
		::= { cnt2subchanEntry2 10 }

	cnt2sctRxMsgs2 OBJECT-TYPE
		SYNTAX  Counter32
		ACCESS  read-only
		STATUS  mandatory
		DESCRIPTION
			"Receive message count."
		::= { cnt2subchanEntry2 11 }

	cnt2sctRxMsgBytes2 OBJECT-TYPE
		SYNTAX  Counter32
		ACCESS  read-only
		STATUS  mandatory
		DESCRIPTION
			"Receive message byte count."
		::= { cnt2subchanEntry2 12 }

	cnt2sctRxDataBytes2 OBJECT-TYPE
		SYNTAX  Counter32
		ACCESS  read-only
		STATUS  mandatory
		DESCRIPTION
			"Receive data byte count."
		::= { cnt2subchanEntry2 13 }

	cnt2sctTxMsgs2 OBJECT-TYPE
		SYNTAX  Counter32
		ACCESS  read-only
		STATUS  mandatory
		DESCRIPTION
			"Transmit message count."
		::= { cnt2subchanEntry2 14 }

	cnt2sctTxMsgBytes2 OBJECT-TYPE
		SYNTAX  Counter32
		ACCESS  read-only
		STATUS  mandatory
		DESCRIPTION
			"Transmit message byte count."
		::= { cnt2subchanEntry2 15 }

	cnt2sctTxDataBytes2 OBJECT-TYPE
		SYNTAX  Counter32
		ACCESS  read-only
		STATUS  mandatory
		DESCRIPTION
			"Transmit data byte count."
		::= { cnt2subchanEntry2 16 }

	cnt2sctTxErrMsgs2 OBJECT-TYPE
		SYNTAX  Counter32
		ACCESS  read-only
		STATUS  mandatory
		DESCRIPTION
			"Transmit error message count."
		::= { cnt2subchanEntry2 17 }

	cnt2sctTotalBytes2 OBJECT-TYPE
		SYNTAX  Counter32
		ACCESS  read-only
		STATUS  mandatory
		DESCRIPTION
			"Total number of bytes transmitted and 
			received for this subchannel."
		::= { cnt2subchanEntry2 18 }

	cnt2sctDrecPid2 OBJECT-TYPE
		SYNTAX  DisplayString
		ACCESS  read-only
		STATUS  mandatory
		DESCRIPTION
			"Channel PID name."
		::= { cnt2subchanEntry2 19 }

	cnt2sctDrecTask2 OBJECT-TYPE
		SYNTAX  DisplayString
		ACCESS  read-only
		STATUS  mandatory
		DESCRIPTION
			"Device specific driver task name."
		::= { cnt2subchanEntry2 20 }

	END
