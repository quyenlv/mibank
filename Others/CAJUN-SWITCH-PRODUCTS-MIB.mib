-- LUCENT CAJUN SWITCH PRODUCTS MIB VERSION V1.0
-- Lucent enterprise-specific Management Information Base for SNMP version 1
-- 
-- Revision History
-- ----------------
-- v1.0   03/31/98   Ira Steckler   Lucent Switch Products MIB
-- 
-- © Copyright LUCENT TECHNOLOGIES 1998 ALL RIGHTS RESERVED
-- Printed in USA, November 1998
-- 
-- The products, specifications, and other technical information regarding the
-- products contained in this document are subject to change without notice. All
-- information in this document is believed to be accurate and reliable, but is
-- presented without warranty of any kind, express or implied, and users must
-- take full responsibility for their application of any products specified in
-- this document. Lucent disclaims responsibility for errors which may appear in
-- this document, and it reserves the right, in its sole discretion and without
-- notice, to make substitutions and modifications in the products and practices
-- described in this document.  Lucent, NetCare, Cajun, CajunDocs, OpenTrunk,
-- P550, and CajunView are trademarks of Lucent Technologies.
-- 
-- This MIB provides managed objects that supplement those capabilities
-- supported by the standard IETF MIBs.  It has the following main sections:
-- 
--    General Agent Support: Manages the SNMP agent.
--           Communications:
--      Resource Management: The Resource Manager is the focal point for
--                           managing dynamic resources.
--                  Chassis: Objects related to the management of the physical
--                           enclosure and environment.
--                Switching: Management of the layer II switching functions and
--                           Virtual LANs.
--         Event Management: RMON Events on steroids.
--              File System: Provides access to the embedded file system.
-- 
-- For technical assistance, please contact Lucent Techologies Netcare Data
-- Networking Systems by phoning (800) 237-0016, pressing 0, then 73300.  You
-- can also contact them on the World Wide Web at https://www.netcaredata.com.



-- MODULE DEFINITION

   CAJUN-SWITCH-PRODUCTS-MIB DEFINITIONS ::= BEGIN

IMPORTS 
	enterprises, MODULE-IDENTITY
                 FROM SNMPv2-SMI;
    	lucent  MODULE-IDENTITY
	      LAST-UPDATED "9901300000Z"
              ORGANIZATION "Lucent's Concord Technology Center (CTC) "
              CONTACT-INFO
                      "Erick M. Crowell -- ecrowell@lucent.com,
			Raj Duggal -- rduggal@lucent.com,
		        Ira Steckler -- isteckler@lucent.com"
              DESCRIPTION
                      "Cajun p220 / p550 / p660 / p880  Private Mib
			top level Architecture."
              ::= {enterprises 1751  }

-- lucent 		OBJECT IDENTIFIER ::= {enterprises 1751}
products 	OBJECT IDENTIFIER ::= {lucent 1}
mibs 		OBJECT IDENTIFIER ::= {lucent 2}

-- Cajun Router is number 43 under the Lucent Enterprise MIB

cajunSwitch 		OBJECT IDENTIFIER ::= {mibs 45}
cajunSwitchProduct	OBJECT IDENTIFIER ::= {products 45}


-- Cajun Switch Product Types
--
cajunL2P550 	OBJECT IDENTIFIER ::= 	{ cajunSwitchProduct 1 }
cajunL3P550 	OBJECT IDENTIFIER ::= 	{ cajunSwitchProduct 2 }
cajunP220G 	OBJECT IDENTIFIER ::= 	{ cajunSwitchProduct 3 }
cajunP220FE 	OBJECT IDENTIFIER ::= 	{ cajunSwitchProduct 4 }




END
