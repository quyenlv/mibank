-- $Header:   K:/WanSuite/archives/include/pvcs/ipstart.mib,v   1.0   20 Jun 2000 10:24:30   richardm  $

IPAD-IPSTART-MIB DEFINITIONS ::= BEGIN

IMPORTS enterprises, 
	IpAddress                                      FROM RFC1155-SMI
        OBJECT-TYPE                                    FROM RFC-1212
        DisplayString                                  FROM RFC1213-MIB
        TRAP-TYPE                                      FROM RFC-1215;

verilink    OBJECT IDENTIFIER ::= { enterprises 321 }
hbu         OBJECT IDENTIFIER ::= { verilink 100 }
ipad        OBJECT IDENTIFIER ::= { hbu 1 }

-- IPAD sections

ipadFrPort      OBJECT IDENTIFIER ::= { ipad 1 }
ipadService     OBJECT IDENTIFIER ::= { ipad 2 }
ipadChannel     OBJECT IDENTIFIER ::= { ipad 3 }
ipadDLCI        OBJECT IDENTIFIER ::= { ipad 4 }
ipadEndpoint    OBJECT IDENTIFIER ::= { ipad 5 }
ipadUser        OBJECT IDENTIFIER ::= { ipad 6 }
ipadPPP         OBJECT IDENTIFIER ::= { ipad 7 }
ipadModem       OBJECT IDENTIFIER ::= { ipad 8 }
ipadSvcAware    OBJECT IDENTIFIER ::= { ipad 9 }
ipadPktSwitch   OBJECT IDENTIFIER ::= { ipad 10 }
ipadTrapDest    OBJECT IDENTIFIER ::= { ipad 11 }
ipadMisc        OBJECT IDENTIFIER ::= { ipad 12 }
ipadRouter      OBJECT IDENTIFIER ::= { ipad 13 }
ipadSoftKey     OBJECT IDENTIFIER ::= { ipad 14 }

-- This MIB, which resides under ipadPPP

ipadPPPStartTable    OBJECT-TYPE
    SYNTAX    SEQUENCE OF IpadPPPStartTableEntry
    ACCESS    not-accessible
    STATUS    optional
    DESCRIPTION
        "The ipad PPP Start table."
    ::= { ipadPPP 4 }

ipadPPPStartTableEntry    OBJECT-TYPE
    SYNTAX    IpadPPPStartTableEntry
    ACCESS    not-accessible
    STATUS    mandatory
    DESCRIPTION
        "An entry in the ipad PPP Start table."
    INDEX { ipadPPPStartService }
    ::= { ipadPPPStartTable 1 }

IpadPPPStartTableEntry ::=
    SEQUENCE
    {    
    ipadPPPStartService                     INTEGER,
    ipadPPPStartLCPState                    INTEGER,
    ipadPPPStartLCPStateTime                INTEGER,
    ipadPPPStartLCPStateChanges             INTEGER,
    ipadPPPStartLCPMRU                      INTEGER,
    ipadPPPStartLCPAsyncCCM                 DisplayString,
    ipadPPPStartLCPAuthProtocol             INTEGER,
    ipadPPPStartLCPQualityProtocol          INTEGER,
    ipadPPPStartLCPMagicNumber              DisplayString,
    ipadPPPStartLCPPFC                      INTEGER,
    ipadPPPStartLCPACFC                     INTEGER,
    ipadPPPStartLCPFCSAlternatives          INTEGER,
    ipadPPPStartLCPSDP                      INTEGER,
    ipadPPPStartLCPCompoundFrames           INTEGER,
    ipadPPPStartAuthState                   INTEGER,
    ipadPPPStartAuthStateTime               INTEGER,
    ipadPPPStartAuthStateChanges            INTEGER,
    ipadPPPStartAuthFailureCount            INTEGER,
    ipadPPPStartAuthFailureTrapEnable       INTEGER,
    ipadPPPStartIPCPState                   INTEGER,
    ipadPPPStartIPCPStateTime               INTEGER,
    ipadPPPStartIPCPStateChanges            INTEGER,
    ipadPPPStartIPCPIPSource                IpAddress,
    ipadPPPStartIPCPIPDestAddress           IpAddress,
    ipadPPPStartIPCPCompressionProtocol     INTEGER
    }

ipadPPPStartService  OBJECT-TYPE
    SYNTAX    INTEGER
    ACCESS    read-only
    STATUS    mandatory
    DESCRIPTION
        ""
    ::= { ipadPPPStartTableEntry 1 }

ipadPPPStartLCPState  OBJECT-TYPE
    SYNTAX    INTEGER
              {
              initial(1),
              starting(2),
              closed(3),
              stopped(4),
              closing(5),
              stopping(6),
              reqSent(7),
              ackRcvd(8),
              ackSent(9),
              opened(10)
              }
    ACCESS    read-only
    STATUS    mandatory
    DESCRIPTION
        ""
    ::= { ipadPPPStartTableEntry 2 }

ipadPPPStartLCPStateTime  OBJECT-TYPE
    SYNTAX    INTEGER
    ACCESS    read-only
    STATUS    mandatory
    DESCRIPTION
        ""
    ::= { ipadPPPStartTableEntry 3 }

ipadPPPStartLCPStateChanges  OBJECT-TYPE
    SYNTAX    INTEGER
    ACCESS    read-only
    STATUS    mandatory
    DESCRIPTION
        ""
    ::= { ipadPPPStartTableEntry 4 }

ipadPPPStartLCPMRU  OBJECT-TYPE
    SYNTAX    INTEGER
    ACCESS    read-only
    STATUS    mandatory
    DESCRIPTION
        ""
    ::= { ipadPPPStartTableEntry 5 }

ipadPPPStartLCPAsyncCCM  OBJECT-TYPE
    SYNTAX    DisplayString(SIZE(4))
    ACCESS    read-only
    STATUS    mandatory
    DESCRIPTION
        ""
    ::= { ipadPPPStartTableEntry 6 }

ipadPPPStartLCPAuthProtocol  OBJECT-TYPE
    SYNTAX    INTEGER
              {
              unknown(1),
              other(2),
              pap(3),
              chap(4),
              spap(5),
              eap(6)
              }
    ACCESS    read-only
    STATUS    mandatory
    DESCRIPTION
        ""
    ::= { ipadPPPStartTableEntry 7 }

ipadPPPStartLCPQualityProtocol  OBJECT-TYPE
    SYNTAX    INTEGER
              {
              unknown(1),
              other(2),
              lqr(3)
              }            
    ACCESS    read-only
    STATUS    mandatory
    DESCRIPTION
        ""
    ::= { ipadPPPStartTableEntry 8 }

ipadPPPStartLCPMagicNumber  OBJECT-TYPE
    SYNTAX    DisplayString(SIZE(4))
    ACCESS    read-only
    STATUS    mandatory
    DESCRIPTION
        ""
    ::= { ipadPPPStartTableEntry 9 }

ipadPPPStartLCPPFC  OBJECT-TYPE
    SYNTAX    INTEGER
              {
              enabled(1),
              disabled(2)
              }
    ACCESS    read-only
    STATUS    mandatory
    DESCRIPTION
        ""
    ::= { ipadPPPStartTableEntry 10 }

ipadPPPStartLCPACFC  OBJECT-TYPE
    SYNTAX    INTEGER
              {
              enabled(1),
              disabled(2)
              }
    ACCESS    read-only
    STATUS    mandatory
    DESCRIPTION
        ""
    ::= { ipadPPPStartTableEntry 11 }

ipadPPPStartLCPFCSAlternatives  OBJECT-TYPE
    SYNTAX    INTEGER
              {
              unknown(1),
              other(2),
              nullFCS(3),
              ccitt16bitFCS(4),
              ccitt32bitFCS(5)
              }
    ACCESS    read-only
    STATUS    mandatory
    DESCRIPTION
        ""
    ::= { ipadPPPStartTableEntry 12 }

ipadPPPStartLCPSDP  OBJECT-TYPE
    SYNTAX    INTEGER
    ACCESS    read-only
    STATUS    mandatory
    DESCRIPTION
        ""
    ::= { ipadPPPStartTableEntry 13 }

ipadPPPStartLCPCompoundFrames  OBJECT-TYPE
    SYNTAX    INTEGER
              {
              enabled(1),
              disabled(2)
              }
    ACCESS    read-only
    STATUS    mandatory
    DESCRIPTION
        ""
    ::= { ipadPPPStartTableEntry 14 }

ipadPPPStartAuthState  OBJECT-TYPE
    SYNTAX    INTEGER
              {
              initial(1),
              starting(2),
              closed(3),
              stopped(4),
              closing(5),
              stopping(6),
              reqSent(7),
              ackRcvd(8),
              ackSent(9),
              opened(10)
              }
    ACCESS    read-only
    STATUS    mandatory
    DESCRIPTION
        ""
    ::= { ipadPPPStartTableEntry 15 }

ipadPPPStartAuthStateTime  OBJECT-TYPE
    SYNTAX    INTEGER
    ACCESS    read-only
    STATUS    mandatory
    DESCRIPTION
        ""
    ::= { ipadPPPStartTableEntry 16 }

ipadPPPStartAuthStateChanges  OBJECT-TYPE
    SYNTAX    INTEGER
    ACCESS    read-only
    STATUS    mandatory
    DESCRIPTION
        ""
    ::= { ipadPPPStartTableEntry 17 }

ipadPPPStartAuthFailureCount  OBJECT-TYPE
    SYNTAX    INTEGER
    ACCESS    read-only
    STATUS    mandatory
    DESCRIPTION
        ""
    ::= { ipadPPPStartTableEntry 18 }

ipadPPPStartAuthFailureTrapEnable  OBJECT-TYPE
    SYNTAX    INTEGER
              {
              enabled(1),
              disabled(2)
              }
    ACCESS    read-write
    STATUS    mandatory
    DESCRIPTION
        ""
    ::= { ipadPPPStartTableEntry 19 }

ipadPPPStartIPCPState  OBJECT-TYPE
    SYNTAX    INTEGER
              {
              initial(1),
              starting(2),
              closed(3),
              stopped(4),
              closing(5),
              stopping(6),
              reqSent(7),
              ackRcvd(8),
              ackSent(9),
              opened(10)
              }
    ACCESS    read-only
    STATUS    mandatory
    DESCRIPTION
        ""
    ::= { ipadPPPStartTableEntry 20 }

ipadPPPStartIPCPStateTime  OBJECT-TYPE
    SYNTAX    INTEGER
    ACCESS    read-only
    STATUS    mandatory
    DESCRIPTION
        ""
    ::= { ipadPPPStartTableEntry 21 }

ipadPPPStartIPCPStateChanges  OBJECT-TYPE
    SYNTAX    INTEGER
    ACCESS    read-only
    STATUS    mandatory
    DESCRIPTION
        ""
    ::= { ipadPPPStartTableEntry 22 }

ipadPPPStartIPCPIPSource  OBJECT-TYPE
    SYNTAX    IpAddress
    ACCESS    read-only
    STATUS    mandatory
    DESCRIPTION
        ""
    ::= { ipadPPPStartTableEntry 23 }

ipadPPPStartIPCPIPDestAddress  OBJECT-TYPE
    SYNTAX    IpAddress
    ACCESS    read-only
    STATUS    mandatory
    DESCRIPTION
        ""
    ::= { ipadPPPStartTableEntry 24 }

ipadPPPStartIPCPCompressionProtocol  OBJECT-TYPE
    SYNTAX    INTEGER
              {
              unknown(1),
              other(2),    
              regularIPdata(3),
              compressedTCP(4),
              uncompressedTCP(5)
              }
    ACCESS    read-only
    STATUS    mandatory
    DESCRIPTION
        ""
    ::= { ipadPPPStartTableEntry 25 }

ipadPPPStartLCPHistoryTable    OBJECT-TYPE
    SYNTAX    SEQUENCE OF IpadPPPStartLCPHistoryTableEntry
    ACCESS    not-accessible
    STATUS    optional
    DESCRIPTION
        "The ipad PPPStart LCP history table."
    ::= { ipadPPP 5 }

ipadPPPStartLCPHistoryTableEntry    OBJECT-TYPE
    SYNTAX    IpadPPPStartLCPHistoryTableEntry
    ACCESS    not-accessible
    STATUS    mandatory
    DESCRIPTION
        "An entry in the ipad PPPStart LCP history table."
    INDEX { ipadPPPStartLCPHistoryIndex }
    ::= { ipadPPPStartLCPHistoryTable 1 }

IpadPPPStartLCPHistoryTableEntry ::=
    SEQUENCE 
    {
    ipadPPPStartLCPHistoryIndex       INTEGER,
    ipadPPPStartLCPHistoryState       INTEGER,
    ipadPPPStartLCPHistoryStateTime   INTEGER
    }

ipadPPPStartLCPHistoryIndex  OBJECT-TYPE
    SYNTAX    INTEGER
    ACCESS    read-only
    STATUS    mandatory
    DESCRIPTION
        ""
    ::= { ipadPPPStartLCPHistoryTableEntry 1 }

ipadPPPStartLCPHistoryState  OBJECT-TYPE
    SYNTAX    INTEGER
              {
              initial(1),
              starting(2),
              closed(3),
              stopped(4),
              closing(5),
              stopping(6),
              reqSent(7),
              ackRcvd(8),
              ackSent(9),
              opened(10)
              }
    ACCESS    read-only
    STATUS    mandatory
    DESCRIPTION
        ""
    ::= { ipadPPPStartLCPHistoryTableEntry 2 }

ipadPPPStartLCPHistoryStateTime  OBJECT-TYPE
    SYNTAX    INTEGER
    ACCESS    read-only
    STATUS    mandatory
    DESCRIPTION
        ""
    ::= { ipadPPPStartLCPHistoryTableEntry 3 }

ipadPPPStartAuthHistoryTable    OBJECT-TYPE
    SYNTAX    SEQUENCE OF IpadPPPStartAuthHistoryTableEntry
    ACCESS    not-accessible
    STATUS    optional
    DESCRIPTION
        "The ipad PPPStart authentication history table."
    ::= { ipadPPP 6 }

ipadPPPStartAuthHistoryTableEntry    OBJECT-TYPE
    SYNTAX    IpadPPPStartAuthHistoryTableEntry
    ACCESS    not-accessible
    STATUS    mandatory
    DESCRIPTION
        "An entry in the ipad PPPStart authentication 
        history table."
    INDEX { ipadPPPStartAuthHistoryIndex }
    ::= { ipadPPPStartAuthHistoryTable 1 }

IpadPPPStartAuthHistoryTableEntry ::=
    SEQUENCE 
    {
    ipadPPPStartAuthHistoryIndex       INTEGER,
    ipadPPPStartAuthHistoryState       INTEGER,
    ipadPPPStartAuthHistoryStateTime   INTEGER
    }

ipadPPPStartAuthHistoryIndex  OBJECT-TYPE
    SYNTAX    INTEGER
    ACCESS    read-only
    STATUS    mandatory
    DESCRIPTION
        ""
    ::= { ipadPPPStartAuthHistoryTableEntry 1 }

ipadPPPStartAuthHistoryState  OBJECT-TYPE
    SYNTAX    INTEGER
              {
              initial(1),
              starting(2),
              closed(3),
              stopped(4),
              closing(5),
              stopping(6),
              reqSent(7),
              ackRcvd(8),
              ackSent(9),
              opened(10)
              }
    ACCESS    read-only
    STATUS    mandatory
    DESCRIPTION
        ""
    ::= { ipadPPPStartAuthHistoryTableEntry 2 }

ipadPPPStartAuthHistoryStateTime  OBJECT-TYPE
    SYNTAX    INTEGER
    ACCESS    read-only
    STATUS    mandatory
    DESCRIPTION
        ""
    ::= { ipadPPPStartAuthHistoryTableEntry 3 }

ipadPPPStartIPCPHistoryTable    OBJECT-TYPE
    SYNTAX    SEQUENCE OF IpadPPPStartIPCPHistoryTableEntry
    ACCESS    not-accessible
    STATUS    optional
    DESCRIPTION
        "The ipad PPPStart IPCP history table."
    ::= { ipadPPP 7 }

ipadPPPStartIPCPHistoryTableEntry    OBJECT-TYPE
    SYNTAX    IpadPPPStartIPCPHistoryTableEntry
    ACCESS    not-accessible
    STATUS    mandatory
    DESCRIPTION
        "An entry in the ipad PPPStart IPCP history table."
    INDEX { ipadPPPStartIPCPHistoryIndex }
    ::= { ipadPPPStartIPCPHistoryTable 1 }

IpadPPPStartIPCPHistoryTableEntry ::=
    SEQUENCE 
    {
    ipadPPPStartIPCPHistoryIndex       INTEGER,
    ipadPPPStartIPCPHistoryState       INTEGER,
    ipadPPPStartIPCPHistoryStateTime   INTEGER
    }

ipadPPPStartIPCPHistoryIndex  OBJECT-TYPE
    SYNTAX    INTEGER
    ACCESS    read-only
    STATUS    mandatory
    DESCRIPTION
        ""
    ::= { ipadPPPStartIPCPHistoryTableEntry 1 }

ipadPPPStartIPCPHistoryState  OBJECT-TYPE
    SYNTAX    INTEGER
              {
              initial(1),
              starting(2),
              closed(3),
              stopped(4),
              closing(5),
              stopping(6),
              reqSent(7),
              ackRcvd(8),
              ackSent(9),
              opened(10)
              }
    ACCESS    read-only
    STATUS    mandatory
    DESCRIPTION
        ""
    ::= { ipadPPPStartIPCPHistoryTableEntry 2 }

ipadPPPStartIPCPHistoryStateTime  OBJECT-TYPE
    SYNTAX    INTEGER
    ACCESS    read-only
    STATUS    mandatory
    DESCRIPTION
        ""
    ::= { ipadPPPStartIPCPHistoryTableEntry 3 }

ipadPPPStartAuthFailureTrap    TRAP-TYPE
    ENTERPRISE    hbu
    DESCRIPTION
        ""
    ::= 25050

END
