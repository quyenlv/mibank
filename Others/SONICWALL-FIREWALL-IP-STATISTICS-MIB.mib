-- *****************************************************************
-- SONICWALL-FIREWALL-IP-STATISTICS
--
-- June 2002, Initial Version, Srikanth  Nayani
-- Apr  2003,   Change Postal, Susan Yan
--
-- Copyright (c) 2001 - 2003 by SonicWall, Inc.
-- All rights reserved.
-- *****************************************************************

SONICWALL-FIREWALL-IP-STATISTICS-MIB DEFINITIONS ::= BEGIN


IMPORTS
    DisplayString,
    TEXTUAL-CONVENTION		 	FROM SNMPv2-TC

    IpAddress,
	snmpModules,
    OBJECT-TYPE,
    NOTIFICATION-TYPE,
	MODULE-IDENTITY             FROM SNMPv2-SMI
	Counter						FROM RFC1155-SMI

    sonicwallFw           		FROM SONICWALL-SMI;

sonicwallFwStatsModule MODULE-IDENTITY
	LAST-UPDATED "200304220000Z"
	ORGANIZATION "SonicWall, Inc."
	CONTACT-INFO
		"	SonicWall Inc.

		Postal: 1143 Borregas Avenue
			Sunnyvale, CA 94089
			USA

		   Tel: +1 408 745 9600
		   Fax: +1 408 745 9300

		E-mail: product@sonicwall.com"
	DESCRIPTION
		"The MIB Module for SonicWALL Firewall Ipsec Statistics."
	REVISION      "200304220000Z"
	DESCRIPTION
		"Initial Version"
    ::= { sonicwallFw 3 }

-- =======================
-- sonic Firewall Statistics
-- =======================


sonicwallFwStats OBJECT IDENTIFIER ::= {sonicwallFwStatsModule 1}

sonicMaxConnCacheEntries OBJECT-TYPE
	SYNTAX Counter
	MAX-ACCESS read-only
	STATUS current
	DESCRIPTION
		" Maximum number of connection cache entries allowed through the firewall"
	::= { sonicwallFwStats 1 }

sonicCurrentConnCacheEntries OBJECT-TYPE
	SYNTAX Counter
	MAX-ACCESS read-only
	STATUS current
	DESCRIPTION
		" Number of active connection cache entries through the firewall"
	::= { sonicwallFwStats 2 }


sonicwallFwVPNStats OBJECT IDENTIFIER ::= {sonicwallFwStatsModule 2}

sonicwallFwVpnIPSecStats OBJECT IDENTIFIER ::= {sonicwallFwVPNStats 1}


-- =======================
-- sonic IPsec Statistics Table
-- =======================

sonicSAStatTable OBJECT-TYPE
	SYNTAX SEQUENCE OF SonicSAStatEntry 
	MAX-ACCESS not-accessible
	STATUS current
	DESCRIPTION
		"This table provides statistics for each Security Association."
	::= { sonicwallFwVpnIPSecStats 1 }

sonicSAStatEntry OBJECT-TYPE
	SYNTAX SonicSAStatEntry
	MAX-ACCESS not-accessible
	STATUS current
	DESCRIPTION
		"Entries in table cannot be added or deleted. This table is
		completely controlled by the agent. Each SA statistics will be
		represented by an entry in this table. "
	INDEX { sonicIpsecSaIndex}
	::= { sonicSAStatTable 1 }

SonicSAStatEntry ::= SEQUENCE {
	sonicIpsecSaIndex			   Counter,
	sonicSAStatPeerGateway         IpAddress,
	sonicSAStatSrcAddrBegin        IpAddress,
	sonicSAStatSrcAddrEnd	       IpAddress,
	sonicSAStatDstAddrBegin        IpAddress,
	sonicSAStatDstAddrEnd	       IpAddress,
	sonicSAStatCreateTime          DisplayString,
	sonicSAStatEncryptPktCount     Counter,
	sonicSAStatEncryptByteCount    Counter,
	sonicSAStatDecryptPktCount     Counter,
	sonicSAStatDecryptByteCount    Counter,
	sonicSAStatInFragPktCount      Counter,
	sonicSAStatOutFragPktCount     Counter,
    sonicSAStatUserName            DisplayString
	}


sonicIpsecSaIndex OBJECT-TYPE
	SYNTAX Counter
	MAX-ACCESS read-only
	STATUS current
	DESCRIPTION
		" Phase2  SA index."
	::= { sonicSAStatEntry 1 }

sonicSAStatPeerGateway OBJECT-TYPE
	SYNTAX IpAddress
	MAX-ACCESS read-only
	STATUS current
	DESCRIPTION
		"Peer gateway address where the tunnel gets terminated ."
	::= { sonicSAStatEntry 2 }

sonicSAStatSrcAddrBegin OBJECT-TYPE
	SYNTAX IpAddress
	MAX-ACCESS read-only
	STATUS current
	DESCRIPTION
		"First address of the Source network for the phase2 SA ."
	::= { sonicSAStatEntry 3 }

sonicSAStatSrcAddrEnd OBJECT-TYPE
	SYNTAX IpAddress
	MAX-ACCESS read-only
	STATUS current
	DESCRIPTION
		"Last address of the Source network for the phase2 SA ."
	::= { sonicSAStatEntry 4 }

sonicSAStatDstAddrBegin OBJECT-TYPE
	SYNTAX IpAddress
	MAX-ACCESS read-only
	STATUS current
	DESCRIPTION
		"First address of the destination network for the phase2 SA ."
	::= { sonicSAStatEntry 5 }

sonicSAStatDstAddrEnd OBJECT-TYPE
	SYNTAX IpAddress
	MAX-ACCESS read-only
	STATUS current
	DESCRIPTION
		"Last address of the destination network for the phase2 SA ."
	::= { sonicSAStatEntry 6 }

sonicSAStatCreateTime OBJECT-TYPE
	SYNTAX DisplayString
    MAX-ACCESS read-only
	STATUS current
	DESCRIPTION
	"Time this phase2 SA was actually created in GMT."
	::= { sonicSAStatEntry 7 }

sonicSAStatEncryptPktCount OBJECT-TYPE
	SYNTAX Counter
	MAX-ACCESS read-only
	STATUS current
	DESCRIPTION
		"Total encrypted packet count for this phase2 SA."
	::= { sonicSAStatEntry 8 }

sonicSAStatEncryptByteCount OBJECT-TYPE
	SYNTAX Counter
	MAX-ACCESS read-only
	STATUS current
	DESCRIPTION
		"Total encrypted byte count for this phase2 SA."
	::= { sonicSAStatEntry 9 }

sonicSAStatDecryptPktCount OBJECT-TYPE
	SYNTAX Counter
	MAX-ACCESS read-only
	STATUS current
	DESCRIPTION
		"Total decrypted packet count for this phase2 SA."
	::= { sonicSAStatEntry  10}

sonicSAStatDecryptByteCount OBJECT-TYPE
	SYNTAX Counter
	MAX-ACCESS read-only
	STATUS current
	DESCRIPTION
		"Total decrypted byte count for this phase2 SA."
	::= { sonicSAStatEntry  11 }

sonicSAStatInFragPktCount OBJECT-TYPE
	SYNTAX Counter
	MAX-ACCESS read-only
	STATUS current
	DESCRIPTION
		"Incoming Fragmented packet count for this phase2 SA"
	::= { sonicSAStatEntry 12 }

sonicSAStatOutFragPktCount OBJECT-TYPE
	SYNTAX Counter
	MAX-ACCESS read-only
	STATUS current
	DESCRIPTION
		"Outgoing Fragmented packet count for this phase2 SA"
	::= { sonicSAStatEntry 13 }


sonicSAStatUserName  OBJECT-TYPE
    SYNTAX DisplayString
    MAX-ACCESS read-only
    STATUS current
    DESCRIPTION
        "Name of the security policy used for creating this phase2 SA."
	::= { sonicSAStatEntry 14 }

	
END
