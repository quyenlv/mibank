EASTER-EGG-MIB DEFINITIONS ::= BEGIN
   IMPORTS
       OBJECT-TYPE              FROM RFC-1212
       roboExec, UsrDisplayString  FROM USR-DEFINITIONS-MIB;
   usrreEasterEgg     OBJECT IDENTIFIER ::= { roboExec 4 }
   -- The RoboExec Easter Egg Group
   --
   -- Implementation of this group is purely at the whim of the implementors
   --
   -- The reEasterEggTable contains an entry for each member of the
   -- team working on the Pilgrim project; disabled
   usrreEasterEggTable OBJECT-TYPE
       SYNTAX SEQUENCE OF UsrreEasterEggEntry
       ACCESS not-accessible
       STATUS mandatory
       DESCRIPTION
              "The table of Pilgrim developers."
       ::= { usrreEasterEgg 1 }
   usrreEasterEggEntry OBJECT-TYPE
       SYNTAX UsrreEasterEggEntry
       ACCESS not-accessible
       STATUS mandatory
       DESCRIPTION
              "An entry for one Pilgrim developer."
       INDEX { usrreEEIndex }
       ::= { usrreEasterEggTable 1 }
   UsrreEasterEggEntry ::= SEQUENCE {
           usrreEEIndex         INTEGER,
           usrreEEName          UsrDisplayString,
           usrreEENickName      UsrDisplayString,
           usrreEEQuote         UsrDisplayString
       }
   usrreEEIndex OBJECT-TYPE
       SYNTAX INTEGER
       ACCESS read-only
       STATUS mandatory
       DESCRIPTION
              "A unique value for each Pilgrim developer."
       ::= { usrreEasterEggEntry 1 }
   usrreEEName OBJECT-TYPE
       SYNTAX UsrDisplayString (SIZE (0..64))
       ACCESS read-only
       STATUS mandatory
       DESCRIPTION
              "A textual name of the developer."
       ::= { usrreEasterEggEntry 2 }
   usrreEENickName OBJECT-TYPE
       SYNTAX UsrDisplayString (SIZE (0..64))
       ACCESS read-only
       STATUS mandatory
       DESCRIPTION
              "Another name for the same person..."
	  --GORDY
       ::= { usrreEasterEggEntry 3 }
   usrreEEQuote OBJECT-TYPE
       SYNTAX UsrDisplayString
       ACCESS read-only
       STATUS mandatory
       DESCRIPTION
              "A quote of note..."
	  --GORDY
       ::= { usrreEasterEggEntry 4 }
   usrJimbo OBJECT-TYPE
       SYNTAX UsrDisplayString
       ACCESS read-only
       STATUS mandatory
       DESCRIPTION
              "An entry in the MIB tree to honor the designer of
		     the Pilgrim Network Management Architecture."
       --GORDY
       ::= { usrreEasterEgg 2 }
   END    -- End of    EASTER-EGG-MIB DEFINITIONS
