-- ****************************************************************************
--
-- Dialogic Digital Network Interface Control
-- Management Information Base for SNMP Network Management
--			Revision 2.0
--			Major version 2 , minor version 0
-- Copyright 1997, Dialogic Corporation.
--			All Rights Reserved.
--
-- The information in this document is subject to change without notice.
--
-- The Dialogic Enterprise number is 3028.
-- The ASN.1 prefix to, and including the Dialogic Enterprise is:
--1.3.6.1.4.1.3028
--
-- This MIB is based on the standard Digital Signal-1 MIB (RFC1406). This 
--MIB is a part of the Dialogic private MIB tree under the 
--dlgNetworkInterfaces node. Where possible the same MIB variable
--Names are used but prepended with the "dlg" prefix to indicate
--They are part of the Dialogic's private DS1 MIB. 
--
--******************************************************************************

DLGDS1-MIB DEFINITIONS ::= BEGIN

    IMPORTS
        Counter                 FROM RFC1155-SMI
        Gauge                   FROM RFC1155-SMI
		OBJECT-TYPE             FROM RFC1155-SMI
        TRAP-TYPE               FROM RFC-1215
        dlgTransmissions        FROM DLGC-GLOBAL-REG;

-- This is the MIB module for the Digital Interface objects

     dlgDs1 OBJECT IDENTIFIER ::= { dlgTransmissions 1 }

--******************************************************************************
--
-- Textual Conventions
--
--******************************************************************************
--
-- Dsx1AlarmType identifies one of the generic types of alarms
-- that a Dialogic Digital network interface can raise.
--

Dsx1AlarmType ::= INTEGER {
  detectedNoAlarm ( 100 ),
  detectedRed  ( 101),
  detectedBlue  ( 102),
  detectedYellow  (103),
  detectedE1Alarm ( 104 )
  }

--
-- Boolean
--
Boolean ::= INTEGER {
  true (1),
  false (0)
  }

--
-- DisplayString 
--
DisplayString ::= OCTET STRING ( SIZE (0..255 ) )  

--****************************************************************************
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--
-- The Digital Signal1 group consists of six tables and a Mib Revision table.
--    These tables are:
--
--       DS1 Configuration table
--       DS1 Current table
--       DS1 Interval table
--       DS1 Total table
--       DS1 Alarm table
--       DS1 Springware Event Mask table
--
--**************************************************************************** 
--
-- The DS1 Configuration Table
--==============================
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--		dlgDsx1ConfigTable          (1.3.6.1.4.1.3028.3.1.1.6)
-- 
--******************************************************************************

	dlgDsx1ConfigTable OBJECT-TYPE
		SYNTAX  SEQUENCE OF DlgDsx1ConfigEntry
		ACCESS  not-accessible
		STATUS  mandatory
		DESCRIPTION
"The DS1 Configuration table. This table is a list of entries Containing
configuration information for all the digital interfaces managed by this
system "
		::={dlgDs1 6}


	dlgDsx1ConfigEntry OBJECT-TYPE
		SYNTAX  DlgDsx1ConfigEntry
		ACCESS  not-accessible
		STATUS  mandatory
		DESCRIPTION
"An entry containing configuration information for all the digital interfaces 
managed by this system."
		INDEX  {dlgDsx1LineIndex}
		::={dlgDsx1ConfigTable 1}


	DlgDsx1ConfigEntry ::=
		SEQUENCE{
			dlgDsx1LineIndex  INTEGER,
			dlgDsx1HiIdentIndex  INTEGER,
			dlgDsx1TimeElapsed  INTEGER,
			dlgDsx1ValidIntervals  INTEGER,
			dlgDsx1LineType  INTEGER,
			dlgDsx1LineCoding  INTEGER,
			dlgDsx1SendCode  INTEGER,
			dlgDsx1CircuitIdentifier  DisplayString,
			dlgDsx1LoopbackConfig  INTEGER,
			dlgDsx1LineStatus  INTEGER,
			dlgDsx1SignalMode  INTEGER,
			dlgDsx1TransmitClockSource  INTEGER
		}


	dlgDsx1LineIndex OBJECT-TYPE
		SYNTAX  INTEGER (1..'7fffffff'h)
		ACCESS  read-only
		STATUS  mandatory
		DESCRIPTION
"This object is the unique identifier of a Digital Network Interface on a 
managed device, the unique identifier is the Dialogic Digital Front End (DTI)"
		::= { dlgDsx1ConfigEntry 1 }

	dlgDsx1HiIdentIndex OBJECT-TYPE
		SYNTAX  INTEGER (1..'7fffffff'h)
		ACCESS  read-only
		STATUS  mandatory
		DESCRIPTION
"This OID provides a way to identify the Dialogic board that hosts the interface
referenced in the DS1 configuration table entry. The value of this object is 
equivalent to the value of the dlgHiIdentIndex that references the board in 
which the interface resides (dlgHiIdentIndex is in the dlghwinf MIB). 
For example, to identify the board hosting the network interface that 
generated an alarm, retrieve the value of this OID for the interface in 
question and then insert  this value in the dlgHiIdentIndex OID in the 
dlghwinf MIB; the board corresponding to the dlgHiIdentIndex value is the one on 
which the network interface that generated the alarm resides"
		::={ dlgDsx1ConfigEntry 2 }


	dlgDsx1TimeElapsed OBJECT-TYPE
		SYNTAX  INTEGER (0..899)
		ACCESS  read-only
		STATUS  mandatory
		DESCRIPTION
"The number of seconds that have elapsed  since the  beginning of the current
error-measurement period .The length of the current error-measurement period 
will be 15 Minutes ( 900 seconds)"
		::={ dlgDsx1ConfigEntry 3 }


	dlgDsx1ValidIntervals OBJECT-TYPE
		SYNTAX  INTEGER (0..96)
		ACCESS  read-only
		STATUS  mandatory
		DESCRIPTION
"The number of previous intervals for which valid data was collected. 
The value will be 96 unless the interface was brought on-line within the last 
24 hours, in which case the value will be the number of complete 15-minute 
intervals, since interface has been online. 'On-line' means both the SNMP and 
the Dialogic service are on that particular Interface to provide valid data "
		::= { dlgDsx1ConfigEntry 4 }


	dlgDsx1LineType OBJECT-TYPE
		SYNTAX  INTEGER {
			other(1),
			dlgDsx1D4(2),
			dlgDsx1E1-CRC(3)
		}
		ACCESS  read-only
		STATUS  mandatory
		DESCRIPTION
"This variable indicates the variety of DS1 Line implementing this circuit. 
The type of circuit affects the number of bits per second that the circuit can 
reasonably carry, as well as the interpretation of the usage 
and error statistics.
1- other
2 - dlgDsx1D4---------->AT&T D4 format Digital signal 1
3 - dlgDsx1E1-CRC------>Consultive Committee on International Telegraphy and 
		  	Telephony Recommendation G.704 (Table 4b) "
		::= { dlgDsx1ConfigEntry 5 }


	dlgDsx1LineCoding OBJECT-TYPE
		SYNTAX  INTEGER {
			dlgDsx1JBZS (1),
			dlgDsx1B8ZS (2),
			dlgDsx1InvertedHDLC (3),
			dlgDsx1TRAN(4)
		}
		ACCESS  read-write
		STATUS  mandatory
		DESCRIPTION
"This variable describes the variety of Zero Code Suppression used on the link,
which in turn affects a number of its characteristics.
1 - dlgDsx1JBZS--------->refers to the Jammed Bit Zero Suppression, in which 
the AT&T specification of at least one pulse every 8 bit periods is literally 
implemented by forcing a pulse in bit 8 of each channel. Thus, only seven bits
per channel, or 1.344 Mbps, is available for data.
2 - dlgDsx1B8ZS--------->refers to the use of a specified pattern of normal 
bits and bipolar violations which are used to replace a sequence of eight zero 
bits.
3 - dlgDsx1InvertedHDLC->refers to a mode wherein no zero code suppression is 
present and the line encoding does not solve the problem directly. In this 
application, the higher layer provides data that meets or exceeds the 
pulse density requirements, such as inverting High level Data Link Control data.
4 - dlgDsx1TRAN	-------->refers to transparent code suppression, which means 
that no code suppression is present "
::= { dlgDsx1ConfigEntry 6 }

	dlgDsx1SendCode OBJECT-TYPE
		SYNTAX  INTEGER {
			dlgDsx1NoSendCode (1)
		}
		ACCESS  read-only
		STATUS  mandatory
		DESCRIPTION 
"The springware boards of dialogic are not capable of sending any code, where 
as the DM3 family of dialogic boards might "
::={ dlgDsx1ConfigEntry 7 }


	dlgDsx1CircuitIdentifier OBJECT-TYPE
		SYNTAX  DisplayString 
		ACCESS  read-write
		STATUS  mandatory
		DESCRIPTION
"This OID enables you to specify a string by which to identify the trunk
connected to the interface referenced in the DS1 configuration table entry. 
For example, the two interfaces on a D/240SC-2T1 might be connected to trunks 
supplied by two different vendors; this OID can be set to the name of the vendor 
supplying the trunk. This OID's default value is 'Dialogic'. "
		::= { dlgDsx1ConfigEntry 8 }


	dlgDsx1LoopbackConfig OBJECT-TYPE
		SYNTAX  INTEGER {
			dlgDsx1Normal(1),
			dlgDsx1PayloadLoop(2),
			dlgDsx1LineLoop(3),
			dlgDsx1LocalLoop(4)
		}
		ACCESS  read-write
		STATUS  mandatory
		DESCRIPTION
"This variable represents the loop back configuration of the Digital 
Network interface. The values mean:
1 - dlgDsx1Normal------->This is the board mode if the Digital Network 
Interface Remote loop back test switch is turned off.
2 - dlgDsx1PayloadLoop-->The received signal at this interface is Looped 
through the device. Typically the received signal is  looped  back  for  
retransmission  after  it has passed through the device's framing function. 
This mode is used for the Digital Network Interface testing .
3 - dlgDsx1LineLoop----->The received signal at this interface does not go 
through the device (minimum penetration) but is looped back out. This loop 
back is generally used by the network for network testing .
4 - dlgDsx1localLoop---->The line interface unit is in local 
loop back mode ( used generally for Digital Network Interface testing "
		::= { dlgDsx1ConfigEntry 9 }


	dlgDsx1LineStatus OBJECT-TYPE
		SYNTAX  INTEGER (1..8191)
		ACCESS  read-only
		STATUS  mandatory
		DESCRIPTION
"This variable indicates the Line Status of the interface. It contains 
loop back, failure, received 'alarm'  and transmitted 'alarm'  information .The 
dlgDsx1LineStatus is a bit  map  represented as a sum , therefore, it can 
represent multiple failures alarms) and a LoopbackState simultaneously. The 
various bit positions are:
1 - dlgDsx1NoAlarm----------->No Alarm Present
2 - dlgDsx1RcvFarEndLOF------>Far end LossOfFrame(Yellow Alarm)
16 - dlgDsx1XmtAIS----------->Near end sending AlarmIndicationSignal
32 - dlgDsx1LossOfFrame------>Near end LossOfFrame (Red Alarm)
64 - dlgDsx1LossOfSignal----->Near end Loss Of Signal
128 - dlgDsx1LoopbackState--->Near end is looped
256 - dlgDsx1T16AIS---------->E1 TimeSlot16alarmIndicationSignal
512 - dlgDsx1RcvFarEndLOMF--->Far End Sending TimeSlot16 LossOfMultiFrame 
1024 -dlgDsx1XmtFarEndLOMF--->Near End Sending TimeSlot16 LossOfMultiFrame 
4096 - dlgDsx1OtherFailure--->Any line status not defined here"
		::= { dlgDsx1ConfigEntry 10 }

	dlgDsx1SignalMode OBJECT-TYPE
		SYNTAX  INTEGER {
			dlgDsx1None (1),
			dlgDsx1RobbedBit (2),
			dlgDsx1BitOriented (3),
			dlgDsx1Isdn (4)
		}
		ACCESS  read-only
		STATUS  mandatory
		DESCRIPTION
"1 - 'dlgDsx1None'------->indicates that no bits are reserved for Signaling 
on this channel.
2 - 'dlgDsx1RobbedBit'--->indicates that T1 Robbed Bit Signaling is in use.
3 - 'dlgDsx1BitOriented'->indicates that E1 Channel Associated Signaling is 
in use.
4 - 'dlgDsx1Isdn'-------->indicates that dialogic supported Isdn protocol is 
in use. For more information on the protocol Query the dlgR4ISDNProtocol 
Oid(1.3.6.1.4.1.3028.2.1.1.2.4.1.2) "
		::= { dlgDsx1ConfigEntry 11 }

	dlgDsx1TransmitClockSource OBJECT-TYPE
		SYNTAX  INTEGER {
			loopTiming (1),
			localTiming (2),
			noOrExternalTiming (3)
		}
		ACCESS  read-write
		STATUS  mandatory
		DESCRIPTION
"The source of Transmit Clock. This is not the Clock source which you can 
set form the Dialogic Configuration Manager 
1 - 'loopTiming'----->indicates that the recovered receive clock is used 
as the transmit clock, the recovered clock is from the network.
2 - 'localTiming'---->indicates that a local or independent clock Source is 
used, 1.544MhzforT1 or 2.048Mhz for E1.
3 - 'No Timing'------>indicates that no clock source is used on this 
interface. The set request with this value will set the clock On this 
interface to No clock."
		::= { dlgDsx1ConfigEntry 12 }


--******************************************************************************
--
--The DS1 Current Table
--=====================
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--		dlgDsx1CurrentTable	(1.3.6.1.4.1.3028.3.1.1.7)
-- 
--******************************************************************************
	dlgDsx1CurrentTable OBJECT-TYPE
		SYNTAX  SEQUENCE OF DlgDsx1CurrentEntry
		ACCESS  not-accessible
		STATUS  mandatory
		DESCRIPTION
"A list of entries containing the current 15 minute interval status information 
for all the Digital network interfaces managed by this system "
		::= { dlgDs1 7 }


	dlgDsx1CurrentEntry OBJECT-TYPE
		SYNTAX  DlgDsx1CurrentEntry
		ACCESS  not-accessible
		STATUS  mandatory
		DESCRIPTION
"An entry containing the current status information for a particular 
Digital network interface "
		INDEX   { dlgDsx1CurrentIndex }
		::= { dlgDsx1CurrentTable 1 }

	DlgDsx1CurrentEntry ::=
		SEQUENCE {
			dlgDsx1CurrentIndex INTEGER,
			dlgDsx1CurrentESs Gauge,
			dlgDsx1CurrentSESs Gauge,
			dlgDsx1CurrentSEFSs Gauge,
			dlgDsx1CurrentUASs Gauge,
			dlgDsx1CurrentCSSs Gauge,
			dlgDsx1CurrentPCVs Gauge,
			dlgDsx1CurrentLESs Gauge,
			dlgDsx1CurrentBESs Gauge,
			dlgDsx1CurrentDMs Gauge,
			dlgDsx1CurrentLCVs Gauge
		}		

	dlgDsx1CurrentIndex OBJECT-TYPE
		SYNTAX  INTEGER (1..'7fffffff'h)
		ACCESS  read-only
		STATUS  mandatory
		DESCRIPTION
"The index value which uniquely identifies  the Digital Network interface  
to which this entry is applicable. The interface identified by a particular 
value of this index ,is the same interface as identified by the same value as 
a dlgDsx1LineIndex object instance."
		::= { dlgDsx1CurrentEntry 1 }


	dlgDsx1CurrentESs OBJECT-TYPE
		SYNTAX  Gauge
		ACCESS  read-only
		STATUS  mandatory
		DESCRIPTION
"The number of Error Seconds, encountered by a Digital Network interface 
in the current 15 minute interval."
		::= { dlgDsx1CurrentEntry 2 }


	dlgDsx1CurrentSESs OBJECT-TYPE
		SYNTAX  Gauge
		ACCESS  read-only
		STATUS  mandatory
		DESCRIPTION
"The number of Severely Error Seconds encountered by a 
Digital Network interface in the current 15 minute interval."
		::= { dlgDsx1CurrentEntry 3 }


	dlgDsx1CurrentSEFSs OBJECT-TYPE
		SYNTAX  Gauge
		ACCESS  read-only
		STATUS  mandatory
		DESCRIPTION
"The number of Severely Error Framing Seconds encountered by a 
Digital Network interface in the current 15 minute interval."
		::= { dlgDsx1CurrentEntry 4 }


	dlgDsx1CurrentUASs OBJECT-TYPE
		SYNTAX  Gauge
		ACCESS  read-only
		STATUS  mandatory
		DESCRIPTION
"The number of Unavailable Seconds encountered by a Digital 
Network interface in the current 15 minute interval."
		::= { dlgDsx1CurrentEntry 5 }


	dlgDsx1CurrentCSSs OBJECT-TYPE
		SYNTAX  Gauge
		ACCESS  read-only		
		STATUS  mandatory
		DESCRIPTION
"The number of Controlled Slip Seconds encountered by a Digital Network 
interface in the current 15 minute interval. Not supported by the 
dialogic SpringWare (Return value will be -1) "
		::= { dlgDsx1CurrentEntry 6 }


	dlgDsx1CurrentPCVs OBJECT-TYPE
		SYNTAX  Gauge
		ACCESS  read-only
		STATUS  mandatory
		DESCRIPTION
"The number of Path Coding Violations encountered by a Digital Network 
interface in the current 15 minute interval."
		::= { dlgDsx1CurrentEntry 7 }


	dlgDsx1CurrentLESs OBJECT-TYPE
		SYNTAX  Gauge
		ACCESS  read-only
		STATUS  mandatory
		DESCRIPTION
"The number of Line Error Seconds encountered by a Digital Network interface 
in the current 15 minute interval."
		::= { dlgDsx1CurrentEntry 8 }


	dlgDsx1CurrentBESs OBJECT-TYPE
		SYNTAX Gauge
		ACCESS read-only
		STATUS mandatory
		DESCRIPTION
"The number of Bursty Error Seconds (BESs) encountered by a Digital 
Network interface in the current 15 minute interval."
		::= {dlgDsx1CurrentEntry 9 }


	dlgDsx1CurrentDMs OBJECT-TYPE
		SYNTAX Gauge
		ACCESS read-only
		STATUS mandatory	
		DESCRIPTION
"The number of Degraded Minutes (DMs) encountered by a Digital network 
interface in the current 15 minute interval. Not implemented in the 
SpringWare (return value -1)"
		::= { dlgDsx1CurrentEntry 10 }


	dlgDsx1CurrentLCVs OBJECT-TYPE
		SYNTAX Gauge
		ACCESS read-only
		STATUS mandatory
		DESCRIPTION		
"The number of Line Code Violations (LCVs) encountered by a Digital Network 
interface in the current 15 minute interval."
::= {dlgDsx1CurrentEntry 11 }


--******************************************************************************
--
--The DS1 Interval Table
--=====================
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--		dlgDsx1IntervalTable	    (1.3.6.1.4.1.3028.3.1.1.8)
-- 
--******************************************************************************   

	dlgDsx1IntervalTable OBJECT-TYPE
		SYNTAX  SEQUENCE OF DlgDsx1IntervalEntry
		ACCESS  not-accessible
		STATUS  mandatory
		DESCRIPTION
"The DS1 Interval table. This table contains various statistics 
collected by each Digital network Interface over the previous 24 hours 
of operation. The past 24 hours are broken into 96 completed 
15 minutes interval. The completed intervals mean both the dialogic service 
and the SNMP were running during that period "
		::= { dlgDs1 8 }


	dlgDsx1IntervalEntry OBJECT-TYPE
		SYNTAX  DlgDsx1IntervalEntry
		ACCESS  not-accessible
		STATUS  mandatory
		DESCRIPTION	
"An entry in the DS1 Interval table, which consist of the statistics for 
all the valid intervals (intervals for which the statistical data is 
collected) of all the Digital network interfaces managed by this system "
		INDEX   { dlgDsx1IntervalIndex, dlgDsx1IntervalNumber }
		::= { dlgDsx1IntervalTable 1 }

	DlgDsx1IntervalEntry ::=
		SEQUENCE {
			dlgDsx1IntervalIndex INTEGER,
			dlgDsx1IntervalNumber INTEGER,
			dlgDsx1IntervalESs Gauge,
			dlgDsx1IntervalSESs Gauge,
			dlgDsx1IntervalSEFSs Gauge,
			dlgDsx1IntervalUASs Gauge,
			dlgDsx1IntervalCSSs Gauge,
			dlgDsx1IntervalPCVs Gauge,
			dlgDsx1IntervalLESs Gauge,
			dlgDsx1IntervalBESs Gauge,
			dlgDsx1IntervalDMs Gauge,
			dlgDsx1IntervalLCVs Gauge
		}


	dlgDsx1IntervalIndex OBJECT-TYPE
		SYNTAX  INTEGER (1..'7fffffff'h)
		ACCESS  read-only
		STATUS  mandatory
		DESCRIPTION
"The index value which uniquely identifies the Digital Network interface 
to which this entry is applicable. The interface identified by a particular 
Value of this index is the same interface as Identified by the same value as 
a dlgDsx1LineIndex Object instance."
		::= { dlgDsx1IntervalEntry 1 }


	dlgDsx1IntervalNumber OBJECT-TYPE
		SYNTAX  INTEGER (1..96)
		ACCESS  read-only
		STATUS  mandatory
		DESCRIPTION
"A number between 1 and 96, where 1 is the most recently completed 15 minute 
interval and 96 is the least recently completed 15 minutes interval 
(assuming that all 96 intervals are valid). The intervals will be valid 
if both the Dialogic and the SNMP service were running for that period 
of time"
		::= { dlgDsx1IntervalEntry 2 }


	dlgDsx1IntervalESs OBJECT-TYPE
		SYNTAX  Gauge
		ACCESS  read-only
		STATUS  mandatory
		DESCRIPTION
"The number of Error Seconds encountered by a Digital Network  interface in 
one of the previous 96, individual 15 minute, intervals."
		::= { dlgDsx1IntervalEntry 3 }


	dlgDsx1IntervalSESs OBJECT-TYPE
		SYNTAX  Gauge
		ACCESS  read-only
		STATUS  mandatory
		DESCRIPTION
"The number of Severely Error Seconds encountered by a Digital Network 
interface in one of the previous 96, individual 15 minute, intervals."
		::= { dlgDsx1IntervalEntry 4 }


	dlgDsx1IntervalSEFSs OBJECT-TYPE
		SYNTAX  Gauge
		ACCESS  read-only
		STATUS  mandatory
		DESCRIPTION
"The number of Severely Error Framing Seconds encountered by a Digital 
network interface in one of the previous 96, individual 15 minute, intervals."
		::= { dlgDsx1IntervalEntry 5 }


	dlgDsx1IntervalUASs OBJECT-TYPE
		SYNTAX  Gauge
		ACCESS  read-only
		STATUS  mandatory		
		DESCRIPTION
"The number of Unavailable Seconds encountered by a Digital Network interface 
in one of the previous 96,individual 15 minute, intervals."
		::= { dlgDsx1IntervalEntry 6 }


	dlgDsx1IntervalCSSs OBJECT-TYPE
		SYNTAX  Gauge
		ACCESS  read-only
		STATUS  mandatory
		DESCRIPTION
"The number of Controlled Slip Seconds encountered by a Digital Network 
interface in one of the previous 96, individual 15 minute, intervals. Not 
supported in Springware( return value -1 )"
		::= { dlgDsx1IntervalEntry 7 }


	dlgDsx1IntervalPCVs OBJECT-TYPE
		SYNTAX  Gauge
		ACCESS  read-only
		STATUS  mandatory
		DESCRIPTION	
"The number of Path Coding Violations encountered by a Digital network 
interface in one of the previous 96, individual 15 minute, intervals."
::= { dlgDsx1IntervalEntry 8 }


	dlgDsx1IntervalLESs OBJECT-TYPE
		SYNTAX  Gauge
		ACCESS  read-only
		STATUS  mandatory
		DESCRIPTION
"The number of Line Error Seconds encountered by a Digital network 
interface in one of the previous 96,individual 15 minute, intervals."
		::= { dlgDsx1IntervalEntry 9 }


	dlgDsx1IntervalBESs OBJECT-TYPE
		SYNTAX Gauge
		ACCESS read-only
		STATUS mandatory
		DESCRIPTION
"The number of Bursty Error Seconds (BESs) encountered by a Digital 
Network interface in one of the previous 96, individual 15 minute, intervals."
		::= {dlgDsx1IntervalEntry 10 }


	dlgDsx1IntervalDMs OBJECT-TYPE
		SYNTAX Gauge
		ACCESS read-only
		STATUS mandatory
		DESCRIPTION
"The number of Degraded Minutes (DMs) encountered by a Digital 
Network interface in one of the previous 96, individual 15 minute, intervals. 
This is not supported in Springware(return value -1 )"
		::= { dlgDsx1IntervalEntry 11 }


	dlgDsx1IntervalLCVs OBJECT-TYPE
		SYNTAX Gauge
		ACCESS read-only
		STATUS mandatory
		DESCRIPTION
"The number of Line Code Violations (LCVs) encountered by a Digital 
Network interface in one of the previous 96, individual 15 minute, intervals."
		::= {dlgDsx1IntervalEntry 12 }


--******************************************************************************
--
--The DS1 Total Table
--=====================
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--		dlgDsx1TotalTable	    	    (1.3.6.1.4.1.3028.3.1.1.9)
-- 
--******************************************************************************

	dlgDsx1TotalTable OBJECT-TYPE
		SYNTAX  SEQUENCE OF DlgDsx1TotalEntry
		ACCESS  not-accessible
		STATUS  mandatory
		DESCRIPTION
"A list of entries containing the total statistics 
(cumulative sum of the various statistics) for the 24 hour period preceding 
the current interval. The value of the current interval will be the value 
provided by the dlgDsx1IntervalNumber (OID 1.3.6.1.4.1.3028.3.1.1.8.1.2)."
		::= { dlgDs1 9 }


	dlgDsx1TotalEntry OBJECT-TYPE
		SYNTAX  DlgDsx1TotalEntry
		ACCESS  not-accessible
		STATUS  mandatory
		DESCRIPTION
"An entry in the DS1 Total table containing the total statistical 
information of all the digital network interfaces managed by this system "
		INDEX   { dlgDsx1TotalIndex }
		::= { dlgDsx1TotalTable 1 }

	DlgDsx1TotalEntry ::=
		SEQUENCE {
			dlgDsx1TotalIndex INTEGER,
			dlgDsx1TotalESs Gauge,
			dlgDsx1TotalSESs Gauge,
			dlgDsx1TotalSEFSs Gauge,
			dlgDsx1TotalUASs Gauge,
			dlgDsx1TotalCSSs Gauge,
			dlgDsx1TotalPCVs Gauge,
			dlgDsx1TotalLESs Gauge,
			dlgDsx1TotalBESs Gauge,
			dlgDsx1TotalDMs Gauge,
			dlgDsx1TotalLCVs Gauge
		}


	dlgDsx1TotalIndex OBJECT-TYPE
		SYNTAX  INTEGER (1..'7fffffff'h)
		ACCESS  read-only
		STATUS  mandatory
		DESCRIPTION
"The index value which uniquely identifies the Digital Network interface to 
which this entry is applicable. The interface identified by a particular 
value of this index is the same interface as identified by the same value 
as a dlgDsx1LineIndex object instance."
		::= { dlgDsx1TotalEntry 1 }


	dlgDsx1TotalESs OBJECT-TYPE
		SYNTAX  Gauge
		ACCESS  read-only
		STATUS  mandatory
		DESCRIPTION
"The number of Error Seconds encountered by a Digital network interface 
in the previous 24 hour interval"
		::= { dlgDsx1TotalEntry 2 }


	dlgDsx1TotalSESs OBJECT-TYPE
		SYNTAX  Gauge
		ACCESS  read-only
		STATUS  mandatory
		DESCRIPTION
"The number of Severely Error Seconds encountered by a Digital 
Network interface in the previous 24 hour interval."
		::= { dlgDsx1TotalEntry 3 }


	dlgDsx1TotalSEFSs OBJECT-TYPE
		SYNTAX  Gauge
		ACCESS  read-only
		STATUS  mandatory
		DESCRIPTION	
"The number of Severely Error Framing Seconds encountered by a Digital 
Network interface in the previous 24 hour interval."
		::= { dlgDsx1TotalEntry 4 }


	dlgDsx1TotalUASs OBJECT-TYPE
		SYNTAX  Gauge
		ACCESS  read-only
		STATUS  mandatory
		DESCRIPTION
"The number of Unavailable Seconds encountered by a Digital Network interface 
in the previous 24 hour interval."
		::= { dlgDsx1TotalEntry 5 }


	dlgDsx1TotalCSSs OBJECT-TYPE
		SYNTAX  Gauge
		ACCESS  read-only
		STATUS  mandatory
		DESCRIPTION
"The number of Controlled Slip Seconds encountered by a Digital Network 
interface in the previous 24 hour interval. Not supported in 
Springware(return value -1 )"
		::= { dlgDsx1TotalEntry 6 }

	
	dlgDsx1TotalPCVs OBJECT-TYPE
		SYNTAX  Gauge
		ACCESS  read-only
		STATUS  mandatory
		DESCRIPTION
"The number of Path Coding Violations encountered by a Digital Network 
interface in the previous 24 hour interval."
		::= { dlgDsx1TotalEntry 7 }


	dlgDsx1TotalLESs OBJECT-TYPE
		SYNTAX  Gauge
		ACCESS  read-only
		STATUS  mandatory
		DESCRIPTION
"The number of Line Error Seconds encountered by a Digital network 
interface in the previous 24 hour interval."
		::= { dlgDsx1TotalEntry 8 }


	dlgDsx1TotalBESs OBJECT-TYPE
		SYNTAX Gauge
		ACCESS read-only
		STATUS mandatory
		DESCRIPTION
"The number of Bursty Error Seconds (BESs) encountered by a Digital Network 
interface in the previous 24 hour interval."
		::= { dlgDsx1TotalEntry 9 }


	dlgDsx1TotalDMs OBJECT-TYPE
		SYNTAX Gauge
		ACCESS read-only
		STATUS mandatory
		DESCRIPTION
"The number of Degraded Minutes  (DMs) encountered by a Digital Network 
interface in the previous 24 hour interval. Not supported in 
Springware (return value -1 )"
		::= { dlgDsx1TotalEntry 10 }


	dlgDsx1TotalLCVs OBJECT-TYPE
		SYNTAX Gauge
		ACCESS read-only
		STATUS mandatory
		DESCRIPTION
"The number of Line Code Violations (LCVs) encountered by a Digital 
Network interface in the current 15 minute interval."
::= {dlgDsx1TotalEntry 11 }

--******************************************************************************
--
--The DS1 Alarm Table
--=====================
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--		dlgDsx1AlarmTable		    (1.3.6.1.4.1.3028.3.1.1.10)
-- 
--******************************************************************************   

	dlgDsx1AlarmTable OBJECT-TYPE
		SYNTAX SEQUENCE OF DlgDsx1AlarmEntry
		ACCESS not-accessible
		STATUS mandatory
		DESCRIPTION
"A table of all currently active alarms on all the Digital network interfaces 
managed by this system. This table is list of entries containing the alarm 
information for all the digital network interfaces managed by this system. "
		::= { dlgDs1 10 }

	dlgDsx1AlarmEntry OBJECT-TYPE
		SYNTAX DlgDsx1AlarmEntry
		ACCESS not-accessible
		STATUS mandatory
		DESCRIPTION
"An entry containing the alarm information for all the digital network 
interfaces managed by this system."
		INDEX { dlgDsx1AlarmIndex }
		::= { dlgDsx1AlarmTable 1 }

	DlgDsx1AlarmEntry ::=
		SEQUENCE {
			dlgDsx1AlarmIndex INTEGER,
			dlgDsx1AlarmType Dsx1AlarmType
		}



	dlgDsx1AlarmIndex OBJECT-TYPE
		SYNTAX INTEGER
		ACCESS read-only
		STATUS mandatory
		DESCRIPTION
"The index value which uniquely identifies the Digital Network interface to 
which this entry is applicable. The interface identified by a particular value 
of this index is the same interface as identified by the same value as a 
dlgDsx1LineIndex object instance."
		::= { dlgDsx1AlarmEntry 1 }

	dlgDsx1AlarmType OBJECT-TYPE
		SYNTAX Dsx1AlarmType
		ACCESS read-only
		STATUS mandatory
		DESCRIPTION
"Identifies an alarm that's currently outstanding on this line
0 - No Alarm.------->The signal(carrier) is available before the Dialogic board 
is downloaded and service is started.
100  - No Alarm.---->The signal is provided to the Dialogic board after
it is downloaded and started.
101 - Red Alarm
102 - Blue Alarm
103 - Yellow Alarm
104 - E1 Alarm "
::= { dlgDsx1AlarmEntry 2 }


--******************************************************************************
--
--The DS1 Spring Ware Event Mask Table
--=====================================
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--		dlgDsx1SwEvtMskTable	    (1.3.6.1.4.1.3028.3.1.1.11)
-- 
--******************************************************************************   



	dlgDsx1SwEvtMskTable OBJECT-TYPE
		SYNTAX SEQUENCE OF DlgDsx1SwEvtMskEntry
		ACCESS not-accessible
		STATUS mandatory
		DESCRIPTION
"A table to manage the Functioning of Event Mask on all the Digital network 
interfaces of dialogic spring ware boards managed by this system."
		::= { dlgDs1 11 }

	dlgDsx1SwEvtMskEntry OBJECT-TYPE
		SYNTAX DlgDsx1SwEvtMskEntry
		ACCESS not-accessible
		STATUS mandatory
		DESCRIPTION
"An entry in the Spring Ware Event mask table which contains the springware 
event mask information for all the springware digital Network 
interfaces managed by this system."
		INDEX  {dlgDsx1SwEvtMskIndex}
		::= { dlgDsx1SwEvtMskTable 1 }



	DlgDsx1SwEvtMskEntry ::=
		SEQUENCE {
			dlgDsx1SwEvtMskIndex INTEGER,
			dlgDsx1SwEvtMskAlwchgmsk Boolean,
			dlgDsx1SwEvtMskValue	INTEGER 
		}

	dlgDsx1SwEvtMskIndex OBJECT-TYPE
		SYNTAX INTEGER
		ACCESS read-only
		STATUS mandatory
		DESCRIPTION
"The index value which uniquely identifies the Digital Network interface 
to which this entry is applicable. The interface identified by a particular 
value of this index is the same interface as identified by the same value as 
a dlgDsx1LineIndex object instance."
		::= { dlgDsx1SwEvtMskEntry 1 }

	dlgDsx1SwEvtMskAlwchgmsk OBJECT-TYPE
		SYNTAX Boolean 	
		ACCESS read-write
		STATUS mandatory
		DESCRIPTION
"This variable gives the permission to change the spring ware 
event value from the agent implementing this MIB. The permission granted here 
doesn't have control over other applications from changing/modifying the 
Springware event mask.
True(1) ---->Permission granted to change/modify the springware event mask.
False(0)---->Permission denied to change/modify the springware event mask."
		::= { dlgDsx1SwEvtMskEntry 2 }
	dlgDsx1SwEvtMskValue OBJECT-TYPE
		SYNTAX INTEGER {
			allAlarmevtmsk (1),
			t1RedAlarmevtmsk (2),
			t1BlueAlarmevtmsk (3),
			t1YellowAlarmevtmsk (4),
			t1OutOfFrameAlarmevtmsk (5),
			lossOfSignalAlarmevtmsk (6),
			bipolarViolationAlarmevtmsk (7),
			e1LossofSynchronizationmsk (8),
			e1ReceivedUnframedAllOnesmsk (9),
			e1FrameSyncErrormsk (10),
			e1MultiFrameSyncErrormsk (11),
			comboAlarmevtmsk(12)
		}
		ACCESS read-write
		STATUS mandatory
		DESCRIPTION
"The events enabled by the SpringWare event mask are sent not only to the 
BoardWatch agents, but also to all processes that read from and write to a 
Dialogic digital network interface device in the system. Before enabling events 
through the event mask, it must be determined that these processes have the 
ability to receive the enabled events .The value of this Object gives the 
Spring Ware Event Mask present on a particular digital network interface. The 
set request for this Object will check the value of dlgDsx1SwevtmskAlwchgmsk 
Object; if it is set to true then only further action will take place. Below 
is the detailed description :
Value					Action					
AllAlarmevtmsk (1)--------------->enables all the Alarm Events.Applicable to	
				  T1&E1
T1RedAlarmevtmsk (2)------------->Adds Red Alarm Event to the Existingevents.
				  Applicable to T1
T1BlueAlarmevtmsk (3)------------>Adds Blue Alarm Event to the Existing events.
				  Applicable to T1
T1YellowAlarmevtmsk (4)---------->Adds Yellow Alarm Event to the Existing events.
				  Applicable to T1
T1OutOfFrameAlarmevtmsk (5)------>Adds Out of frame alarm event to the existing
				  events.Applicable to T1
LossOfSignalAlarmevtmsk (6)------>Adds Loss of signal alarm event to the
				  existing events.Applicable to T1&E1
BipolarViolationAlarmevtmsk (7)-->Adds bipolar violation alarm Event to the
				  existing events.Applicable to T1&E1
E1LossofSynchronizationmsk (8)--->Adds Loss of synchronization Event to the
				  existing events.Applicable to E1
E1ReceivedUnframedAllOnesmsk (9)->Adds Received unframed all ones Event to
				  the existing events.Applicable to E1
E1FrameSyncErrormsk (10)--------->Adds Frame synchronization error Event to 
				  the existing events.Applicable to E1
E1MultiFrameSyncErrormsk (11)---->Adds Multi Frame Synchronization Error event
				  to the existing Events.Applicable to E1
ComboAlarmevtmsk(12)------------->No action .This is a value Provided for 
				  the SNMP get and GetNext request "
		::= { dlgDsx1SwEvtMskEntry 3 }

--******************************************************************************
--
--The DS1 MIB Revision
--=====================
-- The dialogic enterprise              (1.3.6.1.4.1.3028)
--      dlgNetworkInterfaces Group      (1.3.6.1.4.1.3028.3)
--        dlgTransmissions Group        (1.3.6.1.4.1.3028.3.1)
--         dlgDs1 Group                 (1.3.6.1.4.1.3028.3.1.1)
--		dlgDsx1MibRev		    (1.3.6.1.4.1.3028.3.1.1.12)
-- 
--An Agent conforming to this document will return a mibRevMajor of two (2) and 
--a mibRevMinor of zero (0).

--*****************************************************************************

dlgDsx1MibRev       OBJECT IDENTIFIER ::= { dlgDs1 12 }
	dlgDsx1MibRevMajor OBJECT-TYPE
		SYNTAX  INTEGER (1..65535)
		ACCESS  read-only
		STATUS  mandatory
		DESCRIPTION
"The Major Revision level .A change in the major revision level represents 
a major change in the architecture of the MIB.  A change in the major 
revision level may indicate a significant change in the information supported 
and/or the meaning of the supported information, correct interpretation 
of data may require a MIB document with the same major revision level. The 
current major revision number is 2"
	::= { dlgDsx1MibRev 1 }

	dlgDsx1MibRevMinor OBJECT-TYPE
		SYNTAX  INTEGER (0..65535)
		ACCESS  read-only
		STATUS  mandatory
		DESCRIPTION
"The Minor Revision level. A change in the minor revision level may represent 
some minor additional support, no changes to any pre-existing information 
has occurred. Its being advice to look at the associated major revision 
number along with this level number. The current minor number is 0 for the 
current major revision number 2 "
		::= { dlgDsx1MibRev 2 }

	dlgDsx1MibCondition OBJECT-TYPE
		SYNTAX  INTEGER {
		other(1),
		ok(2),
		degraded(3),
		failed(4)
		}
		ACCESS  read-only
		STATUS  mandatory
		DESCRIPTION
"The overall condition. This object represents the overall status of the 
Dialogic Ds1 Agent represented by this MIB.
Other(1) ----->For all the conditions except those defined here
Ok(2) -------->For all the conditions where is Agent associated with 
this Mib is providing valid and correct information .
Degraded(3) -->For the following conditions or the combination of the 
following conditions:
1) Springware event mask is not set to all for the R4 boards.
2) API failure to provide the statistical information on either the R4 or 
the Dm3 cards.
Failed(4)------>For the following conditions or combination of the 
following conditions:
1) If the system runs out of memory to support the agent implementing this Mib.
2) If the system fails to unallocate the memory, allocated by the agent
implementing this mib
3) When the critical API calls to collect the statistics fails, for both 
the R4 and the Dm3 cards paralyzing agent with any valid data "
		::= { dlgDsx1MibRev 3 }
--
-- Traps
--

dlgDsx1Alarm TRAP-TYPE
ENTERPRISE dialogic
VARIABLES { dlgDsx1AlarmIndex, dlgDsx1AlarmType }
DESCRIPTION
"Indicates a change in the alarm condition."
::= 3001

dlgDsx1SwEvtMskTrap TRAP-TYPE
ENTERPRISE dialogic
VARIABLES { dlgDsx1SwEvtMskIndex, dlgDsx1SwEvtMskValue }
DESCRIPTION
"Indicates the change in the Event Mask. The value in this trap is the 
value with which the Set request was sent to the Agent on the object 
dlgDsx1SwEvtMskValue (OID 1.3.6.1.4.1.3028.3.1.1.11.1.3)"
::= 3002
END
