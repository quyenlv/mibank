ACC-IPSEC DEFINITIONS ::= BEGIN

    IMPORTS
	 OBJECT-TYPE, IpAddress, TimeTicks, Gauge, Counter FROM RFC1155-SMI
	 TRAP-TYPE FROM RFC-1215
        accTrapLogSeqNum FROM ACC-SYSTEM
	accBRG, DisplayString, RowStatus, IfIndex, SmdsAddress
             FROM ACC-MIB;
-- IPSEC Group
accIpsec        OBJECT IDENTIFIER      ::= { accBRG 81 }
accIpsecConfig  OBJECT IDENTIFIER      ::= { accIpsec 1 }
accIpsecStats           OBJECT IDENTIFIER      ::= { accIpsec 2 }
accIpsecSAConfig        OBJECT IDENTIFIER      ::= { accIpsec 3 }
accIpsecSAStats         OBJECT IDENTIFIER      ::= { accIpsec 4 }
accIpsecConfigMessageLevel      OBJECT-TYPE
                SYNTAX  INTEGER (1..7)
                ACCESS  read-write
                STATUS  mandatory
DESCRIPTION     "IPSec message level "
            ::= { accIpsecConfig 1 }
accIpsecConfigDebugMask OBJECT-TYPE
                SYNTAX  INTEGER
                ACCESS  read-write
                STATUS  mandatory
DESCRIPTION     "IPSec debug mask"
            ::= { accIpsecConfig 2 }
accIpsecConfigSANumber  OBJECT-TYPE
                SYNTAX  INTEGER
                ACCESS  read-write
                STATUS  mandatory
DESCRIPTION     "The maximum number of SAs"
            ::= { accIpsecConfig 3 }
accIpsecConfigAuthenticationAllowed     OBJECT-TYPE
                SYNTAX  INTEGER { disable(1), enable(2) }
                ACCESS  read-only
                STATUS  mandatory
DESCRIPTION     "Authentication allowed"
            ::= { accIpsecConfig 4 }
accIpsecConfigEncryptionKeyLength       OBJECT-TYPE
                SYNTAX  INTEGER
                ACCESS  read-only
                STATUS  mandatory
DESCRIPTION     "The maximum allowed key length for encryption"
            ::= { accIpsecConfig 5 }
accIpsecStatsInOkPackets        OBJECT-TYPE
                SYNTAX  Counter
                ACCESS  read-only
                STATUS  mandatory
DESCRIPTION     "Number of correctly received IPSec packets"
            ::= { accIpsecStats 1 }
accIpsecStatsOutOkPackets       OBJECT-TYPE
                SYNTAX  Counter
                ACCESS  read-only
                STATUS  mandatory
DESCRIPTION     "Number of correctly sent IPSec packets"
            ::= { accIpsecStats 2 }
accIpsecStatsIllegalInSpis      OBJECT-TYPE
                SYNTAX  Counter
                ACCESS  read-only
                STATUS  mandatory
DESCRIPTION     "Number of packets dropped because the SPI was incorrect"
            ::= { accIpsecStats 3 }
accIpsecStatsIllegalProtos      OBJECT-TYPE
                SYNTAX  Counter
                ACCESS  read-only
                STATUS  mandatory
DESCRIPTION     "Number of packets dropped because the protocol contained
                        inside the received IPSec packet was incorrect, i.e. a transport
mode SA
                        contained a tunneled packet or a tunnel mode SA contained a
non-tunneled
                        packet"
            ::= { accIpsecStats 4 }
accIpsecStatsUnsuppAHLens       OBJECT-TYPE
                SYNTAX  Counter
                ACCESS  read-only
                STATUS  mandatory
DESCRIPTION     "Number of packets dropped because the authenticator length was not
                         supported"
            ::= { accIpsecStats 5 }
accIpsecStatsUnsuppOpts OBJECT-TYPE
                SYNTAX  Counter
                ACCESS  read-only
                STATUS  mandatory
DESCRIPTION     "Number of packets dropped because some IP options were not supported by 
                        IPSec"
            ::= { accIpsecStats 6 }
accIpsecStatsPacketTooSmalls    OBJECT-TYPE
                SYNTAX  Counter
                ACCESS  read-only
                STATUS  mandatory
DESCRIPTION     "Number of packets dropped because the packet was too small to contain
                        all necessary IPSec information"
            ::= { accIpsecStats 7 }
accIpsecStatsMalformedOpts      OBJECT-TYPE
                SYNTAX  Counter
                ACCESS  read-only
                STATUS  mandatory
DESCRIPTION     "Number of packets dropped because some IP options were malformed"
            ::= { accIpsecStats 8 }
accIpsecStatsUnsuppIPVersions   OBJECT-TYPE
                SYNTAX  Counter
                ACCESS  read-only
                STATUS  mandatory
DESCRIPTION     "Number of packets dropped because the tunneled packet was not IPv4"
            ::= { accIpsecStats 9 }
accIpsecStatsNoRoutes   OBJECT-TYPE
                SYNTAX  Counter
                ACCESS  read-only
                STATUS  mandatory
DESCRIPTION     "Number of packets dropped because there was no route to the 
                        specified outgoing security gateway"
            ::= { accIpsecStats 10 }
accIpsecStatsMissingGWs OBJECT-TYPE
                SYNTAX  Counter
                ACCESS  read-only
                STATUS  mandatory
DESCRIPTION     "Number of packets dropped because the outgoing security gateway
                was not specified"
            ::= { accIpsecStats 11 }
accIpsecStatsSha1Mismatches     OBJECT-TYPE
                SYNTAX  Counter
                ACCESS  read-only
                STATUS  mandatory
DESCRIPTION     "Number of packets dropped because the SHA-1 authenticator
                        was incorrect"
            ::= { accIpsecStats 12 }
accIpsecStatsMd5Mistmatches     OBJECT-TYPE
                SYNTAX  Counter
                ACCESS  read-only
                STATUS  mandatory
DESCRIPTION     "Number of packets dropped because the MD5 authenticator
                        was incorrect"
            ::= { accIpsecStats 13 }
accIpsecStatsReplayCheckFaileds OBJECT-TYPE
                SYNTAX  Counter
                ACCESS  read-only
                STATUS  mandatory
DESCRIPTION     "Number of packets dropped because replay checks failed"
        ::= { accIpsecStats 14 }
accIpsecStatsIllegalPads        OBJECT-TYPE
                SYNTAX  Counter
                ACCESS  read-only
                STATUS  mandatory
DESCRIPTION     "Number of packets dropped because ESP padding content
                        was incorrect"
        ::= { accIpsecStats 15 }
accIpsecStatsSeqnoCycles        OBJECT-TYPE
                SYNTAX  Counter
                ACCESS  read-only
                STATUS  mandatory
DESCRIPTION     "Number of packets dropped because of sequence number
                        overflow"
        ::= { accIpsecStats 16 }
accIpsecStatsInsufficientPads   OBJECT-TYPE
                SYNTAX  Counter
                ACCESS  read-only
                STATUS  mandatory
DESCRIPTION     "Number of packets dropped because ESP padding was
                        of incorrect length"
        ::= { accIpsecStats 17 }
accIpsecStatsTtlZeros   OBJECT-TYPE
                SYNTAX  Counter
                ACCESS  read-only
                STATUS  mandatory
DESCRIPTION     "Number of packets dropped because the packet being tunneled
                        had its TTL decremented to zero"
        ::= { accIpsecStats 18 }
accIpsecStatsNoKeys     OBJECT-TYPE
                SYNTAX  Counter
                ACCESS  read-only
                STATUS  mandatory
DESCRIPTION     "Number of packets dropped because the required authentication or 
                        encryption keys were not set"
        ::= { accIpsecStats 19 }
accIpsecStatsIllegalFragments   OBJECT-TYPE
                SYNTAX  Counter
                ACCESS  read-only
                STATUS  mandatory
DESCRIPTION     "Number of packets dropped because a transport mode packet
                        contained a fragment"
        ::= { accIpsecStats 20 }
accIpsecStatsCpuOverloads       OBJECT-TYPE
                SYNTAX  Counter
                ACCESS  read-only
                STATUS  mandatory
DESCRIPTION     "Number of packets dropped because of CPU overload"
        ::= { accIpsecStats 21 }
accIpsecStatsHdrAllocs  OBJECT-TYPE
                SYNTAX  Counter
                ACCESS  read-only
                STATUS  mandatory
DESCRIPTION     "Number of extra memory allocations done for headers"
        ::= { accIpsecStats 22 }
accIpsecStatsTlrAllocs  OBJECT-TYPE
                SYNTAX  Counter
                ACCESS  read-only
                STATUS  mandatory
DESCRIPTION     "Number of extra memory allocations done for trailers"
        ::= { accIpsecStats 23 }
accIpsecStatsBlockJoins OBJECT-TYPE
                SYNTAX  Counter
                ACCESS  read-only
                STATUS  mandatory
DESCRIPTION     "Number of memory block joins "
        ::= { accIpsecStats 24 }
accIpsecSAConfigTable OBJECT-TYPE
        SYNTAX  SEQUENCE OF AccIpsecSAConfigEntry
        ACCESS  not-accessible
        STATUS  mandatory
        DESCRIPTION ""
        ::= { accIpsecSAConfig 1 }
accIpsecSAConfigEntry OBJECT-TYPE
        SYNTAX  AccIpsecSAConfigEntry
        ACCESS  not-accessible
        STATUS  mandatory
        DESCRIPTION ""
        INDEX   { accIpsecSAConfigIndex }
        ::= { accIpsecSAConfigTable 1 }
AccIpsecSAConfigEntry   ::= SEQUENCE  {
        accIpsecSAConfigIndex           OCTET STRING,
        accIpsecSAConfigDir             INTEGER,
        accIpsecSAConfigMode            INTEGER,
        accIpsecSAConfigProtocol        INTEGER,
        accIpsecSAConfigSPI             INTEGER,
        accIpsecSAConfigAuthAlgorithm   INTEGER,
        accIpsecSAConfigReplayCheck     INTEGER,
        accIpsecSAConfigOverflowAudit   INTEGER,
        accIpsecSAConfigCopyDF          INTEGER,
        accIpsecSAConfigDestAddr                IpAddress,
        accIpsecSAConfigSharedAuthSecret        OCTET STRING,
        accIpsecSAConfigEncrAlgorithm           INTEGER,
        accIpsecSAConfigSharedEncrSecret        OCTET STRING,
        accIpsecSAConfigPriority                INTEGER,
        accIpsecSAConfigSequenceNumber          INTEGER,
        accIpsecSAConfigStatus                  RowStatus
}
accIpsecSAConfigIndex   OBJECT-TYPE
                SYNTAX  OCTET STRING
                ACCESS  read-write
                STATUS  mandatory
        DESCRIPTION     "The name of the SA entry"
            ::= { accIpsecSAConfigEntry 1 }
accIpsecSAConfigDir             OBJECT-TYPE
        SYNTAX  INTEGER { incoming(1), outgoing(2) }
        ACCESS  read-write
        STATUS  mandatory
        DESCRIPTION     "The direction of the SA"
        DEFVAL  { incoming }
                        ::= { accIpsecSAConfigEntry 2 }
accIpsecSAConfigMode    OBJECT-TYPE
        SYNTAX  INTEGER { transport(1), tunnel(2), wildcard(3) }
        ACCESS  read-write
        STATUS  mandatory
        DESCRIPTION     "SA mode in the security association data base"
        DEFVAL  { transport }
           ::= { accIpsecSAConfigEntry 3 }
accIpsecSAConfigProtocol        OBJECT-TYPE
        SYNTAX  INTEGER { esp(50), ah(51) }
        ACCESS  read-write
        STATUS  mandatory
        DESCRIPTION     "Which protocol to use for an SA in the security
                                association data base"
        DEFVAL  { ah }
            ::= { accIpsecSAConfigEntry 4 }
accIpsecSAConfigSPI             OBJECT-TYPE
        SYNTAX  INTEGER
        ACCESS  read-write
        STATUS  mandatory
        DESCRIPTION     "The SPI value of the SA"
        DEFVAL  { 0 }
            ::= { accIpsecSAConfigEntry 5 }
accIpsecSAConfigAuthAlgorithm   OBJECT-TYPE
        SYNTAX  INTEGER 
                          { hmac-sha1(1), hmac-md5(2), null(3) }
        ACCESS  read-write
        STATUS  mandatory
        DESCRIPTION     "SA authenticaiton algorithm in the 
                        security association data base"
        DEFVAL  { hmac-md5 }
            ::= { accIpsecSAConfigEntry 6 }
accIpsecSAConfigReplayCheck     OBJECT-TYPE
        SYNTAX  INTEGER { disable(1), enable(2) }
        ACCESS  read-write
        STATUS  mandatory
        DESCRIPTION     "Replay check prevents the same sequence number
                        from being used twice on received packets"
        DEFVAL  { disable }
            ::= { accIpsecSAConfigEntry 7 }
accIpsecSAConfigOverflowAudit   OBJECT-TYPE
        SYNTAX  INTEGER { disable(1), enable(2) }
        ACCESS  read-write
        STATUS  mandatory
        DESCRIPTION     "Overflow audit prevents further packets
                         from being sent when a sequence number overflow occurs"
        DEFVAL  { disable }
            ::= { accIpsecSAConfigEntry 8 }
accIpsecSAConfigCopyDF  OBJECT-TYPE
        SYNTAX  INTEGER { reset(1), set(2), copy(3) }
        ACCESS  read-write
        STATUS  mandatory
        DESCRIPTION     "The handling of the DF bit on the sent encapsulating header
                        based on the DF bit of the encapsulated header"
        DEFVAL  { reset }
            ::= { accIpsecSAConfigEntry 9 }
accIpsecSAConfigDestAddr        OBJECT-TYPE
                SYNTAX  IpAddress
                ACCESS  read-write
                STATUS  mandatory
DESCRIPTION     "Destination IP address"
            ::= { accIpsecSAConfigEntry 10 }
accIpsecSAConfigSharedAuthSecret                OBJECT-TYPE
                SYNTAX  OCTET STRING
                ACCESS  read-write
                STATUS  mandatory
DESCRIPTION     "Shared authentication key for the SA"
        DEFVAL  { "" }
            ::= { accIpsecSAConfigEntry 11 }
accIpsecSAConfigEncrAlgorithm   OBJECT-TYPE
                SYNTAX  INTEGER 
                                { none(1), null(2), cast(3), blowfish(4), des(5), des3(6) }
                ACCESS  read-write
                STATUS  mandatory
        DESCRIPTION     "The encryption algorithm to be used"
        DEFVAL  { none }
            ::= { accIpsecSAConfigEntry 12 }
accIpsecSAConfigSharedEncrSecret        OBJECT-TYPE
        SYNTAX  OCTET STRING
        ACCESS  read-write
        STATUS  mandatory
        DESCRIPTION     "Shared encryption key for the SA"
        DEFVAL  { "" }
            ::= { accIpsecSAConfigEntry 13 }
accIpsecSAConfigPriority        OBJECT-TYPE
        SYNTAX  INTEGER 
                        { high(1), medium(2), low(3) }
        ACCESS  read-write
        STATUS  mandatory
        DESCRIPTION     "Priority of the SA"
        DEFVAL  { medium }
           ::= { accIpsecSAConfigEntry 14 }
accIpsecSAConfigSequenceNumber          OBJECT-TYPE
        SYNTAX  INTEGER
        ACCESS  read-write
        STATUS  mandatory
        DESCRIPTION     "The sequence number to be used in the next IPSec message 
                                to be sent, or the smallest acceptable sequence number in
                                an IPSec message to be received"
        DEFVAL  { 1 }
            ::= { accIpsecSAConfigEntry 15 }
accIpsecSAConfigStatus          OBJECT-TYPE
                SYNTAX  RowStatus
                ACCESS  read-write
                STATUS  mandatory
DESCRIPTION     "The current status of this entry"
            ::= { accIpsecSAConfigEntry 16 }
accIpsecSAStatsTable OBJECT-TYPE
        SYNTAX  SEQUENCE OF AccIpsecSAStatsEntry
        ACCESS  not-accessible
        STATUS  mandatory
        DESCRIPTION ""
        ::= { accIpsecSAStats 1 }
accIpsecSAStatsEntry OBJECT-TYPE
        SYNTAX  AccIpsecSAStatsEntry
        ACCESS  not-accessible
        STATUS  mandatory
        DESCRIPTION ""
        INDEX { accIpsecSAStatsIndex }
        ::= { accIpsecSAStatsTable 1 }
AccIpsecSAStatsEntry    ::= SEQUENCE  {
        accIpsecSAStatsIndex            OCTET STRING,
        accIpsecSAStatsOKPackets        Counter,
        accIpsecSAStatsNotOKPackets     Counter,
        accIpsecSAStatsCurrTicks        TimeTicks,
        accIpsecSAStatsCurrBytes        Counter
}
accIpsecSAStatsIndex    OBJECT-TYPE
                SYNTAX  OCTET STRING
                ACCESS  read-write
                STATUS  mandatory
        DESCRIPTION     "The name of the SA entry"
            ::= { accIpsecSAStatsEntry 1 }
accIpsecSAStatsOKPackets                OBJECT-TYPE
        SYNTAX  Counter
        ACCESS  read-only
        STATUS  mandatory
        DESCRIPTION     "Number of correct packets processed"
            ::= { accIpsecSAStatsEntry 2 }
accIpsecSAStatsNotOKPackets             OBJECT-TYPE
        SYNTAX  Counter
        ACCESS  read-only
        STATUS  mandatory
        DESCRIPTION     "Number of incorrect packets processed"
            ::= { accIpsecSAStatsEntry 3 }
accIpsecSAStatsCurrTicks                OBJECT-TYPE
        SYNTAX  TimeTicks
        ACCESS  read-only
        STATUS  mandatory
        DESCRIPTION     "The number of time ticks this SA has existed"
            ::= { accIpsecSAStatsEntry 4 }
accIpsecSAStatsCurrBytes                OBJECT-TYPE
                SYNTAX  Counter
                ACCESS  read-only
                STATUS  mandatory
DESCRIPTION     "The number of bytes this SA has processed"
           ::= { accIpsecSAStatsEntry 5 }
-- MOL_TRAP_ENHANCEMENTS
accIpsecTraps         OBJECT IDENTIFIER      ::= { accIpsec 5 }
accIpsecTrapMsg       OBJECT-TYPE
                SYNTAX  DisplayString
                ACCESS  read-only
                STATUS  mandatory
		DESCRIPTION     
			"Trap message object for level-1 traps of
			 Ipsec module "
           ::= { accIpsecTraps 1 }
-- END MOL_TRAP_ENHANCEMENTS

accIpSecsameSAIndxTrap TRAP-TYPE
        ENTERPRISE   accIpsecTraps 
        VARIABLES  { accIpsecTrapMsg,
                     accIpsecSAConfigIndex ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 1
accIpSecbadSAIndxTrap TRAP-TYPE
        ENTERPRISE   accIpsecTraps 
        VARIABLES  { accIpsecTrapMsg,
                     accIpsecSAConfigIndex ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 2
accIpSecexpKeyFldTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 3
accIpSecmsgSpiZeroTrap TRAP-TYPE
        ENTERPRISE   accIpsecTraps 
        VARIABLES  { accIpsecTrapMsg,
                     accIpsecSAConfigSPI ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 4
accIpSecauthencAlgoTrap TRAP-TYPE
        ENTERPRISE   accIpsecTraps 
        VARIABLES  { accIpsecTrapMsg,
                     accIpsecSAConfigAuthAlgorithm,
		     accIpsecSAConfigEncrAlgorithm ,
        accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 46 " 
 
            ::= 5
accIpSeccwauthAhAlgoTrap TRAP-TYPE
        ENTERPRISE   accIpsecTraps 
        VARIABLES  { accIpsecTrapMsg,
                     accIpsecSAConfigAuthAlgorithm ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 46 " 
 
            ::= 6
accIpSecmsgOflowOutTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 7 " 
 
            ::= 7
accIpSecdfTunnSATrap TRAP-TYPE
        ENTERPRISE   accIpsecTraps 
        VARIABLES  { accIpsecTrapMsg,
                     accIpsecSAConfigCopyDF ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 7 " 
 
            ::= 8
accIpSecdfNotSuppTrap TRAP-TYPE
        ENTERPRISE   accIpsecTraps 
        VARIABLES  { accIpsecTrapMsg,
                     accIpsecSAConfigCopyDF ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 7 " 
 
            ::= 9
accIpSecunsuppAlgoTrap TRAP-TYPE
        ENTERPRISE   accIpsecTraps 
        VARIABLES  { accIpsecTrapMsg,
                     accIpsecSAConfigEncrAlgorithm ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 7 " 
 
            ::= 10
accIpSecencAlgESPTrap TRAP-TYPE
        ENTERPRISE   accIpsecTraps 
        VARIABLES  { accIpsecTrapMsg,
                     accIpsecSAConfigEncrAlgorithm ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 46 " 
 
            ::= 11
accIpSecvldIPAddrTrap TRAP-TYPE
        ENTERPRISE   accIpsecTraps 
        VARIABLES  { accIpsecTrapMsg,
                     accIpsecSAConfigDestAddr ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 12
accIpSecipAddrSAInTrap TRAP-TYPE
        ENTERPRISE   accIpsecTraps 
        VARIABLES  { accIpsecTrapMsg,
                     accIpsecSAConfigDestAddr ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 13
accIpSecpeerGateAddrTrap TRAP-TYPE
        ENTERPRISE   accIpsecTraps 
        VARIABLES  { accIpsecTrapMsg,
                     accIpsecSAConfigDestAddr ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 14
accIpSeckeyLenZeroTrap TRAP-TYPE
        ENTERPRISE   accIpsecTraps 
        VARIABLES  { accIpsecTrapMsg,
                     accIpsecSAConfigAuthAlgorithm ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 15
accIpSecencKeyLenZeroTrap TRAP-TYPE
        ENTERPRISE   accIpsecTraps 
        VARIABLES  { accIpsecTrapMsg,
                     accIpsecSAConfigEncrAlgorithm ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 16
accIpSecseqZeroTrap TRAP-TYPE
        ENTERPRISE   accIpsecTraps 
        VARIABLES  { accIpsecTrapMsg,
                     accIpsecSAConfigSequenceNumber ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 17
accIpSecallocBytsFaildTrap TRAP-TYPE
        ENTERPRISE   accIpsecTraps 
        VARIABLES  { accIpsecTrapMsg ,
                      accTrapLogSeqNum}
        DESCRIPTION
              " 
SEVERITY-DEFAULT: Major 
EVENTTYPE-DEFAULT: 10 
ADDITIONAL-TEXT-VARIABLES: { accTrapLogSeqNum,accIpsecTrapMsg }
PCAUSE-DEFAULT: 32 " 
 
            ::= 18
accIpSecnoSpcSATrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 19
accIpSecsaNameLenTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 20
accIpSecauthKeyMaxTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 21
accIpSechmacMD5KeyLenTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 22
accIpSechmacSha1KeyLenTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 23
accIpSecencMaxKeyTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 24
accIpSecencKeyLenMaxPhyTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 25
accIpSecdesKeyLen8OctTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 26
accIpSec3desKeyLenTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 27
accIpSeccastKeyLenTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 28
accIpSecblowKeyTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 29
accIpSecsaAreaSzTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 30
accIpSecsameSPIAddrTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 31
accIpSecnotHexDigTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 32
accIpSecsecOddDigTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 33
accIpSecnoSANameTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 5 " 
 
            ::= 34
accIpSecsaInptFiltTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 46 " 
 
            ::= 35
accIpSecsaOtptFiltTrap TRAP-TYPE
        ENTERPRISE   accIpsecTraps 
        VARIABLES  { accIpsecTrapMsg ,
                      accTrapLogSeqNum}
        DESCRIPTION
              " 
SEVERITY-DEFAULT: Warning 
EVENTTYPE-DEFAULT: 10 
ADDITIONAL-TEXT-VARIABLES: { accTrapLogSeqNum,accIpsecTrapMsg }
PCAUSE-DEFAULT: 46 " 
 
            ::= 36
END
