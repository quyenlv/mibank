-- AXIS 1610 Network Print Server MIB.
-- Revision 2.02, Jul  3, 2000.
-- (C) Copyright 1998, Axis Communications AB, LUND, SWEDEN

AXIS-MIB { iso org(3) dod(6) internet(1) private(4) enterprises(1) 368   }
            DEFINITIONS ::= BEGIN
			IMPORTS
				enterprises, OBJECT-TYPE, IpAddress, Counter, Gauge,
				TimeTicks, mgmt                             FROM RFC1155-SMI
				DisplayString, PhysAddress                  FROM RFC1213-MIB
				TRAP-TYPE                                   FROM RFC-1215;
				
			mib-2         OBJECT IDENTIFIER ::= { mgmt 1 }
			snmp          OBJECT IDENTIFIER ::= { mib-2 11 }
			axis          OBJECT IDENTIFIER ::= { enterprises 368 }
			products      OBJECT IDENTIFIER ::= { axis 1 }
			print-server  OBJECT IDENTIFIER ::= { axis 2 }
			status        OBJECT IDENTIFIER ::= { print-server 1 }
			admin         OBJECT IDENTIFIER ::= { print-server 2 }
			setup         OBJECT IDENTIFIER ::= { print-server 3 }

			nps           OBJECT IDENTIFIER ::= { products 1 }

            config        OBJECT IDENTIFIER ::= { setup 1 }
            tcpip         OBJECT IDENTIFIER ::= { setup 2 }
            snmpcontrol   OBJECT IDENTIFIER ::= { setup 3 }
            netware       OBJECT IDENTIFIER ::= { setup 4 }
            lservlmgr     OBJECT IDENTIFIER ::= { setup 5 }
            apple         OBJECT IDENTIFIER ::= { setup 6 }
            logicals      OBJECT IDENTIFIER ::= { setup 7 }
            output        OBJECT IDENTIFIER ::= { setup 8 }
            panel         OBJECT IDENTIFIER ::= { setup 9 }
            nds-netware   OBJECT IDENTIFIER ::= { setup 10 }

            ports         OBJECT IDENTIFIER ::= { status 1 }


--- UNIT STATUS

        -- Printer Port Status

portNumber OBJECT-TYPE
        SYNTAX  INTEGER
        ACCESS  read-only
        STATUS  mandatory
        DESCRIPTION
        "The number of ports."
        ::= { ports 1 }


portTable OBJECT-TYPE
        SYNTAX  SEQUENCE OF PortEntry
        ACCESS  not-accessible
        STATUS  mandatory
        INDEX   { portIndex }
        ::= { ports 2 }

portEntry OBJECT-TYPE
        SYNTAX  PortEntry
        ACCESS  not-accessible
        STATUS  mandatory
        ::= { portTable 1 }

PortEntry ::= SEQUENCE {
    portIndex
        INTEGER,
    portDescr
        DisplayString,
    portOnLine
        INTEGER,
    portBusy
        INTEGER,
    portEndOfForms
        INTEGER,
    portFault
        INTEGER,
    portOutputBytes
        Gauge,
    portInputBytes
        Gauge,
    portPrintouts
        Counter,
    portAvailable
        INTEGER,
    portIsInput
        INTEGER
}

portIndex OBJECT-TYPE
        SYNTAX  INTEGER
        ACCESS  read-only
        STATUS  mandatory
        DESCRIPTION
        "The port's number."
        ::= { portEntry 1 }

portDescr OBJECT-TYPE
        SYNTAX  DisplayString
        ACCESS  read-only
        STATUS  mandatory
        DESCRIPTION
        "The port descriptor, name and type."
        ::= { portEntry 2 }

portOnLine OBJECT-TYPE
        SYNTAX  INTEGER {
                on-line(1),
                off-line(2),
                no-value(3)
        }
        ACCESS  read-only
        STATUS  mandatory
        DESCRIPTION
        "The port's On-Line status."
        ::= { portEntry 3 }

portBusy OBJECT-TYPE
        SYNTAX  INTEGER {
                ready(1),
                busy(2)
        }
        ACCESS  read-only
        STATUS  mandatory
        DESCRIPTION
        "The port's Busy status."
        ::= { portEntry 4 }

portEndOfForms OBJECT-TYPE
        SYNTAX  INTEGER {
                no-error(1),
                end-of-forms(2),
                no-value(3)
        }
        ACCESS  read-only
        STATUS  mandatory
        DESCRIPTION
        "The port's End-of-Forms status."
        ::= { portEntry 5 }

portFault OBJECT-TYPE
        SYNTAX  INTEGER {
                no-error(1),
                fault(2),
                no-value(3)
        }
        ACCESS  read-only
        STATUS  mandatory
        DESCRIPTION
        "The port's Fault status."
        ::= { portEntry 6 }

portOutputBytes OBJECT-TYPE
        SYNTAX  Counter
        ACCESS  read-only
        STATUS  mandatory
        DESCRIPTION
        "The number of bytes sent out on the port during
         a printout in progress or the last printout."
        ::= { portEntry 7 }

portInputBytes OBJECT-TYPE
        SYNTAX  Counter
        ACCESS  read-only
        STATUS  mandatory
        DESCRIPTION
        "The number of bytes received on the port during
         a printout in progress or the last printout."
        ::= { portEntry 8 }

portPrintouts OBJECT-TYPE
        SYNTAX  Counter
        ACCESS  read-only
        STATUS  mandatory
        DESCRIPTION
        "The number of printouts started on the port."
        ::= { portEntry 9 }

portAvailable OBJECT-TYPE
        SYNTAX  INTEGER {
                available(1),
                printing(2)
        }
        ACCESS  read-only
        STATUS  mandatory
        DESCRIPTION
        "If the port is assigned for a printout."
        ::= { portEntry 10 }

portIsInput OBJECT-TYPE
        SYNTAX  INTEGER {
                no(1),
                yes(2)
        }
        ACCESS  read-only
        STATUS  mandatory
        DESCRIPTION
        "If the port is assigned as an input port (bidirectional)."
        ::= { portEntry 11 }

PortStats ::= SEQUENCE {
  portIndex  INTEGER,
  portOutputBytes Counter,
  portInputBytes  Counter
}

--- UNIT ADMINISTRATION

AdminMenu ::= SEQUENCE {
        adminUnitStatus
           INTEGER,
        adminConfigStatus
           INTEGER,
        adminOldIntAddr
           IpAddress
}

adminUnitStatus OBJECT-TYPE
        SYNTAX  INTEGER {
                running(1),
                softReset(2),
                hardReset(3)
        }
        ACCESS  read-write
        STATUS  mandatory
        DESCRIPTION
        "The units's operational status.
         A other than (1) will reset the unit."
        ::= { admin 1 }

adminConfigStatus OBJECT-TYPE
        SYNTAX  INTEGER {
                configUnknown(1),
                configUnknown(2),
                configLoadRequest(3),
                configSaveRequest(4),
                configDefaultRequest(5)
        }
        ACCESS  read-write
        STATUS  mandatory
        DESCRIPTION
        "The units's configuration status.
         read-only values:
           (1) reserved for future use.
           (2) reserved for future use.
         write-only values :
           (3) will load permanent values .
           (4) will save current configuration permanently.
           (5) load default configuration."
        ::= { admin 2 }

adminOldIntAddr OBJECT-TYPE
        SYNTAX  IpAddress
        ACCESS  read-only
        STATUS  mandatory
        DESCRIPTION
        "The Internet Address at power-on or before change by
         RARP or 'arp -s'."
        ::= { admin 3 }



--- UNIT CONFIGURATION

--- The objects correspond to the parameters of the product.

        -- CONFIG MENU

ConfigMenu ::= SEQUENCE {
        ethAddr
           PhysAddress,
        rootPwd
           DisplayString,
        users
           DisplayString,
        hpJetadmin
           INTEGER,
        axisPrintSystem
           INTEGER,
        defOut
           INTEGER,
        baseUrl
           DisplayString
}

ethAddr OBJECT-TYPE
        SYNTAX  PhysAddress
        ACCESS  read-only
        STATUS  mandatory
        DESCRIPTION
        "The Ethernet Address."
        ::= { config 2 }

rootPwd OBJECT-TYPE
        SYNTAX  DisplayString
        ACCESS  read-write
        STATUS  mandatory
        DESCRIPTION
        "The Root Password."
        ::= { config 7 }

users   OBJECT-TYPE
        SYNTAX  DisplayString
        ACCESS  read-write
        STATUS  mandatory
        DESCRIPTION
        "The User Defintions."
        ::= { config 8 }

hpJetadmin OBJECT-TYPE
        SYNTAX INTEGER {
                yes(1),
                no(2)
        }
        ACCESS  read-write
        STATUS  mandatory
        DESCRIPTION
        "HP JetAdmin Support."
        ::= { config 13 }

axisPrintSystem OBJECT-TYPE
        SYNTAX INTEGER {
                no(1),
                yes(2)
        }
        ACCESS  read-write
        STATUS  mandatory
        DESCRIPTION
        "The AXIS Print System enable switch."
        ::= { config 15 }

defOut OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "Internal Printout Destination."
        ::= { config 60 }

baseUrl OBJECT-TYPE
        SYNTAX  DisplayString
        ACCESS  read-write
        STATUS  mandatory
        DESCRIPTION
        "The base URL."
        ::= { config 17 }
        
        -- TCPIP MENU

TCPIPMenu ::= SEQUENCE {
        intAddr
           IpAddress,
        defRout
           IpAddress,
        netMask
           IpAddress,
        tcpEnb
           INTEGER,
        tcpKey
           OCTET STRING,
        prosPwd
           DisplayString,
        prosPrt
           INTEGER,
        lpdBanner
           INTEGER,
        rtnOpt
           INTEGER,
        rTelPr1
           INTEGER,
        rTelPr2
           INTEGER,
        rTelPr3
           INTEGER,
        rTelPr4
           INTEGER,
        rTelPr5
           INTEGER,
        rTelPr6
           INTEGER,
        rTelPr7
           INTEGER,
        rTelPr8
           INTEGER,
        dnsEnb
           INTEGER,
        dnsPrimaryAddr
           IpAddress,
        dnsSecondaryAddr
           IpAddress,
        ipDomain
           DisplayString,
        slpScopeList
           DisplayString,
        winsEnb
           INTEGER,
        winsPrimaryAddr
           IpAddress,
        winsSecondaryAddr
           IpAddress,
        nbtScopeId
           DisplayString,
        dhcpEnb
           INTEGER,
        bootpEnb
           INTEGER,
        rarpEnb
           INTEGER
}


intAddr OBJECT-TYPE
        SYNTAX  IpAddress
        ACCESS  read-write
        STATUS  mandatory
        DESCRIPTION
        "The Internet Address."
        ::= { tcpip 1 }

defRout OBJECT-TYPE
        SYNTAX  IpAddress
        ACCESS  read-write
        STATUS  mandatory
        DESCRIPTION
        "The Default Router."
        ::= { tcpip 3 }

netMask OBJECT-TYPE
        SYNTAX  IpAddress
        ACCESS  read-write
        STATUS  mandatory
        DESCRIPTION
        "The Net Mask."
        ::= { tcpip 4 }

tcpEnb  OBJECT-TYPE
        SYNTAX  INTEGER {
                no(1),
                yes(2)
        }
        ACCESS  read-write
        STATUS  mandatory
        DESCRIPTION
        "The TCP protocol stack enable switch."
        ::= { tcpip 5 }

tcpKey  OBJECT-TYPE
        SYNTAX  OCTET STRING
        ACCESS  read-write
        STATUS  mandatory
        DESCRIPTION
        "The TCP protocol stack enable software key."
        ::= { tcpip 6 }

prosPwd OBJECT-TYPE
        SYNTAX  DisplayString
        ACCESS  read-write
        STATUS  mandatory
        DESCRIPTION
        "The PROS password."
        ::= { tcpip 9 }

prosPrt OBJECT-TYPE
        SYNTAX  INTEGER
        ACCESS  read-write
        STATUS  mandatory
        DESCRIPTION
        "The PROS TCP Port."
        ::= { tcpip 11 }

lpdBanner OBJECT-TYPE
        SYNTAX  INTEGER {
                off(0),
                auto(1),
                last(2)
        }
        ACCESS  read-write
        STATUS  mandatory
        DESCRIPTION
        "The LPD banner page switch."
        ::= { tcpip 12 }

rtnOpt  OBJECT-TYPE
        SYNTAX  INTEGER {
                no(1),
                yes(2)
        }
        ACCESS  read-write
        STATUS  mandatory
        DESCRIPTION
        "The Reverse Telnet option handling switch."
        ::= { tcpip 18 }

rTelPr1 OBJECT-TYPE
        SYNTAX INTEGER
        ACCESS  read-write
        STATUS  mandatory
        DESCRIPTION
        "The TCP port for reverse Telnet to logical printer 1."
        ::= { tcpip 601 }

rTelPr2 OBJECT-TYPE
        SYNTAX INTEGER
        ACCESS  read-write
        STATUS  mandatory
        DESCRIPTION
        "The TCP port for reverse Telnet to logical printer 2."
        ::= { tcpip 602 }

rTelPr3 OBJECT-TYPE
        SYNTAX INTEGER
        ACCESS  read-write
        STATUS  mandatory
        DESCRIPTION
        "The TCP port for reverse Telnet to logical printer 3."
        ::= { tcpip 603 }

rTelPr4 OBJECT-TYPE
        SYNTAX INTEGER
        ACCESS  read-write
        STATUS  mandatory
        DESCRIPTION
        "The TCP port for reverse Telnet to logical printer 4."
        ::= { tcpip 604 }

rTelPr5 OBJECT-TYPE
        SYNTAX INTEGER
        ACCESS  read-write
        STATUS  mandatory
        DESCRIPTION
        "The TCP port for reverse Telnet to logical printer 5."
        ::= { tcpip 605 }

rTelPr6 OBJECT-TYPE
        SYNTAX INTEGER
        ACCESS  read-write
        STATUS  mandatory
        DESCRIPTION
        "The TCP port for reverse Telnet to logical printer 6."
        ::= { tcpip 606 }

rTelPr7 OBJECT-TYPE
        SYNTAX INTEGER
        ACCESS  read-write
        STATUS  mandatory
        DESCRIPTION
        "The TCP port for reverse Telnet to logical printer 7."
        ::= { tcpip 607 }

rTelPr8 OBJECT-TYPE
        SYNTAX INTEGER
        ACCESS  read-write
        STATUS  mandatory
        DESCRIPTION
        "The TCP port for reverse Telnet to logical printer 8."
        ::= { tcpip 608 }

dnsEnb OBJECT-TYPE
        SYNTAX  INTEGER {
                no(1),
                yes(2)
        }
        ACCESS  read-write
        STATUS  mandatory
        DESCRIPTION
        "The DNS on/off switch."
        ::= { tcpip 670 }

dnsPrimaryAddr OBJECT-TYPE
        SYNTAX  IpAddress
        ACCESS  read-write
        STATUS  mandatory
        DESCRIPTION
        "The Primary DNS Server Address."
        ::= { tcpip 671 }

dnsSecondaryAddr OBJECT-TYPE
        SYNTAX  IpAddress
        ACCESS  read-write
        STATUS  mandatory
        DESCRIPTION
        "The Secondary DNS Server Address."
        ::= { tcpip 672 }

ipDomain OBJECT-TYPE
        SYNTAX  DisplayString
        ACCESS  read-write
        STATUS  mandatory
        DESCRIPTION
        "The Domain Name."
        ::= { tcpip 673 }

slpScopeList OBJECT-TYPE
        SYNTAX  DisplayString
        ACCESS  read-write
        STATUS  mandatory
        DESCRIPTION
        "The SLP Scope List."
        ::= { tcpip 680 }

winsEnb OBJECT-TYPE
        SYNTAX  INTEGER {
                no(1),
                yes(2)
        }
        ACCESS  read-write
        STATUS  mandatory
        DESCRIPTION
        "The WINS on/off switch."
        ::= { tcpip 692 }

winsPrimaryAddr OBJECT-TYPE
        SYNTAX  IpAddress
        ACCESS  read-write
        STATUS  mandatory
        DESCRIPTION
        "The Primary WINS Server Address."
        ::= { tcpip 693 }

winsSecondaryAddr OBJECT-TYPE
        SYNTAX  IpAddress
        ACCESS  read-write
        STATUS  mandatory
        DESCRIPTION
        "The Secondary WINS Server Address."
        ::= { tcpip 694 }

nbtScopeId OBJECT-TYPE
        SYNTAX  DisplayString
        ACCESS  read-write
        STATUS  mandatory
        DESCRIPTION
        "The NBT Scope ID."
        ::= { tcpip 695 }

dhcpEnb OBJECT-TYPE
        SYNTAX  INTEGER {
                no(1),
                yes(2)
        }
        ACCESS  read-write
        STATUS  mandatory
        DESCRIPTION
        "The dhcp on/off switch."
        ::= { tcpip 696 }

bootpEnb OBJECT-TYPE
        SYNTAX  INTEGER {
                no(1),
                yes(2)
        }
        ACCESS  read-write
        STATUS  mandatory
        DESCRIPTION
        "The bootp on/off switch."
        ::= { tcpip 698 }

rarpEnb OBJECT-TYPE
        SYNTAX  INTEGER {
                no(1),
                yes(2)
        }
        ACCESS  read-write
        STATUS  mandatory
        DESCRIPTION
        "The rarp on/off switch."
        ::= { tcpip 699 }


        -- SNMP MENU

SnmpMenu ::= SEQUENCE {
        readCommunity
           DisplayString,
        writeCommunity
           DisplayString,
        trapAddress
           IpAddress,
        trapCommunity
           DisplayString,
        enableAuthenTraps
           INTEGER,
        enablePrinterTraps
           INTEGER
}

readCommunity OBJECT-TYPE
        SYNTAX  DisplayString
        ACCESS  read-write
        STATUS  mandatory
        DESCRIPTION
        "The community having read-only access to all
         objects except WriteCommunity."
        ::= { snmpcontrol 701 }

writeCommunity OBJECT-TYPE
        SYNTAX  DisplayString
        ACCESS  read-write
        STATUS  mandatory
        DESCRIPTION
        "The community having full access to all objects."
        ::= { snmpcontrol 702 }

trapAddress OBJECT-TYPE
        SYNTAX  IpAddress
        ACCESS  read-write
        STATUS  mandatory
        DESCRIPTION
        "The IP address to send traps to. No traps if set to 0.0.0.0 ."
        ::= { snmpcontrol 705 }

trapCommunity OBJECT-TYPE
        SYNTAX  DisplayString
        ACCESS  read-write
        STATUS  mandatory
        DESCRIPTION
        "The community used when sending traps."
        ::= { snmpcontrol 706 }

enableAuthenTraps OBJECT-TYPE
        SYNTAX  INTEGER {
                enabled(1),
                disabled(2)
        }
        ACCESS  read-write
        STATUS  mandatory
        DESCRIPTION
        "Same as snmpEnableAuthenTraps in MIB-II."
        ::= { snmpcontrol 715 }

enablePrinterTraps OBJECT-TYPE
        SYNTAX  INTEGER {
                enabled(1),
                disabled(2)
        }
        ACCESS  read-write
        STATUS  mandatory
        DESCRIPTION
        "Enables the enterprise specific 'trapPrinter' traps."
        ::= { snmpcontrol 716 }


        -- NETWARE MENU

NetwareMenu ::= SEQUENCE {
        netwEnb
           INTEGER,
        psName
           DisplayString,
        confServ
           DisplayString,
        psPoll
           INTEGER,
        autoScan
           INTEGER,
        fr-802-3
           INTEGER,
        fr-eth-2
           INTEGER,
        fr-802-2
           INTEGER,
        fr-snap
           INTEGER,
        login1
           DisplayString,
        login2
           DisplayString,
        login3
           DisplayString,
        login4
           DisplayString,
        login5
           DisplayString,
        login6
           DisplayString,
        login7
           DisplayString,
        login8
           DisplayString,
        login9
           DisplayString,
        login10
           DisplayString,
        login11
           DisplayString,
        login12
           DisplayString,
        login13
           DisplayString,
        login14
           DisplayString,
        login15
           DisplayString,
        login16
           DisplayString,
        rprinter1
           DisplayString,
        rprinter2
           DisplayString,
        rprinter3
           DisplayString,
        rprinter4
           DisplayString,
        rprinter5
           DisplayString,
        rprinter6
           DisplayString,
        rprinter7
           DisplayString,
        rprinter8
           DisplayString
}


netwEnb OBJECT-TYPE
        SYNTAX INTEGER {
                no(1),
                yes(2)
        }
        ACCESS  read-write
        STATUS  mandatory
        DESCRIPTION
        "The NetWare protocol stack enable switch."
        ::= { netware 400 }

psName  OBJECT-TYPE
        SYNTAX DisplayString
        ACCESS  read-write
        STATUS  mandatory
        DESCRIPTION
        "The NetWare print server name."
        ::= { netware 401 }

confServ OBJECT-TYPE
        SYNTAX DisplayString
        ACCESS  read-write
        STATUS  mandatory
        DESCRIPTION
        "The NetWare configuration file server name."
        ::= { netware 402 }

psPoll  OBJECT-TYPE
        SYNTAX INTEGER (1..255)
        ACCESS  read-write
        STATUS  mandatory
        DESCRIPTION
        "The NetWare print server poll time."
        ::= { netware 405 }

autoScan OBJECT-TYPE
        SYNTAX INTEGER {
                off(1),
                pserver(2),
                rprinter(3),
                both(4)
        }
        ACCESS  read-write
        STATUS  mandatory
        DESCRIPTION
        "Determines scanning mode of print server."
        ::= { netware 406 }

fr-802-3 OBJECT-TYPE
        SYNTAX INTEGER {
                no(1),
                yes(2)
        }
        ACCESS  read-write
        STATUS  mandatory
        DESCRIPTION
        "The 802.3 frame support switch for NetWare."
        ::= { netware 420 }

fr-eth-2 OBJECT-TYPE
        SYNTAX INTEGER {
                no(1),
                yes(2)
        }
        ACCESS  read-write
        STATUS  mandatory
        DESCRIPTION
        "The Ethernet-2 frame support switch for NetWare."
        ::= { netware 421 }

fr-802-2 OBJECT-TYPE
        SYNTAX INTEGER {
                no(1),
                yes(2)
        }
        ACCESS  read-write
        STATUS  mandatory
        DESCRIPTION
        "The 802.2 frame support switch for NetWare."
        ::= { netware 422 }

fr-snap OBJECT-TYPE
        SYNTAX INTEGER {
                no(1),
                yes(2)
        }
        ACCESS  read-write
        STATUS  mandatory
        DESCRIPTION
        "The SNAP frame support switch for NetWare."
        ::= { netware 423 }

login1  OBJECT-TYPE
        SYNTAX DisplayString
        ACCESS  read-write
        STATUS  mandatory
        DESCRIPTION
        "File server, print queue and logical printer def. ."
        ::= { netware 432 }

login2  OBJECT-TYPE
        SYNTAX DisplayString
        ACCESS  read-write
        STATUS  mandatory
        DESCRIPTION
        "File server, print queue and logical printer def. ."
        ::= { netware 433 }

login3  OBJECT-TYPE
        SYNTAX DisplayString
        ACCESS  read-write
        STATUS  mandatory
        DESCRIPTION
        "File server, print queue and logical printer def. ."
        ::= { netware 434 }

login4  OBJECT-TYPE
        SYNTAX DisplayString
        ACCESS  read-write
        STATUS  mandatory
        DESCRIPTION
        "File server, print queue and logical printer def. ."
        ::= { netware 435 }

login5  OBJECT-TYPE
        SYNTAX DisplayString
        ACCESS  read-write
        STATUS  mandatory
        DESCRIPTION
        "File server, print queue and logical printer def. ."
        ::= { netware 436 }

login6  OBJECT-TYPE
        SYNTAX DisplayString
        ACCESS  read-write
        STATUS  mandatory
        DESCRIPTION
        "File server, print queue and logical printer def. ."
        ::= { netware 437 }

login7  OBJECT-TYPE
        SYNTAX DisplayString
        ACCESS  read-write
        STATUS  mandatory
        DESCRIPTION
        "File server, print queue and logical printer def. ."
        ::= { netware 438 }

login8  OBJECT-TYPE
        SYNTAX DisplayString
        ACCESS  read-write
        STATUS  mandatory
        DESCRIPTION
        "File server, print queue and logical printer def. ."
        ::= { netware 439 }

login9  OBJECT-TYPE
        SYNTAX DisplayString
        ACCESS  read-write
        STATUS  mandatory
        DESCRIPTION
        "File server, print queue and logical printer def. ."
        ::= { netware 440 }

login10 OBJECT-TYPE
        SYNTAX DisplayString
        ACCESS  read-write
        STATUS  mandatory
        DESCRIPTION
        "File server, print queue and logical printer def. ."
        ::= { netware 441 }

login11 OBJECT-TYPE
        SYNTAX DisplayString
        ACCESS  read-write
        STATUS  mandatory
        DESCRIPTION
        "File server, print queue and logical printer def. ."
        ::= { netware 442 }

login12 OBJECT-TYPE
        SYNTAX DisplayString
        ACCESS  read-write
        STATUS  mandatory
        DESCRIPTION
        "File server, print queue and logical printer def. ."
        ::= { netware 443 }

login13 OBJECT-TYPE
        SYNTAX DisplayString
        ACCESS  read-write
        STATUS  mandatory
        DESCRIPTION
        "File server, print queue and logical printer def. ."
        ::= { netware 444 }

login14 OBJECT-TYPE
        SYNTAX DisplayString
        ACCESS  read-write
        STATUS  mandatory
        DESCRIPTION
        "File server, print queue and logical printer def. ."
        ::= { netware 445 }

login15 OBJECT-TYPE
        SYNTAX DisplayString
        ACCESS  read-write
        STATUS  mandatory
        DESCRIPTION
        "File server, print queue and logical printer def. ."
        ::= { netware 446 }

login16 OBJECT-TYPE
        SYNTAX DisplayString
        ACCESS  read-write
        STATUS  mandatory
        DESCRIPTION
        "File server, print queue and logical printer def. ."
        ::= { netware 447 }

rprinter1 OBJECT-TYPE
        SYNTAX DisplayString
        ACCESS  read-write
        STATUS  mandatory
        DESCRIPTION
        "Pserver name and printer number on pserver."
        ::= { netware 470 }

rprinter2 OBJECT-TYPE
        SYNTAX DisplayString
        ACCESS  read-write
        STATUS  mandatory
        DESCRIPTION
        "Pserver name and printer number on pserver."
        ::= { netware 471 }

rprinter3 OBJECT-TYPE
        SYNTAX DisplayString
        ACCESS  read-write
        STATUS  mandatory
        DESCRIPTION
        "Pserver name and printer number on pserver."
        ::= { netware 472 }

rprinter4 OBJECT-TYPE
        SYNTAX DisplayString
        ACCESS  read-write
        STATUS  mandatory
        DESCRIPTION
        "Pserver name and printer number on pserver."
        ::= { netware 473 }

rprinter5 OBJECT-TYPE
        SYNTAX DisplayString
        ACCESS  read-write
        STATUS  mandatory
        DESCRIPTION
        "Pserver name and printer number on pserver."
        ::= { netware 474 }

rprinter6 OBJECT-TYPE
        SYNTAX DisplayString
        ACCESS  read-write
        STATUS  mandatory
        DESCRIPTION
        "Pserver name and printer number on pserver."
        ::= { netware 475 }

rprinter7 OBJECT-TYPE
        SYNTAX DisplayString
        ACCESS  read-write
        STATUS  mandatory
        DESCRIPTION
        "Pserver name and printer number on pserver."
        ::= { netware 476 }

rprinter8 OBJECT-TYPE
        SYNTAX DisplayString
        ACCESS  read-write
        STATUS  mandatory
        DESCRIPTION
        "Pserver name and printer number on pserver."
        ::= { netware 477 }


        -- LAN SERVER / LAN MANAGER MENU

LServLMgrMenu ::= SEQUENCE {
        lslmEnb
           INTEGER,
        lslmFrameType
           INTEGER,
        lPrint1
           DisplayString,
        lLogic1
           INTEGER,
        lPrint2
           DisplayString,
        lLogic2
           INTEGER,
        lPrint3
           DisplayString,
        lLogic3
           INTEGER,
        lPrint4
           DisplayString,
        lLogic4
           INTEGER,
        lPrint5
           DisplayString,
        lLogic5
           INTEGER,
        lPrint6
           DisplayString,
        lLogic6
           INTEGER,
        lPrint7
           DisplayString,
        lLogic7
           INTEGER,
        lPrint8
           DisplayString,
        lLogic8
           INTEGER
}

lslmEnb OBJECT-TYPE
        SYNTAX INTEGER {
                no(1),
                yes(2)
        }
        ACCESS  read-write
        STATUS  mandatory
        DESCRIPTION
        "The Lan Serv/Lan Mgr protocol stack enable switch."
        ::= { lservlmgr 800 }

lslmFrameType OBJECT-TYPE
        SYNTAX INTEGER {
                auto(1),
                fr-802-2(2),
                dix(3)
        }
        ACCESS  read-write
        STATUS  mandatory
        DESCRIPTION
        "Determines which frame type to use."
        ::= { lservlmgr 801 }

lPrint1 OBJECT-TYPE
        SYNTAX DisplayString
        ACCESS  read-write
        STATUS  mandatory
        DESCRIPTION
        "The Lan Serv/Lan Mgr printer 1 name."
        ::= { lservlmgr 810 }

lLogic1 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 1's logical printer."
        ::= { lservlmgr 811 }

lPrint2 OBJECT-TYPE
        SYNTAX DisplayString
        ACCESS  read-write
        STATUS  mandatory
        DESCRIPTION
        "The Lan Serv/Lan Mgr printer 1 name."
        ::= { lservlmgr 820 }

lLogic2 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 1's logical printer."
        ::= { lservlmgr 821 }

lPrint3 OBJECT-TYPE
        SYNTAX DisplayString
        ACCESS  read-write
        STATUS  mandatory
        DESCRIPTION
        "The Lan Serv/Lan Mgr printer 3 name."
        ::= { lservlmgr 830 }

lLogic3 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 3's logical printer."
        ::= { lservlmgr 831 }

lPrint4 OBJECT-TYPE
        SYNTAX DisplayString
        ACCESS  read-write
        STATUS  mandatory
        DESCRIPTION
        "The Lan Serv/Lan Mgr printer 4 name."
        ::= { lservlmgr 840 }

lLogic4 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 4's logical printer."
        ::= { lservlmgr 841 }

lPrint5 OBJECT-TYPE
        SYNTAX DisplayString
        ACCESS  read-write
        STATUS  mandatory
        DESCRIPTION
        "The Lan Serv/Lan Mgr printer 5 name."
        ::= { lservlmgr 850 }

lLogic5 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 5's logical printer."
        ::= { lservlmgr 851 }

lPrint6 OBJECT-TYPE
        SYNTAX DisplayString
        ACCESS  read-write
        STATUS  mandatory
        DESCRIPTION
        "The Lan Serv/Lan Mgr printer 6 name."
        ::= { lservlmgr 860 }

lLogic6 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 6's logical printer."
        ::= { lservlmgr 861 }

lPrint7 OBJECT-TYPE
        SYNTAX DisplayString
        ACCESS  read-write
        STATUS  mandatory
        DESCRIPTION
        "The Lan Serv/Lan Mgr printer 7 name."
        ::= { lservlmgr 870 }

lLogic7 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 7's logical printer."
        ::= { lservlmgr 871 }

lPrint8 OBJECT-TYPE
        SYNTAX DisplayString
        ACCESS  read-write
        STATUS  mandatory
        DESCRIPTION
        "The Lan Serv/Lan Mgr printer 8 name."
        ::= { lservlmgr 880 }

lLogic8 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The Lan Serv/Lan Mgr printer 8's logical printer."
        ::= { lservlmgr 881 }


        -- APPLETALK MENU

AppletalkMenu ::= SEQUENCE {
        atlkEnb
           INTEGER,
        atlkKey
           OCTET STRING,
        atlkZone
           DisplayString,
        atlkHPZoner
           INTEGER,
        atlkFont
           INTEGER,
        atlkBinary
           INTEGER,
        atlkBinaryType
           INTEGER,
        aPrint1
           DisplayString,
        aType1
           DisplayString,
        aLogic1
           INTEGER,
        aBinaryType1
           INTEGER,
        aPrint2
           DisplayString,
        aType2
           DisplayString,
        aLogic2
           INTEGER,
        aBinaryType2
           INTEGER,
        aPrint3
           DisplayString,
        aType3
           DisplayString,
        aLogic3
           INTEGER,
        aBinaryType3
           INTEGER
}

atlkEnb OBJECT-TYPE
        SYNTAX INTEGER {
                no(1),
                yes(2)
        }
        ACCESS  read-write
        STATUS  mandatory
        DESCRIPTION
        "The AppleTalk protocol stack enable switch."
        ::= { apple 500 }

atlkKey OBJECT-TYPE
        SYNTAX  OCTET STRING
        ACCESS  read-write
        STATUS  mandatory
        DESCRIPTION
        "The AppleTalk protocol stack software key."
        ::= { apple 501 }

atlkZone OBJECT-TYPE
        SYNTAX DisplayString
        ACCESS  read-write
        STATUS  mandatory
        DESCRIPTION
        "The AppleTalk zone name."
        ::= { apple 502 }

atlkHPZoner OBJECT-TYPE
        SYNTAX INTEGER {
                no(1),
                yes(2)
        } 
        ACCESS  read-write
        STATUS  mandatory
        DESCRIPTION
        "Enable/Disable support for HP Zoner."
        ::= { apple 503 }

atlkFont OBJECT-TYPE
        SYNTAX INTEGER {
                default(1),
                f35n(2),
                all(3)
        }
        ACCESS  read-write
        STATUS  mandatory
        DESCRIPTION
        "How to respond to a FontListQuery."
        ::= { apple 504 }

atlkBinary OBJECT-TYPE
        SYNTAX INTEGER {
                no(1),
                yes(2)
        }
        ACCESS  read-write
        STATUS  mandatory
        DESCRIPTION
        "Support binary files or not."
        ::= { apple 505 }

atlkBinaryType OBJECT-TYPE
        SYNTAX INTEGER {
                tbcp(1),
                bcp(2)
        }
        ACCESS  read-write
        STATUS  mandatory
        DESCRIPTION
        "Specifies which Binary Communications Protocol to use."
        ::= { apple 506 }

aPrint1 OBJECT-TYPE
        SYNTAX DisplayString
        ACCESS  read-write
        STATUS  mandatory
        DESCRIPTION
        "The AppleTalk printer 1 name."
        ::= { apple 510 }

aType1  OBJECT-TYPE
        SYNTAX DisplayString
        ACCESS  read-write
        STATUS  mandatory
        DESCRIPTION
        "The AppleTalk printer 1 type."
        ::= { apple 511 }

aLogic1 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The AppleTalk printer 1's logical printer."
        ::= { apple 512 }

aBinaryType1 OBJECT-TYPE
        SYNTAX INTEGER {
                tbcp(1),
                bcp(2),
                none(3)
        }
        ACCESS  read-write
        STATUS  mandatory
        DESCRIPTION
        "Specifies which Binary Communications Protocol to use 
        for AppleTalk printer 1."
        ::= { apple 513 }

aPrint2 OBJECT-TYPE
        SYNTAX DisplayString
        ACCESS  read-write
        STATUS  mandatory
        DESCRIPTION
        "The AppleTalk printer 2 name."
        ::= { apple 520 }

aType2  OBJECT-TYPE
        SYNTAX DisplayString
        ACCESS  read-write
        STATUS  mandatory
        DESCRIPTION
        "The AppleTalk printer 2 type."
        ::= { apple 521 }

aLogic2 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The AppleTalk printer 2's logical printer."
        ::= { apple 522 }

aBinaryType2 OBJECT-TYPE
        SYNTAX INTEGER {
                tbcp(1),
                bcp(2),
                none(3)
        }
        ACCESS  read-write
        STATUS  mandatory
        DESCRIPTION
        "Specifies which Binary Communications Protocol to use
        for AppleTalk printer 2."
        ::= { apple 523 }

aPrint3 OBJECT-TYPE
        SYNTAX DisplayString
        ACCESS  read-write
        STATUS  mandatory
        DESCRIPTION
        "The AppleTalk printer 3 name."
        ::= { apple 530 }

aType3  OBJECT-TYPE
        SYNTAX DisplayString
        ACCESS  read-write
        STATUS  mandatory
        DESCRIPTION
        "The AppleTalk printer 3 type."
        ::= { apple 531 }

aLogic3 OBJECT-TYPE
        SYNTAX INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The AppleTalk printer 3's logical printer."
        ::= { apple 532 }

aBinaryType3 OBJECT-TYPE
        SYNTAX INTEGER {
                tbcp(1),
                bcp(2),
                none(3)
        }
        ACCESS  read-write
        STATUS  mandatory
        DESCRIPTION
        "Specifies which Binary Communications Protocol to use
        for AppleTalk printer 3."
        ::= { apple 533 }


        -- PRINTERx MENU

logPrNumber OBJECT-TYPE
        SYNTAX  INTEGER
        ACCESS  read-only
        STATUS  mandatory
        DESCRIPTION
        "The number of logical printers."
        ::= { logicals 1 }


logPrTable OBJECT-TYPE
        SYNTAX  SEQUENCE OF LogPrEntry
        ACCESS  not-accessible
        STATUS  mandatory
        INDEX   { logPrIndex }
        ::= { logicals 2 }

logPrEntry OBJECT-TYPE
        SYNTAX  LogPrEntry
        ACCESS  not-accessible
        STATUS  mandatory
        ::= { logPrTable 1 }

LogPrEntry ::= SEQUENCE {
    logPrIndex
        INTEGER,
    logPrOut
        INTEGER,
    logPrScnd
        INTEGER,
    logPrWait
        INTEGER,
    logPrIn
        INTEGER,
    logPrBef
        OCTET STRING,
    logPrStr
        OCTET STRING,
    logPrCset
        INTEGER,
    logPrFilt
        INTEGER,
    logPrAft
        OCTET STRING,
    logPrDump
        INTEGER,
    logPrSize
        INTEGER,
    logPrOrnt
        INTEGER,
    logPrForm
        DisplayString,
    logPrFont
        DisplayString
}

logPrIndex OBJECT-TYPE
        SYNTAX  INTEGER
        ACCESS  read-only
        STATUS  mandatory
        DESCRIPTION
        "The logical printer's number."
        ::= { logPrEntry 1 }

logPrOut OBJECT-TYPE
        SYNTAX  INTEGER {
                lpt1(1),
                com1(2),
                lpt2(3)
        }
        ACCESS  read-write
        STATUS  mandatory
        DESCRIPTION
        "The logical printer's output port."
        ::= { logPrEntry 2 }

logPrScnd OBJECT-TYPE
        SYNTAX  INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The logical printer's secondary output port."
        ::= { logPrEntry 3 }

logPrWait OBJECT-TYPE
        SYNTAX  INTEGER {
                no(1),
                yes(2)
        }
        ACCESS  read-write
        STATUS  mandatory
        DESCRIPTION
        "The logical printer's wait for printer available switch."
        ::= { logPrEntry 4 }

logPrIn OBJECT-TYPE
        SYNTAX  INTEGER {
                com1(2),
                none(4),
                auto(5)
        }
        ACCESS  read-write
        STATUS  mandatory
        DESCRIPTION
        "The logical printer's input port. If set to auto, 
         the Print Server will try to use the port specified 
         as output port for both output and input."
        ::= { logPrEntry 5 }

logPrBef OBJECT-TYPE
        SYNTAX  OCTET STRING
        ACCESS  read-write
        STATUS  mandatory
        DESCRIPTION
        "The logical printer's string-before-job."
        ::= { logPrEntry 7 }

logPrStr OBJECT-TYPE
        SYNTAX  OCTET STRING
        ACCESS  read-write
        STATUS  mandatory
        DESCRIPTION
        "The logical printer's string-to-string substitution defs."
        ::= { logPrEntry 8 }

logPrCset OBJECT-TYPE
        SYNTAX  INTEGER {
                none(1),
                iso-to-ibm(2),
                uk-to-ibm7(3),
                sw-to-ibm7(4),
                ge-to-ibm7(5),
                fr-to-ibm7(6),
                nd-to-ibm7(7),
                dec-to-ibm(8)
        }
        ACCESS  read-write
        STATUS  mandatory
        DESCRIPTION
        "The logical printer's character set conversion table."
        ::= { logPrEntry 10 }

logPrFilt OBJECT-TYPE
        SYNTAX  INTEGER {
                none(1),
                postscr(2),
                autops(3)
        }
        ACCESS  read-write
        STATUS  mandatory
        DESCRIPTION
        "The logical printer's data stream filter."
        ::= { logPrEntry 11 }

logPrAft OBJECT-TYPE
        SYNTAX  OCTET STRING
        ACCESS  read-write
        STATUS  mandatory
        DESCRIPTION
        "The logical printer's string-after-job."
        ::= { logPrEntry 12 }

logPrDump OBJECT-TYPE
        SYNTAX  INTEGER {
                no(1),
                yes(2)
        }
        ACCESS  read-write
        STATUS  mandatory
        DESCRIPTION
        "The logical printer's hexdump filter."
        ::= { logPrEntry 14 }

logPrSize OBJECT-TYPE
        SYNTAX  INTEGER {
                a4(1),
                letter(2),
                legal(3),
                execut(4)
        }
        ACCESS  read-write
        STATUS  mandatory
        DESCRIPTION
        "The logical printer's ASCII-to-PostScript conversion page size."
        ::= { logPrEntry 17 }

logPrOrnt OBJECT-TYPE
        SYNTAX  INTEGER {
                portr(1),
                lands(2),
                rportr(3),
                rlands(4)
        }
        ACCESS  read-write
        STATUS  mandatory
        DESCRIPTION
        "The logical printer's ASCII-to-PostScript conversion
         page orientation."
        ::= { logPrEntry 18 }

logPrForm OBJECT-TYPE
        SYNTAX  DisplayString
        ACCESS  read-write
        STATUS  mandatory
        DESCRIPTION
        "The logical printer's ASCII-to-PostScript conversion
         page format."
        ::= { logPrEntry 19 }

logPrFont OBJECT-TYPE
        SYNTAX  DisplayString
        ACCESS  read-write
        STATUS  mandatory
        DESCRIPTION
        "The logical printer's PostScript font."
        ::= { logPrEntry 20 }


        -- OUTPUT MENU

OutputMenu ::= SEQUENCE {
        centrLPT1
           INTEGER,
        bsyTimLPT1
           INTEGER,
        mgmInfoLPT1
           INTEGER,
        comLPT1
           DisplayString,
        bidirLPT1
           INTEGER,
        readTimCOM1
           INTEGER,
        handshCOM1
           INTEGER,
        baudrCOM1
           INTEGER,
        stopBitsCOM1
           INTEGER,
        parityCOM1
           INTEGER,
        noBitsCOM1
           INTEGER,
        bsyTimCOM1
           INTEGER,
        mgmInfoCOM1
           INTEGER,
        comCOM1
           DisplayString,
        centrLPT2
           INTEGER,
        bsyTimLPT2
           INTEGER,
        mgmInfoLPT2
           INTEGER,
        comLPT2
           DisplayString,
        bidirLPT2
           INTEGER
}


centrLPT1 OBJECT-TYPE
        SYNTAX  INTEGER {
                ibmpc(1),
                stndrd(2),
                fast(3),
                hispeed(4)
        }
        ACCESS  read-write
        STATUS  mandatory
        DESCRIPTION
        "The LPT1 port speed."
        ::= { output 20 }

bsyTimLPT1 OBJECT-TYPE
        SYNTAX  INTEGER (0..255)
        ACCESS  read-write
        STATUS  mandatory
        DESCRIPTION
        "The LPT1 busy time-out."
        ::= { output 21 }

mgmInfoLPT1 OBJECT-TYPE
        SYNTAX  INTEGER {
                auto(1),
                disable(2)
        }
        ACCESS  read-write
        STATUS  mandatory
        DESCRIPTION
        "Get management information on LPT1."
        ::= { output 22 }

comLPT1 OBJECT-TYPE
        SYNTAX  DisplayString
        ACCESS  read-write
        STATUS  mandatory
        DESCRIPTION
        "Printer comment for printer on LPT1."
        ::= { output 23 }

bidirLPT1 OBJECT-TYPE
        SYNTAX  INTEGER {
                disable(1),
                auto(2)
        }
        ACCESS  read-write
        STATUS  mandatory
        DESCRIPTION
        "LPT1 bidirectional control."
        ::= { output 24 }

	
        -- Objects  readTimCOM1, handshCOM1, baudrCOM1, stopBitsCOM1, 
        -- parityCOM1, noBitsCOM1, bsyTimCOM1, mgmInfoCOM1, comCOM1,
        -- centrLPT2, bsyTimLPT2, mgmInfoLPT2, comLPT2 and bidirLPT2
        -- are not available in the pocket print servers.

readTimCOM1 OBJECT-TYPE
        SYNTAX  INTEGER (0..255)
        ACCESS  read-write
        STATUS  mandatory
        DESCRIPTION
        "The COM1 input time-out."
        ::= { output 27 }

handshCOM1 OBJECT-TYPE
        SYNTAX  INTEGER {
                none(1),
                xonxoff(2),
                robust(3),
                rdybsy(4),
                both(5),
                robustBoth(6)
        }
        ACCESS  read-write
        STATUS  mandatory
        DESCRIPTION
        "The COM1 handshake mode."
        ::= { output 29 }

baudrCOM1 OBJECT-TYPE
        SYNTAX  INTEGER {
                 b300(1),
                 b600(2),
                b1200(3),
                b2400(4),
                b4800(5),
                b9600(6),
               b19200(7),
               b38400(8),
               b57600(9),
              b115200(10)
        }
        ACCESS  read-write
        STATUS  mandatory
        DESCRIPTION
        "The COM1 baudrate.
         The settings b57600 and b115200 are not
         valid for all products, please refer to the
         corresponding User Manual."
        ::= { output 30 }

stopBitsCOM1 OBJECT-TYPE
        SYNTAX  INTEGER {
                one(1),
                two(2)
        }
        ACCESS  read-write
        STATUS  mandatory
        DESCRIPTION
        "The COM1 no of stopbits."
        ::= { output 31 }

parityCOM1 OBJECT-TYPE
        SYNTAX  INTEGER {
                none(1),
                odd(2),
                even(3)
        }
        ACCESS  read-write
        STATUS  mandatory
        DESCRIPTION
        "The COM1 no of parity bits."
        ::= { output 32 }

noBitsCOM1 OBJECT-TYPE
        SYNTAX  INTEGER {
                seven(1),
                eight(2)
        }
        ACCESS  read-write
        STATUS  mandatory
        DESCRIPTION
        "The COM1 no of bits."
        ::= { output 33 }

bsyTimCOM1 OBJECT-TYPE
        SYNTAX  INTEGER (0..255)
        ACCESS  read-write
        STATUS  mandatory
        DESCRIPTION
        "The COM1 busy time-out."
        ::= { output 34 }

mgmInfoCOM1 OBJECT-TYPE
        SYNTAX  INTEGER {
                auto(1),
                disable(2)
        }
        ACCESS  read-write
        STATUS  mandatory
        DESCRIPTION
        "Get management information on COM1."
        ::= { output 35 }

comCOM1 OBJECT-TYPE
        SYNTAX  DisplayString
        ACCESS  read-write
        STATUS  mandatory
        DESCRIPTION
        "Printer comment for printer on COM1."
        ::= { output 36 }

centrLPT2 OBJECT-TYPE
        SYNTAX  INTEGER {
                ibmpc(1),
                stndrd(2),
                fast(3),
                hispeed(4)
        }
        ACCESS  read-write
        STATUS  mandatory
        DESCRIPTION
        "The LPT2 port speed."
        ::= { output 40 }

bsyTimLPT2 OBJECT-TYPE
        SYNTAX  INTEGER (0..255)
        ACCESS  read-write
        STATUS  mandatory
        DESCRIPTION
        "The LPT2 busy time-out."
        ::= { output 41 }

mgmInfoLPT2 OBJECT-TYPE
        SYNTAX  INTEGER {
                auto(1),
                disable(2)
        }
        ACCESS  read-write
        STATUS  mandatory
        DESCRIPTION
        "Get management information on LPT2."
        ::= { output 42 }

comLPT2 OBJECT-TYPE
        SYNTAX  DisplayString
        ACCESS  read-write
        STATUS  mandatory
        DESCRIPTION
        "Printer comment for printer on LPT2."
        ::= { output 43 }

bidirLPT2 OBJECT-TYPE
        SYNTAX  INTEGER {
                disable(1),
                auto(2)
        }
        ACCESS  read-write
        STATUS  mandatory
        DESCRIPTION
        "LPT2 bidirectional control."
        ::= { output 44 }
	
	
        -- PANEL MENU

PanelMenu ::= SEQUENCE {
        defOut
           INTEGER
}


defOut  OBJECT-TYPE
        SYNTAX  INTEGER {
                pr1(1),
                pr2(2),
                pr3(3),
                pr4(4),
                pr5(5),
                pr6(6),
                pr7(7),
                pr8(8),
                lpt1(9),
                com1(10),
                lpt2(11)
        }
        ACCESS  read-write
        STATUS  mandatory
        DESCRIPTION
        "The default logical printer."
        ::= { panel 60 }


        -- NETWARE NDS MENU
        -- Some objects have a prefix to avoid collisions with the older
        -- NetWare menu

NDS-NetwareMenu ::= SEQUENCE {
        nds-netwEnb
           INTEGER,
        nds-psName
           DisplayString,
        jobCheckDelay
           INTEGER,
        confCheckDelay
           INTEGER,
        nds-fr-802-3
           INTEGER,
        nds-fr-eth-2
           INTEGER,
        nds-fr-802-2
           INTEGER,
        nds-fr-snap
           INTEGER,
        pserverNDS
           DisplayString,
        pserverBindery1
           DisplayString,
        pserverBindery2
           DisplayString,
        pserverBindery3
           DisplayString,
        pserverBindery4
           DisplayString,
        pserverBindery5
           DisplayString,
        pserverBindery6
           DisplayString,
        pserverBindery7
           DisplayString,
        pserverBindery8
           DisplayString,
        pserverBindery9
           DisplayString,
        pserverBindery10
           DisplayString,
        pserverBindery11
           DisplayString,
        pserverBindery12
           DisplayString,
        pserverBindery13
           DisplayString,
        pserverBindery14
           DisplayString,
        pserverBindery15
           DisplayString,
        pserverBindery16
           DisplayString,
        nprinter1
           DisplayString,
        nprinter2
           DisplayString,
        nprinter3
           DisplayString,
        nprinter4
           DisplayString,
        nprinter5
           DisplayString,
        nprinter6
           DisplayString,
        nprinter7
           DisplayString,
        nprinter8
           DisplayString
}


nds-netwEnb OBJECT-TYPE
        SYNTAX INTEGER {
                no(1),
                yes(2)
        }
        ACCESS  read-write
        STATUS  mandatory
        DESCRIPTION
        "The NetWare protocol stack enable switch."
        ::= { nds-netware 900 }

nds-psName  OBJECT-TYPE
        SYNTAX DisplayString
        ACCESS  read-write
        STATUS  mandatory
        DESCRIPTION
        "The print server name."
        ::= { nds-netware 901 }

nds-netwProt OBJECT-TYPE
        SYNTAX INTEGER {
                ipx(1),
                ip(2),
                dual(3)
        }
        ACCESS  read-write
        STATUS  mandatory
        DESCRIPTION
        "The NetWare protocol switch."
        ::= { nds-netware 902 }

jobCheckDelay OBJECT-TYPE
        SYNTAX  INTEGER (0..255)
        ACCESS  read-write
        STATUS  mandatory
        DESCRIPTION
        "Print queue polling interval."
        ::= { nds-netware 920 }

confCheckDelay OBJECT-TYPE
        SYNTAX  INTEGER (0..65535)
        ACCESS  read-write
        STATUS  mandatory
        DESCRIPTION
        "Configuration scanning interval."
        ::= { nds-netware 921 }

       -- Objects fr-802-3 and fr-eth-2 are not available in the
       -- Token Ring versions

nds-fr-802-3 OBJECT-TYPE
        SYNTAX INTEGER {
                no(1),
                yes(2)
        }
        ACCESS  read-write
        STATUS  mandatory
        DESCRIPTION
        "The 802.3 frame support switch for NetWare."
        ::= { nds-netware 910 }

nds-fr-eth-2 OBJECT-TYPE
        SYNTAX INTEGER {
                no(1),
                yes(2)
        }
        ACCESS  read-write
        STATUS  mandatory
        DESCRIPTION
        "The Ethernet-2 frame support switch for NetWare."
        ::= { nds-netware 911 }

nds-fr-802-2 OBJECT-TYPE
        SYNTAX INTEGER {
                no(1),
                yes(2)
        }
        ACCESS  read-write
        STATUS  mandatory
        DESCRIPTION
        "The 802.2 frame support switch for NetWare."
        ::= { nds-netware 912 }

nds-fr-snap OBJECT-TYPE
        SYNTAX INTEGER {
                no(1),
                yes(2)
        }
        ACCESS  read-write
        STATUS  mandatory
        DESCRIPTION
        "The SNAP frame support switch for NetWare."
        ::= { nds-netware 913 }

pserverNDS  OBJECT-TYPE
        SYNTAX DisplayString
        ACCESS  read-write
        STATUS  mandatory
        DESCRIPTION
        "Initial file server and NDS print server name."
        ::= { nds-netware 926 }

pserverBindery1  OBJECT-TYPE
        SYNTAX DisplayString
        ACCESS  read-write
        STATUS  mandatory
        DESCRIPTION
        "Bindery file server."
        ::= { nds-netware 930 }

pserverBindery2  OBJECT-TYPE
        SYNTAX DisplayString
        ACCESS  read-write
        STATUS  mandatory
        DESCRIPTION
        "Bindery file server."
        ::= { nds-netware 931 }

pserverBindery3  OBJECT-TYPE
        SYNTAX DisplayString
        ACCESS  read-write
        STATUS  mandatory
        DESCRIPTION
        "Bindery file server."
        ::= { nds-netware 932 }

pserverBindery4  OBJECT-TYPE
        SYNTAX DisplayString
        ACCESS  read-write
        STATUS  mandatory
        DESCRIPTION
        "Bindery file server."
        ::= { nds-netware 933 }

pserverBindery5  OBJECT-TYPE
        SYNTAX DisplayString
        ACCESS  read-write
        STATUS  mandatory
        DESCRIPTION
        "Bindery file server."
        ::= { nds-netware 934 }

pserverBindery6  OBJECT-TYPE
        SYNTAX DisplayString
        ACCESS  read-write
        STATUS  mandatory
        DESCRIPTION
        "Bindery file server."
        ::= { nds-netware 935 }

pserverBindery7  OBJECT-TYPE
        SYNTAX DisplayString
        ACCESS  read-write
        STATUS  mandatory
        DESCRIPTION
        "Bindery file server."
        ::= { nds-netware 936 }

pserverBindery8  OBJECT-TYPE
        SYNTAX DisplayString
        ACCESS  read-write
        STATUS  mandatory
        DESCRIPTION
        "Bindery file server."
        ::= { nds-netware 937 }

pserverBindery9  OBJECT-TYPE
        SYNTAX DisplayString
        ACCESS  read-write
        STATUS  mandatory
        DESCRIPTION
        "Bindery file server."
        ::= { nds-netware 938 }

pserverBindery10 OBJECT-TYPE
        SYNTAX DisplayString
        ACCESS  read-write
        STATUS  mandatory
        DESCRIPTION
        "Bindery file server."
        ::= { nds-netware 939 }

pserverBindery11 OBJECT-TYPE
        SYNTAX DisplayString
        ACCESS  read-write
        STATUS  mandatory
        DESCRIPTION
        "Bindery file server."
        ::= { nds-netware 940 }

pserverBindery12 OBJECT-TYPE
        SYNTAX DisplayString
        ACCESS  read-write
        STATUS  mandatory
        DESCRIPTION
        "Bindery file server."
        ::= { nds-netware 941 }

pserverBindery13 OBJECT-TYPE
        SYNTAX DisplayString
        ACCESS  read-write
        STATUS  mandatory
        DESCRIPTION
        "Bindery file server."
        ::= { nds-netware 942 }

pserverBindery14 OBJECT-TYPE
        SYNTAX DisplayString
        ACCESS  read-write
        STATUS  mandatory
        DESCRIPTION
        "Bindery file server."
        ::= { nds-netware 943 }

pserverBindery15 OBJECT-TYPE
        SYNTAX DisplayString
        ACCESS  read-write
        STATUS  mandatory
        DESCRIPTION
        "Bindery file server."
        ::= { nds-netware 944 }

pserverBindery16 OBJECT-TYPE
        SYNTAX DisplayString
        ACCESS  read-write
        STATUS  mandatory
        DESCRIPTION
        "Bindery file server."
        ::= { nds-netware 945 }

nprinter1 OBJECT-TYPE
        SYNTAX DisplayString
        ACCESS  read-write
        STATUS  mandatory
        DESCRIPTION
        "Pserver name and slot number on pserver."
        ::= { nds-netware 970 }

nprinter2 OBJECT-TYPE
        SYNTAX DisplayString
        ACCESS  read-write
        STATUS  mandatory
        DESCRIPTION
        "Pserver name and slot number on pserver."
        ::= { nds-netware 971 }

nprinter3 OBJECT-TYPE
        SYNTAX DisplayString
        ACCESS  read-write
        STATUS  mandatory
        DESCRIPTION
        "Pserver name and slot number on pserver."
        ::= { nds-netware 972 }

nprinter4 OBJECT-TYPE
        SYNTAX DisplayString
        ACCESS  read-write
        STATUS  mandatory
        DESCRIPTION
        "Pserver name and slot number on pserver."
        ::= { nds-netware 973 }

nprinter5 OBJECT-TYPE
        SYNTAX DisplayString
        ACCESS  read-write
        STATUS  mandatory
        DESCRIPTION
        "Pserver name and slot number on pserver."
        ::= { nds-netware 974 }

nprinter6 OBJECT-TYPE
        SYNTAX DisplayString
        ACCESS  read-write
        STATUS  mandatory
        DESCRIPTION
        "Pserver name and slot number on pserver."
        ::= { nds-netware 975 }

nprinter7 OBJECT-TYPE
        SYNTAX DisplayString
        ACCESS  read-write
        STATUS  mandatory
        DESCRIPTION
        "Pserver name and slot number on pserver."
        ::= { nds-netware 976 }

nprinter8 OBJECT-TYPE
        SYNTAX DisplayString
        ACCESS  read-write
        STATUS  mandatory
        DESCRIPTION
        "Pserver name and slot number on pserver."
        ::= { nds-netware 977 }


--- STANDARD TRAPS

coldStart TRAP-TYPE
        ENTERPRISE  snmp
        DESCRIPTION
        "A coldStart trap signifies that the sending
         protocol entity is reinitializing itself such
         that the agent's configuration or the protocol
         entity implementation may be altered."
        ::= 0

authenticationFailure TRAP-TYPE
        ENTERPRISE  snmp
        DESCRIPTION
        "An authenticationFailure trap signifies that
         the sending protocol entity is the addressee
         of a protocol message that is not properly
         authenticated.  While implementations of the
         SNMP must be capable of generating this trap,
         they must also be capable of suppressing the
         emission of such traps via an implementation-
         specific mechanism."
        ::= 4



--- PRIVATE ENTERPRISE TRAPS

trapPrinter TRAP-TYPE
        ENTERPRISE axis
        VARIABLES  { portIndex,
                     portDescr,
                     portOnLine,
                     portBusy,
                     portEndOfForms,
                     portFault }
        DESCRIPTION
        "A printer error has occurred."
        ::= 1

trapNewIPaddr TRAP-TYPE
        ENTERPRISE axis
        VARIABLES  { adminOldIntAddr }
        DESCRIPTION
        "The IP address has been changed by RARP or an 'arp -s'."
        ::= 2


        END
