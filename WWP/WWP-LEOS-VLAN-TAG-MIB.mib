--
 -- WWP-LEOS-VLAN-TAG-MIB.my
 --

 WWP-LEOS-VLAN-TAG-MIB DEFINITIONS ::= BEGIN

 IMPORTS                
   Counter32, TimeTicks, Integer32, Unsigned32, OBJECT-TYPE, MODULE-IDENTITY                       
        FROM SNMPv2-SMI                 
   DisplayString, MacAddress, TEXTUAL-CONVENTION, RowStatus                 
        FROM SNMPv2-TC                                                  
   wwpModulesLeos           
        FROM WWP-SMI;

        
 wwpLeosVlanMIB MODULE-IDENTITY
            LAST-UPDATED "200301151700Z"
            ORGANIZATION "World Wide Packets, Inc"
            CONTACT-INFO
                    "   Mib Meister
                        Postal: World Wide Packets
                        P.O. Box 950
                        Veradale, WA 99037
                        USA
                        Phone:  +1 509 242 9000
                        Email:  mib.meister@worldwidepackets.com"
            DESCRIPTION
                    "This MIB module defines the mgmt objects for the VLAN,
                    specific for the WWP products."  
            REVISION    "200301151700Z"
            DESCRIPTION
                    "Initial creation."
            ::= { wwpModulesLeos 5 }

 --
 -- Textual conventions
 --

 VlanId ::= TEXTUAL-CONVENTION
    STATUS      current
    DESCRIPTION
        "A Vlan Id represents a Broadcast Domain."
    SYNTAX      INTEGER (1..24576)
 
 VlanTag ::= TEXTUAL-CONVENTION
    STATUS      current
    DESCRIPTION
        "A 12-bit ID used in the VLAN Tag header."
    SYNTAX      INTEGER (1..4094)
 
 --
 -- Node definitions
 --
        
 wwpLeosVlanMIBObjects OBJECT IDENTIFIER ::= { wwpLeosVlanMIB 1 }

 wwpLeosVlan  OBJECT IDENTIFIER ::= { wwpLeosVlanMIBObjects 1 }
 
 wwpLeosVlanEPR OBJECT IDENTIFIER ::= { wwpLeosVlanMIBObjects 2 }
 
 
 -- Notifications 
  
 wwpLeosVlanMIBNotificationPrefix  OBJECT IDENTIFIER ::= { wwpLeosVlanMIB 2 } 
 wwpLeosVlanMIBNotifications       OBJECT IDENTIFIER ::=  
                       { wwpLeosVlanMIBNotificationPrefix 0 }

 -- Conformance information 
 
 wwpLeosVlanMIBConformance OBJECT IDENTIFIER ::= { wwpLeosVlanMIB 3 } 
 wwpLeosVlanMIBCompliances OBJECT IDENTIFIER ::= { wwpLeosVlanMIBConformance 1 }                
 wwpLeosVlanMIBGroups      OBJECT IDENTIFIER ::= { wwpLeosVlanMIBConformance 2 }
   
 wwpLeosMaxVlans OBJECT-TYPE
    SYNTAX      Unsigned32
    MAX-ACCESS  read-only
    STATUS      current
    DESCRIPTION
        "The maximum number of VLANs that this device
        supports."
    ::= { wwpLeosVlan 1 }
    
 wwpLeosMaxSupportedVlanTagId OBJECT-TYPE
    SYNTAX      Unsigned32
    MAX-ACCESS  read-only
    STATUS      current
    DESCRIPTION
        "The maximum value of VLAN Tag ID that this 
        device supports."
    ::= { wwpLeosVlan 2 }
    
 wwpLeosNumVlans OBJECT-TYPE
    SYNTAX      Unsigned32
    MAX-ACCESS  read-only
    STATUS      current
    DESCRIPTION
        "The current number of VLANs that are
        configured in this device."
    ::= { wwpLeosVlan 3 }
    
 wwpLeosVlanTable OBJECT-TYPE
     SYNTAX     SEQUENCE OF WwpLeosVlanEntry
     MAX-ACCESS not-accessible
     STATUS     current
     DESCRIPTION
            "The (conceptual) table listing the config 
            parameters for the VLAN."  
     ::= { wwpLeosVlan 4 }
                
 wwpLeosVlanEntry OBJECT-TYPE
     SYNTAX      WwpLeosVlanEntry
     MAX-ACCESS  not-accessible
     STATUS      current
     DESCRIPTION
           "An entry (conceptual row) in the wwpLeosVlanTable."
     INDEX { wwpLeosVlanId }
     ::= { wwpLeosVlanTable 1 }
                
 WwpLeosVlanEntry ::=  SEQUENCE { 
     wwpLeosVlanId                     VlanId,
     wwpLeosVlanName                   OCTET STRING,
     wwpLeosVlanStatus                 RowStatus,
     wwpLeosVlanMacLrnState		      INTEGER,
     wwpLeosVlanMacLrnOperState		   INTEGER
 }

 wwpLeosVlanId OBJECT-TYPE
     SYNTAX      VlanId
     MAX-ACCESS  read-only
     STATUS      current
     DESCRIPTION
             "A unique identifier for the VLAN."
     ::= { wwpLeosVlanEntry 1 }
                
 wwpLeosVlanName OBJECT-TYPE
     SYNTAX       OCTET STRING (SIZE (0..32))
     MAX-ACCESS   read-create
     STATUS       current
     DESCRIPTION
             "Name associated with this VLAN Entry."
     ::= { wwpLeosVlanEntry 2 }

 wwpLeosVlanStatus OBJECT-TYPE
     SYNTAX       RowStatus
     MAX-ACCESS   read-write
     STATUS       current
     DESCRIPTION
             "Used to manage the creation and deletion of the 
             conceptual rows in this table.

             To create a row in this table, a manager must
             set this object to 'createAndGo'. To delete a row in this
             table, there should not be any port/tag associated with 
             this vlan."
     ::= { wwpLeosVlanEntry 4 }  
 
 wwpLeosVlanMacLrnState OBJECT-TYPE
     SYNTAX       INTEGER {
     				enabled(1),
     				disabled(2)
     			  }
     MAX-ACCESS   read-write
     STATUS       current      
     DESCRIPTION
             "Setting this object will enable or disable Mac learning for the vlan."
     DEFVAL		  { enabled }
     ::= { wwpLeosVlanEntry 5 } 

 wwpLeosVlanMacLrnOperState OBJECT-TYPE
     SYNTAX       INTEGER {
     				enabled(1),
     				disabled(2)
     			  }
     MAX-ACCESS   read-only
     STATUS       current      
     DESCRIPTION
             "Displays the oper status of MAC learning."
     DEFVAL		  { enabled }
     ::= { wwpLeosVlanEntry 6 } 
     
 
     
 --
 --  The VLAN Membership Table
 --

 wwpLeosVlanTagMemberTable OBJECT-TYPE
     SYNTAX     SEQUENCE OF WwpLeosVlanTagMemberEntry
     MAX-ACCESS not-accessible
     STATUS     current
     DESCRIPTION
            "The (conceptual) table listing the config parameters 
            for the Members of the VLANs."
    ::= { wwpLeosVlan 5 }

 wwpLeosVlanTagMemberEntry OBJECT-TYPE
    SYNTAX     WwpLeosVlanTagMemberEntry
    MAX-ACCESS not-accessible
    STATUS     current
    DESCRIPTION
            "An entry (conceptual row) in the wwpLeosVlanTagMemberTable."
    INDEX      { wwpLeosVlanId, wwpLeosVlanMemberPortId, wwpLeosVlanMemberTagId }
    ::= { wwpLeosVlanTagMemberTable 1 }

 WwpLeosVlanTagMemberEntry ::= SEQUENCE {   
    wwpLeosVlanMemberPortId             INTEGER,
    wwpLeosVlanMemberTagId              VlanTag,    
    wwpLeosVlanMemberStatus             RowStatus
 }
 
 wwpLeosVlanMemberPortId   OBJECT-TYPE
     SYNTAX           INTEGER(1..65535)
     MAX-ACCESS       read-only
     STATUS           current
     DESCRIPTION
             "The port id to be associated with this VLAN."               
     ::= { wwpLeosVlanTagMemberEntry 1 }

 wwpLeosVlanMemberTagId   OBJECT-TYPE
     SYNTAX      VlanTag
     MAX-ACCESS  read-only
     STATUS      current
     DESCRIPTION
             "The VLAN Tag Id used by the port on this
             VLAN. If the switch is being used as a traditional 
             Layer 2 device, then the value of 
             wwpLeosVlanMemberTagId should be same as wwpLeosVlanMemberId."
     ::= { wwpLeosVlanTagMemberEntry 2 } 
     
 wwpLeosVlanMemberStatus OBJECT-TYPE
     SYNTAX         RowStatus
     MAX-ACCESS     read-create
     STATUS         current
     DESCRIPTION
             "Used to manage the creation and deletion of the 
             conceptual rows in this table.

             To create a row in this table, a manager must
             set this object to 'createAndGo'."
     ::= { wwpLeosVlanTagMemberEntry 4 }

 --
 -- VC Table
 -- 
 wwpLeosVlanCircuitTable OBJECT-TYPE
     SYNTAX     SEQUENCE OF WwpLeosVlanCircuitEntry
     MAX-ACCESS not-accessible
     STATUS     deprecated
     DESCRIPTION
            "The (conceptual) table listing the cirtual circuit table.
             To create entry use SNMP multiple set operation because 
             wwpLeosCircuitVlanId and wwpLeosCircuitType is mandatory 
             while creating entry in the table."
     ::= { wwpLeosVlan 6 }
     
 wwpLeosVlanCircuitEntry  OBJECT-TYPE
     SYNTAX       WwpLeosVlanCircuitEntry
     MAX-ACCESS   not-accessible
     STATUS       deprecated
     DESCRIPTION
             "The virtual circuit table entry index by virtual circuit index.
              To create entry use SNMP multiple set operation because 
              wwpLeosCircuitVlanId, wwpLeosCircuitName and wwpLeosCircuitType 
              is mandatory while creating entry in the table."
     INDEX { wwpLeosCircuitIndex}
     ::= { wwpLeosVlanCircuitTable 1 }
     
 WwpLeosVlanCircuitEntry ::=  SEQUENCE {
     wwpLeosCircuitIndex                        INTEGER,
     wwpLeosCircuitVlanId                       VlanId,
     wwpLeosCircuitType                         INTEGER,
     wwpLeosCircuitName                         OCTET STRING,
     wwpLeosCircuitPriority                     INTEGER,
     wwpLeosCircuitDataTunnelState              INTEGER,
     wwpLeosCircuitCtrlProtocolTunnelState      INTEGER,
     wwpLeosCircuitNumEndPoints                 INTEGER,
     wwpLeosCircuitStatus                       RowStatus
 }
 
 wwpLeosCircuitIndex OBJECT-TYPE
     SYNTAX      INTEGER (1..65535)
     MAX-ACCESS  read-only
     STATUS      deprecated
     DESCRIPTION
        "This represents the virtual circuit index in the table."
     ::= { wwpLeosVlanCircuitEntry 1 } 
  
 wwpLeosCircuitVlanId OBJECT-TYPE
     SYNTAX      VlanId
     MAX-ACCESS  read-write
     STATUS      deprecated
     DESCRIPTION
        "This represents the vlan id associated with virtual circuit index in the table."
     ::= { wwpLeosVlanCircuitEntry 2 }
  
 wwpLeosCircuitType OBJECT-TYPE
     SYNTAX      INTEGER {
                        ethernet(1),
                        mpls(2)
                 }
     MAX-ACCESS  read-write
     STATUS      deprecated
     DESCRIPTION
        "This represents the type of virtual circuit eth or mpls."
     ::= { wwpLeosVlanCircuitEntry 3 }

 wwpLeosCircuitName OBJECT-TYPE
     SYNTAX      OCTET STRING (SIZE (0..16))
     MAX-ACCESS  read-write
     STATUS      deprecated
     DESCRIPTION
        "This represents the name associated with the virtual circuit."
     ::= { wwpLeosVlanCircuitEntry 4 }
 
 wwpLeosCircuitPriority OBJECT-TYPE
     SYNTAX      INTEGER (0..7)
     MAX-ACCESS  read-write
     STATUS      deprecated
     DESCRIPTION
        "This represents the 802.1D priority associated with the virtual circuit."
     ::= { wwpLeosVlanCircuitEntry 5 }
 
 wwpLeosCircuitDataTunnelState OBJECT-TYPE
     SYNTAX      INTEGER {
                        on(1),
                        off(2)
                 }
     MAX-ACCESS  read-write
     STATUS      deprecated
     DESCRIPTION
        "This represents the data tunnel state associated with the virtual circuit.
         If set to 'on' will enable tunnel for data frames. If set to 'off' then it 
         will disable tunnel for data frames."
     ::= { wwpLeosVlanCircuitEntry 6 }
 
 wwpLeosCircuitCtrlProtocolTunnelState OBJECT-TYPE
     SYNTAX      INTEGER {
                        on(1),
                        off(2)
                 }
     MAX-ACCESS  read-write
     STATUS      deprecated
     DESCRIPTION
        "This represents the control frame tunnel state associated with the virtual circuit.
         If set to 'on' will enable tunnel for control frames. If set to 'off' then it 
         will disable tunnel for control frames."
     ::= { wwpLeosVlanCircuitEntry 7 }
 
 wwpLeosCircuitNumEndPoints OBJECT-TYPE
     SYNTAX      INTEGER (0..65535)
     MAX-ACCESS  read-only
     STATUS      deprecated
     DESCRIPTION
        "This represents the number of end points associated with this entry."
     ::= { wwpLeosVlanCircuitEntry 8 }

 wwpLeosCircuitStatus OBJECT-TYPE
     SYNTAX      RowStatus
     MAX-ACCESS  read-create
     STATUS      deprecated
     DESCRIPTION
        "Setting this object to 'createAndGo' will create the entry 
         and by default will enable control frame and data frame tunnel
         .       
         Setting this object to 'destroy' will delete the entry
         from the table for given vlan."
     ::= { wwpLeosVlanCircuitEntry 9 }

 --
 -- Vc Port Exclusive list
 --  
 wwpLeosVlanCircuitPortExclusiveTable OBJECT-TYPE
     SYNTAX     SEQUENCE OF WwpLeosVlanCircuitPortExclusiveEntry
     MAX-ACCESS not-accessible
     STATUS     deprecated
     DESCRIPTION
            "The (conceptual) table listing the l2 control frame tunnel status 
             on a vlan."
     ::= { wwpLeosVlan 7 }
     
 wwpLeosVlanCircuitPortExclusiveEntry  OBJECT-TYPE
     SYNTAX       WwpLeosVlanCircuitPortExclusiveEntry
     MAX-ACCESS   not-accessible
     STATUS       deprecated
     DESCRIPTION
             "The layer 2 control frame protocol tunnel entry for the vlan."
     INDEX { wwpLeosCircuitIndex, wwpLeosPortId}
     ::= { wwpLeosVlanCircuitPortExclusiveTable 1 }
     
 WwpLeosVlanCircuitPortExclusiveEntry ::=  SEQUENCE { 
     wwpLeosPortId                      INTEGER,
     wwpLeosPortExclusiveStatus         RowStatus
 }
 
 wwpLeosPortId OBJECT-TYPE
     SYNTAX      INTEGER (1..65535)
     MAX-ACCESS  read-only
     STATUS      deprecated
     DESCRIPTION
        "This specifies the port which is the end point for in this virtual circuit."
     ::= { wwpLeosVlanCircuitPortExclusiveEntry 1 }

 wwpLeosPortExclusiveStatus OBJECT-TYPE
     SYNTAX      RowStatus
     MAX-ACCESS  read-create
     STATUS      deprecated
     DESCRIPTION
        "Setting this object to 'createAndGo' will create the entry 
         and designate the port as end point of the virtual circuit.     
         Setting this object to 'destroy' will delete the entry
         from the table for given virtual circuit."
     ::= { wwpLeosVlanCircuitPortExclusiveEntry 2 }

--
-- l2 control frame protocol table
--
wwpLeosVlanCircuitCtrlProtocolTable OBJECT-TYPE
     SYNTAX     SEQUENCE OF WwpLeosVlanCircuitCtrlProtocolEntry
     MAX-ACCESS not-accessible
     STATUS     deprecated
     DESCRIPTION
            "The (conceptual) table listing the l2 control frame protocol status 
             tunnel for a given vlan."
     ::= { wwpLeosVlan 8 }
     
 wwpLeosVlanCircuitCtrlProtocolEntry  OBJECT-TYPE
     SYNTAX       WwpLeosVlanCircuitCtrlProtocolEntry
     MAX-ACCESS   not-accessible
     STATUS       deprecated
     DESCRIPTION
             "The layer 2 control frame protocol tunnel entry for the vlan."
     INDEX {wwpLeosCircuitIndex, wwpLeosVlanl2ProtocolNum}
     ::= { wwpLeosVlanCircuitCtrlProtocolTable 1 }
     
 WwpLeosVlanCircuitCtrlProtocolEntry ::=  SEQUENCE { 
     wwpLeosVlanl2ProtocolNum           INTEGER,
     wwpLeosVlanl2Type                  INTEGER
 }

  wwpLeosVlanl2ProtocolNum OBJECT-TYPE
     SYNTAX      INTEGER {                     
                     l28021x(1),
                     rstp(2),
                     ciscoCdp(3),
                     ciscoDtp(4),
                     ciscoPagp(5),
                     ciscoPvst(6),
                     ciscoUplinkFast(7),
                     ciscoUdlp(8),
                     ciscoVtp(9),
                     gvrp(10),
                     lacp(11),
                     lacpMarker(12),
                     lldp(13),
                     oam(14),
                     vlanBridge(15)                  
                 }
     MAX-ACCESS  read-only
     STATUS      deprecated
     DESCRIPTION
        "This object represent the list of protocols supported by 
         the device."
     ::= { wwpLeosVlanCircuitCtrlProtocolEntry 1 }

  wwpLeosVlanl2Type OBJECT-TYPE
     SYNTAX      INTEGER {
                     discard(1),
                     peer(2),
                     tunnel(3)               
                 }
     MAX-ACCESS  read-create
     STATUS      deprecated
     DESCRIPTION
        "Setting this object to 'discard' will cause wwpLeosProtocolNum
         frames arriving at the specified UNI to be discarded.  
         Setting this to 'peer' will cause the wwpLeosProtocolNum frame
         to be processed by the provider network and cause the provider 
         network to behave as a peer.  
         Setting this to 'tunnel' will cause the wwpLeosProtocolNum frame to be 
         tunneled."
     ::= { wwpLeosVlanCircuitCtrlProtocolEntry 2 }

--
-- l2 global stats
--
wwpLeosVlanCircuitStats OBJECT IDENTIFIER ::= { wwpLeosVlan 9 }

 wwpLeosVlanl2AllRxPkts OBJECT-TYPE
     SYNTAX      Counter32
     MAX-ACCESS  read-only
     STATUS      deprecated
     DESCRIPTION
        "Specifies total number of packets ingressed on vlan."
     ::= { wwpLeosVlanCircuitStats 1 }

 wwpLeosVlanl2AllTunneledPkts OBJECT-TYPE
     SYNTAX      Counter32
     MAX-ACCESS  read-only
     STATUS      deprecated
     DESCRIPTION
        "Specifies the total number of packets that were made 
         tunneled on the vlan."
     ::= { wwpLeosVlanCircuitStats 2 }

 wwpLeosVlanl2AllPeerPkts OBJECT-TYPE
     SYNTAX      Counter32
     MAX-ACCESS  read-only
     STATUS      deprecated
     DESCRIPTION
        "Specifies the total number of packets peered on the vlan."
     ::= { wwpLeosVlanCircuitStats 3 }

 wwpLeosVlanl2AllDiscardedPkts OBJECT-TYPE
     SYNTAX      Counter32
     MAX-ACCESS  read-only
     STATUS      deprecated
     DESCRIPTION
        "Specifies the total number of discarded packets on the vlan."
     ::= { wwpLeosVlanCircuitStats 4 }

 wwpLeosVlanl2AllDecodedPkts OBJECT-TYPE
     SYNTAX      Counter32
     MAX-ACCESS  read-only
     STATUS      deprecated
     DESCRIPTION
        "Specifies the total number of packets that came in 
         tunneled and then restored on the vlan."
     ::= { wwpLeosVlanCircuitStats 5 }

 wwpLeosVlanl2AllDecodedFailures OBJECT-TYPE
     SYNTAX      Counter32
     MAX-ACCESS  read-only
     STATUS      deprecated
     DESCRIPTION
        "Specifies the total number of packets that failed to 
         'untunnel' on the vlan."
     ::= { wwpLeosVlanCircuitStats 6 }

 wwpLeosVlanl2AllTunneledSubcriberPortPkts OBJECT-TYPE
     SYNTAX      Counter32
     MAX-ACCESS  read-only
     STATUS      deprecated
     DESCRIPTION
        "Specifies the total number of tunneled packets received 
         on subscriber port on the vlan."
     ::= { wwpLeosVlanCircuitStats 7 }

--
-- l2 control frame protocol table stats
--
 wwpLeosVlanCircuitProtocolStatsTable OBJECT-TYPE
     SYNTAX     SEQUENCE OF WwpLeosVlanCircuitProtocolStatsEntry
     MAX-ACCESS not-accessible
     STATUS     deprecated
     DESCRIPTION
            "The (conceptual) table listing the l2 control frame protocol stats 
             for a given vlan."
     ::= { wwpLeosVlan 10 }
     
 wwpLeosVlanCircuitProtocolStatsEntry  OBJECT-TYPE
     SYNTAX       WwpLeosVlanCircuitProtocolStatsEntry
     MAX-ACCESS   not-accessible
     STATUS       deprecated
     DESCRIPTION
             "The layer 2 control frame protocol stats entry for the vlan."
     INDEX { wwpLeosCircuitIndex, wwpLeosVlanl2ProtocolNum}
     ::= { wwpLeosVlanCircuitProtocolStatsTable 1 }
     
 WwpLeosVlanCircuitProtocolStatsEntry ::=  SEQUENCE { 
     wwpLeosVlanl2RxPkts                        Counter32,
     wwpLeosVlanl2TunneledPkts                  Counter32,
     wwpLeosVlanl2PeerPkts                      Counter32,
     wwpLeosVlanl2DiscardedPkts                 Counter32,
     wwpLeosVlanl2DecodedPkts                   Counter32,
     wwpLeosVlanl2DecodedFailures               Counter32,
     wwpLeosVlanl2TunneledSubcriberPortPkts     Counter32
 }

 wwpLeosVlanl2RxPkts OBJECT-TYPE
     SYNTAX      Counter32
     MAX-ACCESS  read-only
     STATUS      deprecated
     DESCRIPTION
        "Specifies number of packets ingressed matching protocol."
     ::= { wwpLeosVlanCircuitProtocolStatsEntry 1 }

 wwpLeosVlanl2TunneledPkts OBJECT-TYPE
     SYNTAX      Counter32
     MAX-ACCESS  read-only
     STATUS      deprecated
     DESCRIPTION
        "Specifies the number of packets that were made tunneled."
     ::= { wwpLeosVlanCircuitProtocolStatsEntry 2 }

 wwpLeosVlanl2PeerPkts OBJECT-TYPE
     SYNTAX      Counter32
     MAX-ACCESS  read-only
     STATUS      deprecated
     DESCRIPTION
        "Specifies the number of peered packets."
     ::= { wwpLeosVlanCircuitProtocolStatsEntry 3 }

 wwpLeosVlanl2DiscardedPkts OBJECT-TYPE
     SYNTAX      Counter32
     MAX-ACCESS  read-only
     STATUS      deprecated
     DESCRIPTION
        "Specifies the number of discarded packets."
     ::= { wwpLeosVlanCircuitProtocolStatsEntry 4 }

 wwpLeosVlanl2DecodedPkts OBJECT-TYPE
     SYNTAX      Counter32
     MAX-ACCESS  read-only
     STATUS      deprecated
     DESCRIPTION
        "Specifies the number of packets that came in 
         tunneled and then restored."
     ::= { wwpLeosVlanCircuitProtocolStatsEntry 5 }

 wwpLeosVlanl2DecodedFailures OBJECT-TYPE
     SYNTAX      Counter32
     MAX-ACCESS  read-only
     STATUS      deprecated
     DESCRIPTION
        "Specifies the number of packets that failed to 'untunnel'."
     ::= { wwpLeosVlanCircuitProtocolStatsEntry 6 }

 wwpLeosVlanl2TunneledSubcriberPortPkts OBJECT-TYPE
     SYNTAX      Counter32
     MAX-ACCESS  read-only
     STATUS      deprecated
     DESCRIPTION
        "Specifies the number of tunneled packets received 
         on subscriber port.."
     ::= { wwpLeosVlanCircuitProtocolStatsEntry 7 }
--
-- EPR
--
 wwpLeosVlanEPRTable OBJECT-TYPE
     SYNTAX     SEQUENCE OF WwpLeosVlanEPREntry
     MAX-ACCESS not-accessible
     STATUS     current
     DESCRIPTION
            "The (conceptual) table listing the egress port
            restriction parameters for the VLAN."  
     ::= { wwpLeosVlanEPR 1 }
     
 wwpLeosVlanEPREntry  OBJECT-TYPE
     SYNTAX       WwpLeosVlanEPREntry
     MAX-ACCESS   not-accessible
     STATUS       current
     DESCRIPTION
             "The egress port restriction entry for a vlan."
     INDEX { wwpLeosVlanId }
     ::= { wwpLeosVlanEPRTable 1 }
     
 WwpLeosVlanEPREntry ::=  SEQUENCE { 
     wwpLeosVlanEPRState             INTEGER    
 } 
 
 wwpLeosVlanEPRState OBJECT-TYPE
     SYNTAX      INTEGER {
                    enable(1),
                    disable(2)
                 }
     MAX-ACCESS  read-write
     STATUS      current
     DESCRIPTION
        "Setting this object to 'enable' will enable the 
         egress port restriction on this vlan. Setting this 
         object to 'disable' will disable the egress port 
         restriction on this vlan."
      DEFVAL { disable } 
     ::= { wwpLeosVlanEPREntry 1 }
     
 --
 -- wwpLeosVlanEPRGrpMemTable
 --  
 wwpLeosVlanEPRGrpMemTable OBJECT-TYPE
     SYNTAX     SEQUENCE OF WwpLeosVlanEPRGrpMemEntry
     MAX-ACCESS not-accessible
     STATUS     current
     DESCRIPTION
            "The (conceptual) table listing the egress port
            restriction group for the VLAN members."  
     ::= { wwpLeosVlanEPR 2 }
     
 wwpLeosVlanEPRGrpMemEntry  OBJECT-TYPE
     SYNTAX       WwpLeosVlanEPRGrpMemEntry
     MAX-ACCESS   not-accessible
     STATUS       current
     DESCRIPTION
             "The egress port restriction group entry for the
              vlan members."
     INDEX { wwpLeosVlanId, wwpLeosVlanMemberPortId, wwpLeosVlanMemberTagId }
     ::= { wwpLeosVlanEPRGrpMemTable 1 }
     
 WwpLeosVlanEPRGrpMemEntry ::=  SEQUENCE {
     wwpLeosVlanEPRGrpName      INTEGER     
 }
 
 wwpLeosVlanEPRGrpName OBJECT-TYPE
     SYNTAX      INTEGER {
                    groupA(1),
                                groupB(2)
                 }
     MAX-ACCESS  read-write
     STATUS      current
     DESCRIPTION
        "Setting this object will assign group to given port-tag-vlan combination."      
     ::= { wwpLeosVlanEPRGrpMemEntry 1 }
      
 --
 -- wwpLeosVlanEPRGrpAccessTable
 --  
 wwpLeosVlanEPRGrpAccessTable OBJECT-TYPE
     SYNTAX     SEQUENCE OF WwpLeosVlanEPRGrpAccessEntry
     MAX-ACCESS not-accessible
     STATUS     current
     DESCRIPTION
            "The (conceptual) table listing the group access
             for given VLAN."  
     ::= { wwpLeosVlanEPR 3 }
     
 wwpLeosVlanEPRGrpAccessEntry  OBJECT-TYPE
     SYNTAX       WwpLeosVlanEPRGrpAccessEntry
     MAX-ACCESS   not-accessible
     STATUS       current
     DESCRIPTION
             "Entry for the group access for the given vlan."
     INDEX { wwpLeosVlanId }
     ::= { wwpLeosVlanEPRGrpAccessTable 1 }
     
 WwpLeosVlanEPRGrpAccessEntry ::=  SEQUENCE {
     wwpLeosVlanEPRGrpAAccess           INTEGER,
     wwpLeosVlanEPRGrpBAccess           INTEGER
 }
 
 wwpLeosVlanEPRGrpAAccess OBJECT-TYPE
     SYNTAX      INTEGER {
                    groupA(1),
                                groupB(2),
                                groupAB(3)
                 }
     MAX-ACCESS  read-write
     STATUS      current
     DESCRIPTION
        "Setting this object will allow group A memebers for this vlan
         to talk to specifed group."      
     ::= { wwpLeosVlanEPRGrpAccessEntry 1 }
 
 wwpLeosVlanEPRGrpBAccess OBJECT-TYPE
     SYNTAX      INTEGER {
                    groupA(1),
                                groupB(2),
                                groupAB(3)
                 }
     MAX-ACCESS  read-write
     STATUS      current
     DESCRIPTION
        "Setting this object will allow group B memebers for this vlan
         to talk to specifed group."      
     ::= { wwpLeosVlanEPRGrpAccessEntry 2 } 

  END
