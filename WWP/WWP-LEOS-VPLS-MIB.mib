--
 -- WWP-LEOS-VPLS-MIB.my
 --
 --

 WWP-LEOS-VPLS-MIB DEFINITIONS ::= BEGIN

 IMPORTS                
   Counter32, IpAddress, TimeTicks, Integer32, Unsigned32, OBJECT-TYPE, MODULE-IDENTITY                       
        FROM SNMPv2-SMI                 
   TruthValue, DisplayString, MacAddress, TEXTUAL-CONVENTION, RowStatus                 
        FROM SNMPv2-TC
   AddressFamilyNumbers
            FROM IANA-ADDRESS-FAMILY-NUMBERS-MIB        
   wwpModulesLeos           
        FROM WWP-SMI;
                      
 wwpLeosVplsMIB MODULE-IDENTITY
            LAST-UPDATED "200508151700Z"
            ORGANIZATION "World Wide Packets, Inc"
            CONTACT-INFO
                    "   Mib Meister
                        Postal: World Wide Packets
                        P.O. Box 950
                        Veradale, WA 99037
                        USA
                        Phone:  +1 509 242 9000
                        Email:  mib.meister@worldwidepackets.com"
            DESCRIPTION
                    "This MIB module defines the mgmt objects for the VPLS feature
                     for LEOS based WWP products."  
            REVISION    "200508151700Z"
            DESCRIPTION
                    "Initial creation."
            ::= { wwpModulesLeos 28 }

 --
 -- Textual conventions
 --

 VlanId ::= TEXTUAL-CONVENTION
    STATUS      current
    DESCRIPTION
        "A Vlan Id represents a Broadcast Domain."
    SYNTAX      INTEGER (1..24576)
 
 --
 -- Node definitions
 --
        
 wwpLeosVplsMIBObjects OBJECT IDENTIFIER ::= { wwpLeosVplsMIB 1 }
 wwpLeosVpls  OBJECT IDENTIFIER ::= { wwpLeosVplsMIBObjects 1 } 
  
 -- Notifications   
 wwpLeosVplsMIBNotificationPrefix  OBJECT IDENTIFIER ::= { wwpLeosVplsMIB 2 } 
 wwpLeosVplsMIBNotifications       OBJECT IDENTIFIER ::=  { wwpLeosVplsMIBNotificationPrefix 0 }

 -- Conformance information  
 wwpLeosVplsMIBConformance OBJECT IDENTIFIER ::= { wwpLeosVplsMIB 3 } 
 wwpLeosVplsMIBCompliances OBJECT IDENTIFIER ::= { wwpLeosVplsMIBConformance 1 }                
 wwpLeosVplsMIBGroups      OBJECT IDENTIFIER ::= { wwpLeosVplsMIBConformance 2 } 

 --
 -- VPLS VC Table
 -- 
 wwpLeosVplsVirtualCircuitTable OBJECT-TYPE
     SYNTAX     SEQUENCE OF WwpLeosVplsVirtualCircuitEntry
     MAX-ACCESS not-accessible
     STATUS     deprecated
     DESCRIPTION
            "The (conceptual) table listing the virtual circuit table.
             To create entry use SNMP, multiple set operation must 
             be usedd because following mib objects needs to be set 
             while creating entry in the table.
             - wwpLeosVplsVirtualCircuitIndex
             - wwpLeosVplsVirtualCircuitProviderVlanId (should exist on the device)
             - wwpLeosVplsVirtualCircuitType
             - wwpLeosVplsVirtualCircuitStatus.
             - wwpLeosVplsVirtualCircuitName.
             "
     ::= { wwpLeosVpls 1 }
     
 wwpLeosVplsVirtualCircuitEntry  OBJECT-TYPE
     SYNTAX       WwpLeosVplsVirtualCircuitEntry
     MAX-ACCESS   not-accessible
     STATUS       deprecated
     DESCRIPTION
             "The virtual circuit table entry index by 
              wwpLeosVplsVirtualCircuitIndex."
     INDEX { wwpLeosVplsVirtualCircuitIndex }
     ::= { wwpLeosVplsVirtualCircuitTable 1 }
     
 WwpLeosVplsVirtualCircuitEntry ::=  SEQUENCE {
     wwpLeosVplsVirtualCircuitIndex                                                     INTEGER,
     wwpLeosVplsVirtualCircuitProviderVlanId                    VlanId,
     wwpLeosVplsVirtualCircuitType                              INTEGER,
     wwpLeosVplsVirtualCircuitName                              DisplayString,          
     wwpLeosVplsVirtualCircuitIngressVcLabel                INTEGER,
     wwpLeosVplsVirtualCircuitEgressVcLabel                 INTEGER,
     wwpLeosVplsVirtualCircuitTunnelIndx                                        INTEGER,     
     wwpLeosVplsVirtualCircuitStatus                            RowStatus
 }
 
 wwpLeosVplsVirtualCircuitIndex OBJECT-TYPE
     SYNTAX      INTEGER (1..65535)
     MAX-ACCESS  read-only
     STATUS      deprecated
     DESCRIPTION
        "This represents the virtual circuit index in the table.
         This number should be unique in the table."
     ::= { wwpLeosVplsVirtualCircuitEntry 1 }
  
 wwpLeosVplsVirtualCircuitProviderVlanId OBJECT-TYPE
     SYNTAX      VlanId
     MAX-ACCESS  read-write
     STATUS      deprecated
     DESCRIPTION
        "This represents the provider vlan id associated with the virtual circuit for
         a given wwpLeosVplsVirtualCircuitIndex."
     ::= { wwpLeosVplsVirtualCircuitEntry 2 }
  
 wwpLeosVplsVirtualCircuitType OBJECT-TYPE
     SYNTAX      INTEGER {                              
                        ethernet(1),
                        mpls(2)
                 }
     MAX-ACCESS  read-create
     STATUS      deprecated
     DESCRIPTION
        "This represents the type of virtual circuit associated with 
         the given cirtual circuit."
     ::= { wwpLeosVplsVirtualCircuitEntry 3 }

 wwpLeosVplsVirtualCircuitName OBJECT-TYPE
     SYNTAX      DisplayString (SIZE (1..15))
     MAX-ACCESS  read-create
     STATUS      deprecated
     DESCRIPTION
        "This represents the name of the vrtual circuit associated 
         with the given virtual circuit."
     ::= { wwpLeosVplsVirtualCircuitEntry 4 } 
                                          
 wwpLeosVplsVirtualCircuitIngressVcLabel OBJECT-TYPE
     SYNTAX      INTEGER (16..1048575)
     MAX-ACCESS  read-write
     STATUS      deprecated
     DESCRIPTION
        "This represents the vc label to be used for given virtual circuit. 
         This mib object can only be set for virtual circuit entries which has 
         wwpLeosCircuitType = mpls."
     ::= { wwpLeosVplsVirtualCircuitEntry 5 }
 
 wwpLeosVplsVirtualCircuitEgressVcLabel OBJECT-TYPE
     SYNTAX      INTEGER (16..1048575)
     MAX-ACCESS  read-write
     STATUS      deprecated
     DESCRIPTION
        "This represents the vc label to be used for given virtual circuit. 
         This mib object can only be set for virtual circuit entries which has 
          wwpLeosCircuitType = mpls."
     ::= { wwpLeosVplsVirtualCircuitEntry 6 }

 wwpLeosVplsVirtualCircuitTunnelIndx OBJECT-TYPE
     SYNTAX      INTEGER (1..65535)
     MAX-ACCESS  read-write
     STATUS      deprecated
     DESCRIPTION
        "This represents the tunnel associated with this virtual circuit.
         This mib object can only be set for virtual circuit entries which has 
         wwpLeosCircuitType = mpls."
     ::= { wwpLeosVplsVirtualCircuitEntry 7 }

 wwpLeosVplsVirtualCircuitStatus OBJECT-TYPE
     SYNTAX      RowStatus
     MAX-ACCESS  read-create
     STATUS      deprecated
     DESCRIPTION
        "Setting this object to 'createAndGo' will create the entry 
         and by default will enable control frame and data frame tunnel
         .       
         Setting this object to 'destroy' will delete the entry
         from the table for given vlan."
     ::= { wwpLeosVplsVirtualCircuitEntry 8 }

--
 --  Virtual Switch Table
 -- 
 wwpLeosVplsVirtualSwitchTable OBJECT-TYPE
     SYNTAX       SEQUENCE OF WwpLeosVplsVirtualSwitchEntry
     MAX-ACCESS   not-accessible
     STATUS       deprecated
     DESCRIPTION
             "This table is used to manage virtual switch entries
              on the device."
     ::= { wwpLeosVpls 5 }
                
 wwpLeosVplsVirtualSwitchEntry  OBJECT-TYPE
     SYNTAX       WwpLeosVplsVirtualSwitchEntry
     MAX-ACCESS   not-accessible
     STATUS       deprecated
     DESCRIPTION
             "This entry corresponds to single entry in wwpLeosVplsVirtualSwitchTable table.
              To create an entry in the table following criteria must be met.
              - wwpLeosVplsVirtualSwitchIndx must be specified.              
              - wwpLeosVplsVirtualSwitchStatus must be specified.
              - wwpLeosVplsVirtualSwitchType must be specified.
              - wwpLeosVplsVirtualSwitchName must be specified"
     INDEX { wwpLeosVplsVirtualSwitchIndx }
     ::= { wwpLeosVplsVirtualSwitchTable 1 }
     
 WwpLeosVplsVirtualSwitchEntry ::= SEQUENCE {
     wwpLeosVplsVirtualSwitchIndx                       INTEGER,     
     wwpLeosVplsVirtualSwitchName                       DisplayString,
     wwpLeosVplsVirtualSwitchPriVc                      INTEGER,
     wwpLeosVplsVirtualSwitchSecVc                      INTEGER,     
     wwpLeosVplsVirtualSwitchActiveVc                   INTEGER,
     wwpLeosVplsVirtualSwitchEncapCosPolicy                             INTEGER,
     wwpLeosVplsVirtualSwitchEncapFixedDot1dPri                 INTEGER,
     wwpLeosVplsVirtualSwitchDecapCosPolicy                     INTEGER,
     wwpLeosVplsVirtualSwitchDecapFixedDot1dPri                 INTEGER,
     wwpLeosVplsVirtualSwitchSubscriberVlan                             INTEGER,     
     wwpLeosVplsVirtualSwitchCtrlProtocolTunnelState    INTEGER,     
     wwpLeosVplsVirtualSwitchType                                               INTEGER,             
     wwpLeosVplsVirtualSwitchStatus                     RowStatus
 }    
     
 wwpLeosVplsVirtualSwitchIndx    OBJECT-TYPE
     SYNTAX         INTEGER (1..65535)
     MAX-ACCESS     read-only
     STATUS         deprecated
     DESCRIPTION
             "This object specifies the virtual switch index which is used as unique 
              index in the table."
     ::= { wwpLeosVplsVirtualSwitchEntry 1 }         
       
 wwpLeosVplsVirtualSwitchName    OBJECT-TYPE
     SYNTAX         DisplayString (SIZE (0..16))
     MAX-ACCESS     read-write
     STATUS         deprecated
     DESCRIPTION
             "This object specifies the virtual switch name. this object can only be specified at the 
              time of creation and cannot be modified later."
     ::= { wwpLeosVplsVirtualSwitchEntry 2 }
 
 wwpLeosVplsVirtualSwitchPriVc    OBJECT-TYPE
     SYNTAX         INTEGER (0..65535)
     MAX-ACCESS     read-write
     STATUS         deprecated
     DESCRIPTION
             "This object specifies the primary virtual circuit ID associated with this virtual switch.
              To unset it set this to 0."
     ::= { wwpLeosVplsVirtualSwitchEntry 3 }

 wwpLeosVplsVirtualSwitchSecVc    OBJECT-TYPE
     SYNTAX         INTEGER (0..65535)
     MAX-ACCESS     read-write
     STATUS         deprecated
     DESCRIPTION
             "This object specifies the secondary virtual circuit ID associated with this virtual switch.
              To unset it set this to 0. This object is applicable if wwpLeosVplsVirtualSwitchType = mpls."
     ::= { wwpLeosVplsVirtualSwitchEntry 4 }
 
 wwpLeosVplsVirtualSwitchActiveVc    OBJECT-TYPE
     SYNTAX         INTEGER {
                                        none(1),
                                        primVc(2),
                                        secVc(3)                                        
                                }
     MAX-ACCESS     read-only
     STATUS         deprecated
     DESCRIPTION
             "This object specifies the virtual circuit which is currently used by 
              this virtual switch instance."
     ::= { wwpLeosVplsVirtualSwitchEntry 5 }

 wwpLeosVplsVirtualSwitchEncapCosPolicy    OBJECT-TYPE
     SYNTAX         INTEGER {
                        fixed(1),                        
                        inheritDot1dPri(2),
                                                inheritIpPrec(3),                                               
                                                inheritPhbg(4)                          
                        }
     MAX-ACCESS     read-write
     STATUS         deprecated
     DESCRIPTION
             "This object specifies the ingress cos policy for given virtual switch."
     ::= { wwpLeosVplsVirtualSwitchEntry 6 }
 
 wwpLeosVplsVirtualSwitchEncapFixedDot1dPri    OBJECT-TYPE
     SYNTAX         INTEGER (0..7)
     MAX-ACCESS     read-write
     STATUS         deprecated
     DESCRIPTION
             "This object specifies the ingress fixed cos attributes for given virtual switch."
     ::= { wwpLeosVplsVirtualSwitchEntry 7 }

 wwpLeosVplsVirtualSwitchDecapCosPolicy    OBJECT-TYPE
     SYNTAX         INTEGER {
                        fixed(1),
                        inheritVc(2),
                        inheritTunnel(3),
                        leave(4)                        
                        }
     MAX-ACCESS     read-write
     STATUS         deprecated
     DESCRIPTION
             "This object specifies the egress cos policy for given virtual switch."
     ::= { wwpLeosVplsVirtualSwitchEntry 8 }
 
 wwpLeosVplsVirtualSwitchDecapFixedDot1dPri    OBJECT-TYPE
     SYNTAX         INTEGER (0..7)
     MAX-ACCESS     read-write
     STATUS         deprecated
     DESCRIPTION
             "This object specifies the egress cos attributes for given virtual switch."
     ::= { wwpLeosVplsVirtualSwitchEntry 9 }
      
 wwpLeosVplsVirtualSwitchSubscriberVlan    OBJECT-TYPE
     SYNTAX         INTEGER (0..4094)
     MAX-ACCESS     read-write
     STATUS         deprecated
     DESCRIPTION
             "This object specifies the subscriber vlan Id for given virtual switch."
     ::= { wwpLeosVplsVirtualSwitchEntry 10 }
         
 wwpLeosVplsVirtualSwitchCtrlProtocolTunnelState    OBJECT-TYPE
     SYNTAX         INTEGER {
                        enabled(1),
                        disabled(2)                      
                        }
     MAX-ACCESS     read-write
     STATUS         deprecated
     DESCRIPTION
             "This object enables or disables control protocol tunneling for a given 
              virtual switch."
     ::= { wwpLeosVplsVirtualSwitchEntry 11 } 
 
 wwpLeosVplsVirtualSwitchType    OBJECT-TYPE
     SYNTAX         INTEGER {
                        ethernet(1),
                        mpls(2)                      
                        }
     MAX-ACCESS     read-create
     STATUS         deprecated
     DESCRIPTION
             "This object specifies the type of virtual witch."
     ::= { wwpLeosVplsVirtualSwitchEntry 12 }
     
 wwpLeosVplsVirtualSwitchStatus    OBJECT-TYPE
     SYNTAX         RowStatus
     MAX-ACCESS     read-create
     STATUS         deprecated
     DESCRIPTION
             "This object can be set to 'createAndGo' to create entry in the table. 
              This object can be set to 'destory' to delete entry in the table.
              Following objects must be set to valid values to create entry in the table."
     ::= { wwpLeosVplsVirtualSwitchEntry 13 }

--
 --  Virtual Switch Membership Table
 -- 
 wwpLeosVplsVirtualSwitchMemberTable OBJECT-TYPE
     SYNTAX       SEQUENCE OF WwpLeosVplsVirtualSwitchMemberEntry
     MAX-ACCESS   not-accessible
     STATUS       deprecated
     DESCRIPTION
             "This table is used to create virtual switch membership entry."
     ::= { wwpLeosVpls 6 }
                
 wwpLeosVplsVirtualSwitchMemberEntry  OBJECT-TYPE
     SYNTAX       WwpLeosVplsVirtualSwitchMemberEntry
     MAX-ACCESS   not-accessible
     STATUS       deprecated
     DESCRIPTION
             "This entry corresponds to single entry in wwpLeosVplsVirtualSwitchMemberTable table."
     INDEX { wwpLeosVplsVirtualSwitchIndx, wwpLeosVplsVirtualSwitchMemberPortId }
     ::= { wwpLeosVplsVirtualSwitchMemberTable 1 }
     
 WwpLeosVplsVirtualSwitchMemberEntry ::= SEQUENCE {
     wwpLeosVplsVirtualSwitchMemberPortId               INTEGER,
     wwpLeosVplsVirtualSwitchMemberStatus               RowStatus
 }    
     
 wwpLeosVplsVirtualSwitchMemberPortId    OBJECT-TYPE
     SYNTAX         INTEGER (1..65535)
     MAX-ACCESS     read-only
     STATUS         deprecated
     DESCRIPTION
             "This object specifes the port id associated with 
              wwpLeosVplsVirtualSwitchIndx."
     ::= { wwpLeosVplsVirtualSwitchMemberEntry 1 }

  wwpLeosVplsVirtualSwitchMemberStatus    OBJECT-TYPE
     SYNTAX         RowStatus
     MAX-ACCESS     read-create
     STATUS         deprecated
     DESCRIPTION
             "This object can be set to 'createandgo' to add entry in the table.
              This object can be set to 'destroy' to delete entry in the table.
              Refer to description of table entry to see how to create entries 
              in the table."
     ::= { wwpLeosVplsVirtualSwitchMemberEntry 2 }  
     
 --
 -- Virtual switch  control protocol table
 --
 wwpLeosVplsSwitchCtrlProtocolTable OBJECT-TYPE
     SYNTAX     SEQUENCE OF WwpLeosVplsSwitchCtrlProtocolEntry
     MAX-ACCESS not-accessible
     STATUS     deprecated
     DESCRIPTION
            "The (conceptual) table listing the l2 virtual switch control frame 
             protocol status tunnel for a given Vpls."
     ::= { wwpLeosVpls 7 }
     
 wwpLeosVplsSwitchCtrlProtocolEntry  OBJECT-TYPE
     SYNTAX       WwpLeosVplsSwitchCtrlProtocolEntry
     MAX-ACCESS   not-accessible
     STATUS       deprecated
     DESCRIPTION
             "The layer 2 virtual switch control frame protocol tunnel 
              entry for the Vpls."
     INDEX {wwpLeosVplsVirtualSwitchIndx, wwpLeosVplsSwitchCtrlProtocolNum}
     ::= { wwpLeosVplsSwitchCtrlProtocolTable 1 }
     
 WwpLeosVplsSwitchCtrlProtocolEntry ::=  SEQUENCE { 
     wwpLeosVplsSwitchCtrlProtocolNum     INTEGER,
     wwpLeosVplsSwitchCtrlType            INTEGER       
 }

  wwpLeosVplsSwitchCtrlProtocolNum OBJECT-TYPE
     SYNTAX      INTEGER {                     
                     l28021x(1),
                     rstp(2),
                     ciscoCdp(3),
                     ciscoDtp(4),
                     ciscoPagp(5),
                     ciscoPvst(6),
                     ciscoUplinkFast(7),
                     ciscoUdlp(8),
                     ciscoVtp(9),
                     gvrp(10),
                     lacp(11),
                     lacpMarker(12),
                     oam(13),
                     lldp(14),
                     vlanBridge(15)                     
                 }
     MAX-ACCESS  read-only
     STATUS      deprecated
     DESCRIPTION
        "This object represent the list of protocols the device 
         can support."
     ::= { wwpLeosVplsSwitchCtrlProtocolEntry 1 }

  wwpLeosVplsSwitchCtrlType OBJECT-TYPE
     SYNTAX      INTEGER {
                     discard(1),
                     peer(2),
                     tunnel(3)               
                 }
     MAX-ACCESS  read-create
     STATUS      deprecated
     DESCRIPTION
        "Setting this object to 'discard' will cause wwpLeosVplsSwitchCtrlProtocolNum
         frames arriving at the specified UNI to be discarded.  
         Setting this to 'peer' will cause the wwpLeosVplsSwitchCtrlProtocolNum frame
         to be processed by the provider network and cause the provider 
         network to behave as a peer.  
         Setting this to 'tunnel' will cause the wwpLeosVplsSwitchCtrlProtocolNum frame to be 
         tunneled."
     ::= { wwpLeosVplsSwitchCtrlProtocolEntry 2 } 
 
 --
 -- Reserved Vlans
 --  
 wwpLeosVplsSwitchReservedVlanTable OBJECT-TYPE
     SYNTAX     SEQUENCE OF WwpLeosVplsSwitchReservedVlanEntry
     MAX-ACCESS not-accessible
     STATUS     current
     DESCRIPTION
            "The (conceptual) table listing the reserved Vlans used for virtual
             switch."
     ::= { wwpLeosVpls 8 }
     
 wwpLeosVplsSwitchReservedVlanEntry  OBJECT-TYPE
     SYNTAX       WwpLeosVplsSwitchReservedVlanEntry
     MAX-ACCESS   not-accessible
     STATUS       current
     DESCRIPTION
             "The entry to reserve vlans for vlan switch."
     INDEX {wwpLeosVplsSwitchReservedVlanId}
     ::= { wwpLeosVplsSwitchReservedVlanTable 1 }
     
 WwpLeosVplsSwitchReservedVlanEntry ::=  SEQUENCE { 
     wwpLeosVplsSwitchReservedVlanId            INTEGER,
     wwpLeosVplsSwitchReservedVlanStatus    RowStatus
 }

 wwpLeosVplsSwitchReservedVlanId OBJECT-TYPE
     SYNTAX      INTEGER (1..24576)
     MAX-ACCESS  read-only
     STATUS      current
     DESCRIPTION
        "This object is used to specify the vlan ID to be reserved for virtual switch.
         Reserved vlans are used when virtual switch is created."
     ::= { wwpLeosVplsSwitchReservedVlanEntry 1 }

 wwpLeosVplsSwitchReservedVlanStatus OBJECT-TYPE
     SYNTAX      RowStatus
     MAX-ACCESS  read-create
     STATUS      current
     DESCRIPTION
        "Setting this object to 'createandgo' will reseve the vlan 
         for virtual switch.
         Setting this object to 'destroy will no longer be 
         reserved for virtual switch."
     ::= { wwpLeosVplsSwitchReservedVlanEntry 2 }
  
  --
 --  Global VPLS Attrs Table
 --      
 wwpLeosVplsGlobalAttrs  OBJECT IDENTIFIER ::= { wwpLeosVpls 9 } 
  
 wwpLeosVplsTunnelFixedTTL    OBJECT-TYPE
     SYNTAX         INTEGER (2..255)
     MAX-ACCESS     read-write
     STATUS         current
     DESCRIPTION
             "This object specifies the fixed TTL value for all tunnels."
     DEFVAL { 255 }
     ::= { wwpLeosVplsGlobalAttrs 1 }
 
 wwpLeosVplsResolverTimeout    OBJECT-TYPE
     SYNTAX         INTEGER (10..255)     
     MAX-ACCESS     read-write
     STATUS         current
     DESCRIPTION
             "Setting this object will set the PE resolver timeout.
              This timeout value decides how frequently PE resolver will arp
              for the destination IP specified by wwpLeosVplsEncapTunnelDestAddr."
     DEFVAL { 10 }
     ::= { wwpLeosVplsGlobalAttrs 2 }        

--
-- Path Table
-- 
  wwpLeosVplsMplsPathTable OBJECT-TYPE
     SYNTAX       SEQUENCE OF WwpLeosVplsMplsPathEntry
     MAX-ACCESS   not-accessible
     STATUS       current
     DESCRIPTION
             "Mpls Path table used to represent the explicit path for 
              RSVP tunnels."
     ::= { wwpLeosVpls 10 }
                
 wwpLeosVplsMplsPathEntry  OBJECT-TYPE
     SYNTAX       WwpLeosVplsMplsPathEntry
     MAX-ACCESS   not-accessible
     STATUS       current
     DESCRIPTION
             "Entry in the MPLS Path table."
     INDEX { wwpLeosVplsMplsPathIndex }
     ::= { wwpLeosVplsMplsPathTable 1 }
     
 WwpLeosVplsMplsPathEntry ::= SEQUENCE {
     wwpLeosVplsMplsPathIndex                       INTEGER,
     wwpLeosVplsMplsPathName                        DisplayString,
     wwpLeosVplsMplsPathRowStatus                   RowStatus
}    
     
 wwpLeosVplsMplsPathIndex    OBJECT-TYPE
     SYNTAX         INTEGER (1..32)
     MAX-ACCESS     read-only
     STATUS         current
     DESCRIPTION
             "This mib specifies the unique entry in the Mpls path table.
              This is the primary index into this table identifying a particular explicit 
              route object"
     ::= { wwpLeosVplsMplsPathEntry 1 }     
     
 wwpLeosVplsMplsPathName    OBJECT-TYPE
     SYNTAX         DisplayString (SIZE (1..15))
     MAX-ACCESS     read-create
     STATUS         current
     DESCRIPTION
             "This mib specifies the name for the path."
     ::= { wwpLeosVplsMplsPathEntry 2 }     
 
 wwpLeosVplsMplsPathRowStatus    OBJECT-TYPE
     SYNTAX         RowStatus
     MAX-ACCESS     read-create
     STATUS         current
     DESCRIPTION
             "Used to manage the creation and deletion of the 
              conceptual rows in this table.
              To create a row in this table, a manager must
              set this object to 'createAndGo'. To delete a row in this
              table, a manager must set this object to 'destroy'.
              If the entry exists, it will be displayed as 'active'."
     ::= { wwpLeosVplsMplsPathEntry 3 }     

--
-- List of IP address in the mpls path
-- 
 wwpLeosVplsMplsPathMemberTable OBJECT-TYPE
     SYNTAX       SEQUENCE OF WwpLeosVplsMplsPathMemberEntry
     MAX-ACCESS   not-accessible
     STATUS       current
     DESCRIPTION
             "Table specifies the list of IP addresses (Hops) 
              to get to the destination PE."
     ::= { wwpLeosVpls 11 }
                
 wwpLeosVplsMplsPathMemberEntry  OBJECT-TYPE
     SYNTAX       WwpLeosVplsMplsPathMemberEntry
     MAX-ACCESS   not-accessible
     STATUS       current
     DESCRIPTION
             "Represents the entry in the table."
     INDEX { wwpLeosVplsMplsPathIndex, wwpLeosVplsMplsPathOptionIndex, wwpLeosVplsMplsPathMemberIpIndex }
     ::= { wwpLeosVplsMplsPathMemberTable 1 }
     
 WwpLeosVplsMplsPathMemberEntry ::= SEQUENCE {
     wwpLeosVplsMplsPathOptionIndex					  INTEGER,
     wwpLeosVplsMplsPathMemberIpIndex		          INTEGER,
     wwpLeosVplsMplsPathMemberIp                      IpAddress,
     wwpLeosVplsMplsPathMemberRowStatus               RowStatus
 }    
 
 wwpLeosVplsMplsPathOptionIndex    OBJECT-TYPE
     SYNTAX         INTEGER (1..5)
     MAX-ACCESS     read-only
     STATUS         current
     DESCRIPTION
             "Secondary index into this table identifying a
          	  particular group of hops representing a particular
              configured path. This is otherwise known as a path
              option."
     ::= { wwpLeosVplsMplsPathMemberEntry 1 }
     
 wwpLeosVplsMplsPathMemberIpIndex    OBJECT-TYPE
     SYNTAX         INTEGER (1..5)
     MAX-ACCESS     read-only
     STATUS         current
     DESCRIPTION
             "Unique index to identify the IP address within the path specifies by
              wwpLeosVplsMplsPathIndex."
     ::= { wwpLeosVplsMplsPathMemberEntry 2 }
        
 wwpLeosVplsMplsPathMemberIp    OBJECT-TYPE
     SYNTAX         IpAddress
     MAX-ACCESS     read-create
     STATUS         current
     DESCRIPTION
             "Specifies the IP address of the Hop that the tunnel 
              the tunnel should traverse."
     ::= { wwpLeosVplsMplsPathMemberEntry 3 }     
 
 wwpLeosVplsMplsPathMemberRowStatus    OBJECT-TYPE
     SYNTAX         RowStatus
     MAX-ACCESS     read-create
     STATUS         current
     DESCRIPTION
             "Used to manage the creation and deletion of the 
              conceptual rows in this table.
              To create a row in this table, a manager must
              set this object to 'createAndGo'. To delete a row in this
              table, a manager must set this object to 'destroy'.
              If the entry exists, it will be displayed as 'active'."
     ::= { wwpLeosVplsMplsPathMemberEntry 4 }     
 
--
-- RSVP Attrs Table
-- 
 wwpLeosVplsRsvpAttrTable OBJECT-TYPE
     SYNTAX       SEQUENCE OF WwpLeosVplsRsvpAttrEntry
     MAX-ACCESS   not-accessible
     STATUS       current
     DESCRIPTION
             "RSVP Attr Table used by MPLS wwpLeosVplsEncapTunnelTable Tunnels
              when wwpLeosVplsEncapTunnelProtType = rsvp.
              Whenever entry is created in the wwpLeosVplsEncapTunnelTable table 
              with wwpLeosVplsEncapTunnelProtType = rsvp and wwpLeosVplsEncapTunnelType
              = dynamic then corresponding entry will be created in this table with 
              the same index as wwpLeosVplsEncapTunnelId."
      ::= { wwpLeosVpls 12 }
                
 wwpLeosVplsRsvpAttrEntry  OBJECT-TYPE
     SYNTAX       WwpLeosVplsRsvpAttrEntry
     MAX-ACCESS   not-accessible
     STATUS       current
     DESCRIPTION
             "Entry in wwpLeosVplsRsvpAttrTable table."
     INDEX { wwpLeosVplsRsvpAttrIndex }
     ::= { wwpLeosVplsRsvpAttrTable 1 }
     
 WwpLeosVplsRsvpAttrEntry ::= SEQUENCE {
     wwpLeosVplsRsvpAttrIndex                            INTEGER,     
     wwpLeosVplsRsvpAttrHoldPri                          INTEGER,
     wwpLeosVplsRsvpAttrSetupPri                         INTEGER,
     wwpLeosVplsRsvpAttrRecordRoute                      TruthValue     
 }    
     
 wwpLeosVplsRsvpAttrIndex    OBJECT-TYPE
     SYNTAX         INTEGER (1..65535)
     MAX-ACCESS     read-only
     STATUS         current
     DESCRIPTION
             "Unique index into the table."
     ::= { wwpLeosVplsRsvpAttrEntry 1 }     
     
 wwpLeosVplsRsvpAttrHoldPri    OBJECT-TYPE
     SYNTAX         INTEGER (0..7)
     MAX-ACCESS     read-write
     STATUS         current
     DESCRIPTION
             "The Hold priority used by RSVP protocol when signaling 
              for tunnels."
     DEFVAL { 0 }
     ::= { wwpLeosVplsRsvpAttrEntry 2 }     
 
 wwpLeosVplsRsvpAttrSetupPri    OBJECT-TYPE
     SYNTAX         INTEGER (0..7)
     MAX-ACCESS     read-write
     STATUS         current
     DESCRIPTION
             "The setup priority used by RSVP protocol when signaling 
              for tunnels."
     DEFVAL { 0 }
     ::= { wwpLeosVplsRsvpAttrEntry 3 }     
 
 wwpLeosVplsRsvpAttrRecordRoute    OBJECT-TYPE
     SYNTAX         TruthValue
     MAX-ACCESS     read-write
     STATUS         current
     DESCRIPTION
             "The object specifies if record route feature is enabled
              when RSVP protocol is used to signal tunnel LSP."
     DEFVAL { false }
     ::= { wwpLeosVplsRsvpAttrEntry 4 }     
 
 --
 --  Encap Tunnel Table
 -- 
  wwpLeosVplsEncapTunnelTable OBJECT-TYPE
     SYNTAX       SEQUENCE OF WwpLeosVplsEncapTunnelEntry
     MAX-ACCESS   not-accessible
     STATUS       current
     DESCRIPTION
             "This table represents the encap tunnels for VPLS.              
              To create STATIC encap tunnel following objects must be set  
              Encap and Decap Tunnel name cannot be same but indexes can be 
              wwpLeosVplsEncapTunnelName                must be specified. 
              wwpLeosVplsEncapTunnelEncapLabel		must be specified (0, 32..1023)
              wwpLeosVplsEncapTunnelType                must be set to static 
              wwpLeosVplsEncapTunnelRowStatus   		must be set to createAndGo
              
              To create DYNAMIC encap tunnel following objects must be set              
              wwpLeosVplsEncapTunnelName                must be specified
              wwpLeosVplsEncapTunnelType                must be set to dynamic
              wwpLeosVplsEncapTunnelProtType			must be set to rsvp 
              wwpLeosVplsEncapTunnelPathName    		must be specified, this path must 
                                                        exist in wwpLeosVplsMplsPathTable
              wwpLeosVplsEncapTunnelRowStatus   		must be set to createAndGo."
     ::= { wwpLeosVpls 13 }
                
  wwpLeosVplsEncapTunnelEntry  OBJECT-TYPE
     SYNTAX       WwpLeosVplsEncapTunnelEntry
     MAX-ACCESS   not-accessible
     STATUS       current
     DESCRIPTION
             "Represents each entry in wwpLeosVplsEncapTunnelTable."
     INDEX { wwpLeosVplsEncapTunnelId }
     ::= { wwpLeosVplsEncapTunnelTable 1 }
     
  WwpLeosVplsEncapTunnelEntry ::= SEQUENCE {
     wwpLeosVplsEncapTunnelId                    	INTEGER,
     wwpLeosVplsEncapTunnelName                  	DisplayString,
     wwpLeosVplsEncapTunnelType                  	INTEGER,
     wwpLeosVplsEncapTunnelDestAddr              	IpAddress,
     wwpLeosVplsEncapTunnelPathIndex              	Integer32,     
     wwpLeosVplsEncapTunnelEncapCosPolicy        	INTEGER,     
     wwpLeosVplsEncapTunnelEncapFixedExp       		INTEGER,     
     wwpLeosVplsEncapTunnelTTLPolicy                INTEGER,
     wwpLeosVplsEncapTunnelEncapLabel               Unsigned32,
     wwpLeosVplsEncapTunnelProtType                 INTEGER,
     wwpLeosVplsEncapTunnelDestResolvedMac          MacAddress,  
     wwpLeosVplsEncapTunnelOperStatus               INTEGER,     
     wwpLeosVplsEncapTunnelAdminStatus              INTEGER, 
     wwpLeosVplsEncapTunnelDestResolvedPort         INTEGER,
     wwpLeosVplsEncapTunnelDestResolvedVlan         INTEGER,            
     wwpLeosVplsEncapTunnelRowStatus                RowStatus
 }    
     
 wwpLeosVplsEncapTunnelId    OBJECT-TYPE
     SYNTAX         INTEGER (1..65535)
     MAX-ACCESS     read-only
     STATUS         current
     DESCRIPTION
             "This object specifies the unique index used in the table."
     ::= { wwpLeosVplsEncapTunnelEntry 1 }     
     
 wwpLeosVplsEncapTunnelName    OBJECT-TYPE
     SYNTAX         DisplayString (SIZE (1..15))
     MAX-ACCESS     read-create
     STATUS         current
     DESCRIPTION
             "This object specfies the name assigned to this tunnel. 
              This object can only be specifed while creating entry in the table
              and cannot be modified after the entry has been created.
              Encap and Decap Tunnel name cannot be same but indexes can be "
     ::= { wwpLeosVplsEncapTunnelEntry 2 }  

 wwpLeosVplsEncapTunnelType    OBJECT-TYPE
     SYNTAX         INTEGER {
                                        static(1),
                                        dynamic(2)
                                        }
     MAX-ACCESS     read-create
     STATUS         current
     DESCRIPTION
             "This object specifies the type of tunnel.
              This object can only be specifed while creating entry in the table
              and cannot be modified after the entry has been created."              
     ::= { wwpLeosVplsEncapTunnelEntry 3 }
 
 wwpLeosVplsEncapTunnelDestAddr    OBJECT-TYPE
     SYNTAX         IpAddress
     MAX-ACCESS     read-write
     STATUS         current
     DESCRIPTION
             "This object specifies the IP address used to resolve this tunnel."
     ::= { wwpLeosVplsEncapTunnelEntry 4 }
 
 wwpLeosVplsEncapTunnelPathIndex    OBJECT-TYPE
     SYNTAX         Integer32
     MAX-ACCESS     read-create
     STATUS         current
     DESCRIPTION
             "This object specifies the path that this tunnel is supposed to use
              signal labels for this tunnel.
              This object is only used if wwpLeosVplsEncapTunnelType is set to dynamic."
     ::= { wwpLeosVplsEncapTunnelEntry 5 }
  
 wwpLeosVplsEncapTunnelEncapCosPolicy    OBJECT-TYPE
     SYNTAX         INTEGER {
                        fixed(1),
                        inheritVc(2),
                        inheritVs(3)
                    }
     MAX-ACCESS     read-write
     STATUS         current
     DESCRIPTION
             "This object specifies the MPLS encapsulated cos policy assigned to this tunnel."
     DEFVAL { inheritVc }
     ::= { wwpLeosVplsEncapTunnelEntry 6 }

 wwpLeosVplsEncapTunnelEncapFixedExp    OBJECT-TYPE
     SYNTAX         INTEGER (0..7)
     MAX-ACCESS     read-write
     STATUS         current
     DESCRIPTION
             "This object specifies the encap fixed EXP assigned to this tunnel."
     DEFVAL { 2 }
     ::= { wwpLeosVplsEncapTunnelEntry 7 } 
 
 wwpLeosVplsEncapTunnelTTLPolicy    OBJECT-TYPE
     SYNTAX         INTEGER {
                        pipe(1),
                        uniform(2)
                        }
     MAX-ACCESS     read-write
     STATUS         current
     DESCRIPTION
             "This object specifies the TTL policy for given tunnel."
     DEFVAL { pipe }
     ::= { wwpLeosVplsEncapTunnelEntry 8 }    
   
 wwpLeosVplsEncapTunnelEncapLabel    OBJECT-TYPE
     SYNTAX         Unsigned32 (0..1048576)
     MAX-ACCESS     read-write
     STATUS         current
     DESCRIPTION
             "This mib object specifies the encap label assigned to this tunnel.
              If the label is not yet known (signaling in process), the  
           	  object should return a value of 0xFFFF."
     ::= { wwpLeosVplsEncapTunnelEntry 9 }
 
 wwpLeosVplsEncapTunnelProtType    OBJECT-TYPE
     SYNTAX         INTEGER {
     					none (1),
     					rsvp (2)  
     					}
     MAX-ACCESS     read-create
     STATUS         current
     DESCRIPTION
             "Setting this object at the time of entry creation will specify the type of Protocol
              to be used for this tunnel. This object is only used if wwpLeosVplsEncapTunnelType
              is set to dynamic. This object cannot be modified after the entry has been created."              
     DEFVAL { none }
     ::= { wwpLeosVplsEncapTunnelEntry 10 }
 
 wwpLeosVplsEncapTunnelDestResolvedMac    OBJECT-TYPE
     SYNTAX         MacAddress
     MAX-ACCESS     read-only
     STATUS         current
     DESCRIPTION
             "This object specifies the resolved mac address for given destination IP 
              (wwpLeosVplsEncapTunnelDestIp)."
     ::= { wwpLeosVplsEncapTunnelEntry 11 }

 wwpLeosVplsEncapTunnelOperStatus OBJECT-TYPE
         SYNTAX         INTEGER {
                                  enabled(1),
                                  disabled(2)
                                }
         MAX-ACCESS  read-only
     	 STATUS      current
     	 DESCRIPTION
        	"This mib object represents the operational status of tunnel."
     ::= { wwpLeosVplsEncapTunnelEntry 12 } 
  
 wwpLeosVplsEncapTunnelAdminStatus OBJECT-TYPE
     SYNTAX         INTEGER {
                              enabled(1),
                              disabled(2)
                            }
     MAX-ACCESS  read-write
     STATUS      current
     DESCRIPTION
      	"This mib object represents the administrative status of tunnel."
     DEFVAL { enabled }
     ::= { wwpLeosVplsEncapTunnelEntry 13 } 
  
 wwpLeosVplsEncapTunnelDestResolvedPort OBJECT-TYPE
     SYNTAX         INTEGER (0..65535)
     MAX-ACCESS  read-only
     STATUS      current
     DESCRIPTION
      	"This mib object represents the resolved port number 
      	 to destination."     
     ::= { wwpLeosVplsEncapTunnelEntry 14 } 
 
 wwpLeosVplsEncapTunnelDestResolvedVlan OBJECT-TYPE
     SYNTAX         INTEGER (0..4094)
     MAX-ACCESS  read-only
     STATUS      current
     DESCRIPTION
      	"This mib object represents the resolved transport vlan  
      	 to destination."     
     ::= { wwpLeosVplsEncapTunnelEntry 15 }  
  
  wwpLeosVplsEncapTunnelRowStatus    OBJECT-TYPE
     SYNTAX         RowStatus
     MAX-ACCESS     read-create
     STATUS         current
     DESCRIPTION
             "Setting this object to 'createAndGo' will create the entry 
              in the table.      
              Setting this object to 'destroy' will delete the entry
              from the table.
              Refer to description of wwpLeosVplsEncapTunnelTable for details of 
              creating and deleting entries in the table."
     ::= { wwpLeosVplsEncapTunnelEntry 16 }  
 
 --
 --  Decap Tunnel Table
 -- 
 wwpLeosVplsDecapTunnelTable OBJECT-TYPE
     SYNTAX       SEQUENCE OF WwpLeosVplsDecapTunnelEntry
     MAX-ACCESS   not-accessible
     STATUS       current
     DESCRIPTION
             "This table represents the Decap tunnels for VPLS
              
              To create STATIC Decap tunnel following objects must be set              
              Encap and Decap Tunnel name cannot be same but indexes can be 
              wwpLeosVplsDecapTunnelName                must be specified
              wwpLeosVplsDecapTunnelLabel               must be specified (0, 32..1023)
              wwpLeosVplsDecapTunnelRowStatus   must be set to createAndGo."
              
     ::= { wwpLeosVpls 14 }
                
 wwpLeosVplsDecapTunnelEntry  OBJECT-TYPE
     SYNTAX       WwpLeosVplsDecapTunnelEntry
     MAX-ACCESS   not-accessible
     STATUS       current
     DESCRIPTION
             "represents each entry in wwpLeosVplsDecapTunnelTable."
     INDEX { wwpLeosVplsDecapTunnelId }
     ::= { wwpLeosVplsDecapTunnelTable 1 }
     
 WwpLeosVplsDecapTunnelEntry ::= SEQUENCE {
     wwpLeosVplsDecapTunnelId                                   INTEGER,
     wwpLeosVplsDecapTunnelName                                 DisplayString,
     wwpLeosVplsDecapTunnelLabel                        		Unsigned32,     
     wwpLeosVplsDecapTunnelType                                 INTEGER,
     wwpLeosVplsDecapTunnelRowStatus                        	RowStatus
 }    
     
 wwpLeosVplsDecapTunnelId    OBJECT-TYPE
     SYNTAX         INTEGER (1..65535)
     MAX-ACCESS     read-only
     STATUS         current
     DESCRIPTION
             "This object specifies the unique index used in the table."
     ::= { wwpLeosVplsDecapTunnelEntry 1 }     
     
 wwpLeosVplsDecapTunnelName    OBJECT-TYPE
     SYNTAX         DisplayString (SIZE (1..15))
     MAX-ACCESS     read-create
     STATUS         current
     DESCRIPTION
             "This object specfies the name assigned to thi tunnel. 
              This object can only be specifed while creating entry in the table
              and cannot be modified after the entry has been created."
     ::= { wwpLeosVplsDecapTunnelEntry 2 }  
     
 wwpLeosVplsDecapTunnelLabel    OBJECT-TYPE
     SYNTAX         Unsigned32 (0..1048576)
     MAX-ACCESS     read-write
     STATUS         current
     DESCRIPTION
             "This mib object specifies the Decap label assigned to this tunnel.
              If the label is not yet known (signaling in process), the  
           	  object should return a value of 0xFFFF."
     ::= { wwpLeosVplsDecapTunnelEntry 3 }
 
  wwpLeosVplsDecapTunnelType    OBJECT-TYPE
     SYNTAX         INTEGER {
                               static(1),
                               dynamic(2)
                            }
     MAX-ACCESS     read-only
     STATUS         current
     DESCRIPTION
             "This object specifies if the tunnel is created because 
              of remote PE request (decap tunnel) or it is created by the
              user on the device (Decap tunnel)."              
     ::= { wwpLeosVplsDecapTunnelEntry 4 }
  
  wwpLeosVplsDecapTunnelRowStatus    OBJECT-TYPE
     SYNTAX         RowStatus
     MAX-ACCESS     read-create
     STATUS         current
     DESCRIPTION
             "Setting this object to 'createAndGo' will create the entry 
              in the table.      
              Setting this object to 'destroy' will delete the entry
              from the table.
              Refer to description of wwpLeosVplsDecapTunnelTable for details of 
              creating and deleting entries in the table."
     ::= { wwpLeosVplsDecapTunnelEntry 5 }  

 --
 -- Virtual circuit mpls table
 -- 
 wwpLeosVplsVirtualCircuitMplsTable OBJECT-TYPE
     SYNTAX     SEQUENCE OF WwpLeosVplsVirtualCircuitMplsEntry
     MAX-ACCESS not-accessible
     STATUS     current
     DESCRIPTION
            "The (conceptual) table listing the mpls virtual circuit table.
             To create entry use SNMP, multiple set operation must 
             be used.
             Following Mib objects must be specified while creating MPLS
             virtual circuit
             Mpls and Ethernet virtual circuit name name cannot be same but indexes can be 
             - wwpLeosVplsVirtualCircuitMplsType  must be set to dynamic
             - wwpLeosVplsVirtualCircuitMplsStatus must be set to createAndGo
             - wwpLeosVplsVirtualCircuitMplsName must be specified
             - wwpLeosVplsVirtualCircuitMplsDestAddr must be specified
                                       
             Following MIB objects must be specified while creating static 
             MPLS virtual circuit
             - wwpLeosVplsVirtualCircuitMplsType  must be set to static
             - wwpLeosVplsVirtualCircuitMplsStatus must be set to createAndGo
             - wwpLeosVplsVirtualCircuitMplsName must be specified
             - wwpLeosVplsVirtualCircuitMplsDestAddr must be specified
             - wwpLeosVplsVirtualCircuitMplsEncapLabel must be specified (2048..18431)
             - wwpLeosVplsVirtualCircuitMplsDecapLabel must be specified (2048..18431)"
             
     ::= { wwpLeosVpls 15 }
     
 wwpLeosVplsVirtualCircuitMplsEntry  OBJECT-TYPE
     SYNTAX       WwpLeosVplsVirtualCircuitMplsEntry
     MAX-ACCESS   not-accessible
     STATUS       current
     DESCRIPTION
             "The virtual circuit table entry index by 
              wwpLeosVplsVirtualCircuitMplsIndex."
     INDEX { wwpLeosVplsVirtualCircuitMplsIndex }
     ::= { wwpLeosVplsVirtualCircuitMplsTable 1 }
     
 WwpLeosVplsVirtualCircuitMplsEntry ::=  SEQUENCE {
     wwpLeosVplsVirtualCircuitMplsIndex                         INTEGER,
     wwpLeosVplsVirtualCircuitMplsName                          DisplayString,
     wwpLeosVplsVirtualCircuitMplsType                          INTEGER,
     wwpLeosVplsVirtualCircuitMplsDestAddr                      IpAddress,
     wwpLeosVplsVirtualCircuitMplsTunnelPolicy                  INTEGER,
     wwpLeosVplsVirtualCircuitMplsFixedTunnelId                 INTEGER,
     wwpLeosVplsVirtualCircuitMplsActiveTunnelId                INTEGER,
     wwpLeosVplsVirtualCircuitMplsOperStatus                    INTEGER,
     wwpLeosVplsVirtualCircuitMplsEncapLabel                    Unsigned32,
     wwpLeosVplsVirtualCircuitMplsDecapLabel                    Unsigned32,
     wwpLeosVplsVirtualCircuitMplsGroupId                       Unsigned32,
     wwpLeosVplsVirtualCircuitMplsProtectionType                INTEGER,     
     wwpLeosVplsVirtualCircuitMplsStatusTlv                     INTEGER,
     wwpLeosVplsVirtualCircuitMplsMtu                           INTEGER,
     wwpLeosVplsVirtualCircuitMplsStatus                        RowStatus
 } 
 
  wwpLeosVplsVirtualCircuitMplsIndex OBJECT-TYPE
     SYNTAX      INTEGER (1..65535)
     MAX-ACCESS  read-only
     STATUS      current
     DESCRIPTION
        "This represents the virtual circuit index in the table.
         This number should be unique in the table."
     ::= { wwpLeosVplsVirtualCircuitMplsEntry 1 }
  
  wwpLeosVplsVirtualCircuitMplsName OBJECT-TYPE
     SYNTAX      DisplayString (SIZE (1..15))
     MAX-ACCESS  read-create
     STATUS      current
     DESCRIPTION
        "This represents the name of the vrtual circuit associated 
         with the given virtual circuit.
         Mpls and Ethernet virtual circuit name name cannot be same 
         but indexes can be "
     ::= { wwpLeosVplsVirtualCircuitMplsEntry 2 } 
 
  wwpLeosVplsVirtualCircuitMplsType OBJECT-TYPE
     SYNTAX      INTEGER {
                                dynamic(1),
                                static(2)
                        }
     MAX-ACCESS  read-create
     STATUS      current
     DESCRIPTION
        "This represents the type of the virtual circuit."
     ::= { wwpLeosVplsVirtualCircuitMplsEntry 3 }
   
  wwpLeosVplsVirtualCircuitMplsDestAddr OBJECT-TYPE
     SYNTAX      IpAddress
     MAX-ACCESS  read-create
     STATUS      current
     DESCRIPTION
        "This represents the destination address used 
         by the signaling protocol if wwpLeosVplsVirtualCircuitMplsType is
         set to dynamic.
         This object cannot be modified once entry is created."
     ::= { wwpLeosVplsVirtualCircuitMplsEntry 4 } 
  
  wwpLeosVplsVirtualCircuitMplsTunnelPolicy OBJECT-TYPE
     SYNTAX      INTEGER {
                                fixed(1),
                                firstAvailable(2)                       
                         }
     MAX-ACCESS  read-create
     STATUS      current
     DESCRIPTION
        "This object represents that this virtual circuit should select the tunnel
         as fixed or should it use the first active tunnel avaiable on the outgoing port.
         If this object is set to fixed then wwpLeosVplsVirtualCircuitMplsTunnelIndx must
         be specified."
     DEFVAL { firstAvailable }
     ::= { wwpLeosVplsVirtualCircuitMplsEntry 5 }
  
  wwpLeosVplsVirtualCircuitMplsFixedTunnelId OBJECT-TYPE
     SYNTAX      INTEGER (0..65535)
     MAX-ACCESS  read-create
     STATUS      current
     DESCRIPTION
        "This represents the tunnel that this virtual circuit should be mapped to.
         This object is only used if wwpLeosVplsVirtualCircuitMplsTunnelPolicy is set
         to fixed."
     DEFVAL { 0 }
     ::= { wwpLeosVplsVirtualCircuitMplsEntry 6 }
     
  wwpLeosVplsVirtualCircuitMplsActiveTunnelId OBJECT-TYPE
     SYNTAX      INTEGER (0..65535)
     MAX-ACCESS  read-only
     STATUS      current
     DESCRIPTION
        "This represents the tunnel that this virtual circuit is currently using.
         This object is equal to wwpLeosVplsVirtualCircuitMplsFixedTunnelId if
         wwpLeosVplsVirtualCircuitMplsTunnelPolicy is set to fixed."
     ::= { wwpLeosVplsVirtualCircuitMplsEntry 7 }  
  
  wwpLeosVplsVirtualCircuitMplsOperStatus OBJECT-TYPE
     SYNTAX      INTEGER {
                        enabled(1),
                        disabled(2)
                         }
     MAX-ACCESS  read-only
     STATUS      current
     DESCRIPTION
        "This represents the operational status of the virtual circuit."
     ::= { wwpLeosVplsVirtualCircuitMplsEntry 8 }
     
  wwpLeosVplsVirtualCircuitMplsEncapLabel OBJECT-TYPE
     SYNTAX      Unsigned32  (0..1048576)
     MAX-ACCESS  read-create
     STATUS      current
     DESCRIPTION
        "If wwpLeosVplsVirtualCircuitMplsType is set to static
         then this object specifies the encap label the should be used 
         for this virtual circuit. Label should be in the range 2048..18431.
         If the label is not yet known (signaling in process), the  
         object should return a value of 0xFFFF."
     ::= { wwpLeosVplsVirtualCircuitMplsEntry 9 }
     
  wwpLeosVplsVirtualCircuitMplsDecapLabel OBJECT-TYPE
     SYNTAX      Unsigned32 (0..1048576)
     MAX-ACCESS  read-create
     STATUS      current
     DESCRIPTION
        "If wwpLeosVplsVirtualCircuitMplsType is set to static
         then this object specifies the decap label the should be used 
         for this virtual circuit. Label should be in the range 2048..18431.
         If the label is not yet known (signaling in process), the  
         object should return a value of 0xFFFF."
     ::= { wwpLeosVplsVirtualCircuitMplsEntry 10 }
      
  wwpLeosVplsVirtualCircuitMplsGroupId OBJECT-TYPE
     SYNTAX       Unsigned32
     MAX-ACCESS  read-create
     STATUS      current
     DESCRIPTION
        "This represents the group ID advertised in the LDP signaling
         if wwpLeosVplsVirtualCircuitMplsType is set to dynamic."
     DEFVAL { 0 }
     ::= { wwpLeosVplsVirtualCircuitMplsEntry 11 }  
  
  wwpLeosVplsVirtualCircuitMplsProtectionType OBJECT-TYPE
     SYNTAX      INTEGER {
     				primary(1),
     				secondary(2)
     				}
     MAX-ACCESS  read-create
     STATUS      current
     DESCRIPTION
        "This represents that this virtual circuit is primary or secondary
         virtual circuit. If primary virtual circuit goes down that secondary 
         virtual circuit will be used."
     DEFVAL { secondary }
     ::= { wwpLeosVplsVirtualCircuitMplsEntry 12 }
      
  wwpLeosVplsVirtualCircuitMplsStatusTlv OBJECT-TYPE
     SYNTAX      TruthValue
     MAX-ACCESS  read-create
     STATUS      current
     DESCRIPTION
        "This mib specifies that the Status TLV in LDP signaling should be advewrtised or not.
         This mib object is only used if wwpLeosVplsVirtualCircuitMplsType is set to dynamic.
         This field cannot be modified while wwpLeosVplsVirtualCircuitMplsStatus is active"
     DEFVAL { false }
     ::= { wwpLeosVplsVirtualCircuitMplsEntry 13 }
                                          
  wwpLeosVplsVirtualCircuitMplsMtu    OBJECT-TYPE
     SYNTAX         INTEGER (1500..9216)     
     MAX-ACCESS     read-write
     STATUS         current
     DESCRIPTION
             "Setting this object will set the MTU for this VC.
              This MTU is advertised to the peer if wwpLeosVplsVirtualCircuitMplsType
              is set to dynamic."              
     DEFVAL { 9190 }
     ::= { wwpLeosVplsVirtualCircuitMplsEntry 14 }
 
  wwpLeosVplsVirtualCircuitMplsStatus OBJECT-TYPE
     SYNTAX      RowStatus
     MAX-ACCESS  read-create
     STATUS      current
     DESCRIPTION
        "Used to manage the creation and deletion of the           
         conceptual rows in this table.
         To create a row in this table, a manager must
         set this object to 'createAndGo'. To delete a row in this
         table, a manager must set this object to 'destroy'.
         If the entry exists, it will be displayed as 'active'."
     ::= { wwpLeosVplsVirtualCircuitMplsEntry 15 }
 
 --
 -- VPLS MPLS VC Stats Table
 -- 
 wwpLeosVplsVirtualCircuitMplsStatsTable OBJECT-TYPE
     SYNTAX     SEQUENCE OF WwpLeosVplsVirtualCircuitMplsStatsEntry
     MAX-ACCESS not-accessible
     STATUS     current
     DESCRIPTION
            "The (conceptual) table listing the mpls virtual circuit stats
             table."
     ::= { wwpLeosVpls 16 }
     
 wwpLeosVplsVirtualCircuitMplsStatsEntry  OBJECT-TYPE
     SYNTAX       WwpLeosVplsVirtualCircuitMplsStatsEntry
     MAX-ACCESS   not-accessible
     STATUS       current
     DESCRIPTION
             "The mpls virtual circuit stats table entry index by 
              wwpLeosVplsVirtualCircuitMplsIndex."
     INDEX { wwpLeosVplsVirtualCircuitMplsIndex }
     ::= { wwpLeosVplsVirtualCircuitMplsStatsTable 1 }
     
 WwpLeosVplsVirtualCircuitMplsStatsEntry ::=  SEQUENCE {   
         wwpLeosVplsVirtualCircuitMplsTxBytesHi Counter32,
         wwpLeosVplsVirtualCircuitMplsTxBytesLo Counter32,    
         wwpLeosVplsVirtualCircuitMplsRxBytesHi Counter32,
         wwpLeosVplsVirtualCircuitMplsRxBytesLo Counter32
 }
 
 wwpLeosVplsVirtualCircuitMplsTxBytesHi OBJECT-TYPE
     SYNTAX      Counter32
     MAX-ACCESS  read-only
     STATUS      current
     DESCRIPTION
        "This represents the total number of higher 32 bits transmitted for 
         given virtual circuit."
     ::= { wwpLeosVplsVirtualCircuitMplsStatsEntry 1 }
     
 wwpLeosVplsVirtualCircuitMplsTxBytesLo OBJECT-TYPE
     SYNTAX      Counter32
     MAX-ACCESS  read-only
     STATUS      current
     DESCRIPTION
        "This represents the total number of lower 32 bits transmitted for 
         given virtual circuit."
     ::= { wwpLeosVplsVirtualCircuitMplsStatsEntry 2 }
      
 wwpLeosVplsVirtualCircuitMplsRxBytesHi OBJECT-TYPE
     SYNTAX      Counter32
     MAX-ACCESS  read-only
     STATUS      current
     DESCRIPTION
        "This represents the total number of higher 32 bits received for 
         given mpls virtual circuit."
     ::= { wwpLeosVplsVirtualCircuitMplsStatsEntry 3 }
     
 wwpLeosVplsVirtualCircuitMplsRxBytesLo OBJECT-TYPE
     SYNTAX      Counter32
     MAX-ACCESS  read-only
     STATUS      current
     DESCRIPTION
        "This represents the total number of lower 32 bits received for 
         given virtual circuit."
     ::= { wwpLeosVplsVirtualCircuitMplsStatsEntry 4 }

 --
 -- Virtual circuit ethernet table
 -- 
 wwpLeosVplsVirtualCircuitEthTable OBJECT-TYPE
     SYNTAX     SEQUENCE OF WwpLeosVplsVirtualCircuitEthEntry
     MAX-ACCESS not-accessible
     STATUS     current
     DESCRIPTION
            "The (conceptual) table listing the virtual circuit table.
             To create entry use SNMP, multiple set operation must 
             be usedd because following mib objects needs to be set 
             while creating entry in the table.
             Mpls and Ethernet virtual circuit name name cannot be same but indexes can be 
             - wwpLeosVplsVirtualCircuitEthName must be specified
             - wwpLeosVplsVirtualCircuitEthProviderVlanId must be specified and must exist
               on the device.
             - wwpLeosVplsVirtualCircuitEthStatus must be specified."
     ::= { wwpLeosVpls 17 }
     
 wwpLeosVplsVirtualCircuitEthEntry  OBJECT-TYPE
     SYNTAX       WwpLeosVplsVirtualCircuitEthEntry
     MAX-ACCESS   not-accessible
     STATUS       current
     DESCRIPTION
             "The virtual circuit table entry index by 
              wwpLeosVplsVirtualCircuitMplsIndex."
     INDEX { wwpLeosVplsVirtualCircuitEthIndex }
     ::= { wwpLeosVplsVirtualCircuitEthTable 1 }
     
 WwpLeosVplsVirtualCircuitEthEntry ::=  SEQUENCE {
     wwpLeosVplsVirtualCircuitEthIndex                         INTEGER,
     wwpLeosVplsVirtualCircuitEthName                          DisplayString,          
     wwpLeosVplsVirtualCircuitEthProviderVlanId                VlanId,
     wwpLeosVplsVirtualCircuitEthRowStatus                     RowStatus
 }
 
 wwpLeosVplsVirtualCircuitEthIndex OBJECT-TYPE
     SYNTAX      INTEGER (1..65535)
     MAX-ACCESS  read-only
     STATUS      current
     DESCRIPTION
        "This represents the virtual circuit index in the table.
         This number should be unique in the table."
     ::= { wwpLeosVplsVirtualCircuitEthEntry 1 }
 
 wwpLeosVplsVirtualCircuitEthName OBJECT-TYPE
     SYNTAX      DisplayString (SIZE (1..15))
     MAX-ACCESS  read-create
     STATUS      current
     DESCRIPTION
        "This represents the name of the vrtual circuit associated 
         with the given virtual circuit.
         Mpls and Ethernet virtual circuit name name cannot be same but indexes can be "
     ::= { wwpLeosVplsVirtualCircuitEthEntry 2 } 
  
 wwpLeosVplsVirtualCircuitEthProviderVlanId OBJECT-TYPE
     SYNTAX      VlanId
     MAX-ACCESS  read-write
     STATUS      current
     DESCRIPTION
        "This represents the provider vlan id associated with the virtual circuit for
         a given wwpLeosVplsVirtualCircuitMplsIndex."
     ::= { wwpLeosVplsVirtualCircuitEthEntry 3 }
                                            
  wwpLeosVplsVirtualCircuitEthRowStatus OBJECT-TYPE
     SYNTAX      RowStatus
     MAX-ACCESS  read-create
     STATUS      current
     DESCRIPTION
        "Used to manage the creation and deletion of the 
             conceptual rows in this table.
             To create a row in this table, a manager must
             set this object to 'createAndGo'. To delete a row in this
             table, a manager must set this object to 'destroy'
             If the entry exists, it will be displayed as 'active'."
     ::= { wwpLeosVplsVirtualCircuitEthEntry 4 }

 --
 -- Ether Type Table
 --                                                 
 wwpLeosVplsVirtualCircuitEtherTypeTable OBJECT-TYPE
     SYNTAX     SEQUENCE OF WwpLeosVplsVirtualCircuitEtherTypeEntry
     MAX-ACCESS not-accessible
     STATUS     current
     DESCRIPTION
            "The (conceptual) table listing the ether type to be used 
             for each port."
     ::= { wwpLeosVpls 18 }
     
 wwpLeosVplsVirtualCircuitEtherTypeEntry  OBJECT-TYPE
     SYNTAX       WwpLeosVplsVirtualCircuitEtherTypeEntry
     MAX-ACCESS   not-accessible
     STATUS       current
     DESCRIPTION
             "The entry to assign ether type for each port."
     INDEX {wwpLeosVplsVirtualCircuitPortId}
     ::= { wwpLeosVplsVirtualCircuitEtherTypeTable 1 }
     
 WwpLeosVplsVirtualCircuitEtherTypeEntry ::=  SEQUENCE { 
     wwpLeosVplsVirtualCircuitPortId              INTEGER,
     wwpLeosVplsVirtualCircuitEtherType           INTEGER,
     wwpLeosVplsVirtualCircuitEtherTypePolicy     INTEGER
 }

 wwpLeosVplsVirtualCircuitPortId OBJECT-TYPE
     SYNTAX           INTEGER (1..65535)
     MAX-ACCESS       read-write
     STATUS           current
     DESCRIPTION
             "This object specifies the port number used as index in the 
              table."    
     ::= { wwpLeosVplsVirtualCircuitEtherTypeEntry 1 }
                                                       
 wwpLeosVplsVirtualCircuitEtherType OBJECT-TYPE
     SYNTAX           INTEGER {
                           type8100(1),
                           type9100(2)                     
                      }
     MAX-ACCESS       read-write
     STATUS           current
     DESCRIPTION
             "This object specifies the ethertype of the outer VLAN tag
              for given port."
         DEFVAL { type8100 }
     ::= { wwpLeosVplsVirtualCircuitEtherTypeEntry 2 }
       
 wwpLeosVplsVirtualCircuitEtherTypePolicy OBJECT-TYPE
     SYNTAX           INTEGER {
                           all(1),
                           encapOnly(2)                     
                      }
     MAX-ACCESS       read-write
     STATUS           current
     DESCRIPTION
             "This object specifies the policy for the ethertype of the outer VLAN tag
              for given port.  All means all frames will have the type set in wwpLeosVplsVirtualCircuitEtherType.
              encapOnly means only Q-in-Q encapsulated frames will use that value.
              If wwpLeosVplsVirtualCircuitEtherType is set to type8100 then ALL will always
              be the operational value for this item."
         DEFVAL { encapOnly }
     ::= { wwpLeosVplsVirtualCircuitEtherTypeEntry 3 }  

 --
 -- VPLS VC Stats Table
 -- 
 wwpLeosVplsVirtualCircuitEthStatsTable OBJECT-TYPE
     SYNTAX     SEQUENCE OF WwpLeosVplsVirtualCircuitEthStatsEntry
     MAX-ACCESS not-accessible
     STATUS     current
     DESCRIPTION
            "The (conceptual) table listing the virtual circuit stats
             table."
     ::= { wwpLeosVpls 19 }
     
 wwpLeosVplsVirtualCircuitEthStatsEntry  OBJECT-TYPE
     SYNTAX       WwpLeosVplsVirtualCircuitEthStatsEntry
     MAX-ACCESS   not-accessible
     STATUS       current
     DESCRIPTION
             "The ethernet virtual circuit stats table entry index by 
              wwpLeosVplsVirtualCircuitMplsIndex."
     INDEX { wwpLeosVplsVirtualCircuitEthIndex }
     ::= { wwpLeosVplsVirtualCircuitEthStatsTable 1 }
     
 WwpLeosVplsVirtualCircuitEthStatsEntry ::=  SEQUENCE {   
         wwpLeosVplsVirtualCircuitEthTxBytesHi Counter32,
         wwpLeosVplsVirtualCircuitEthTxBytesLo Counter32,    
         wwpLeosVplsVirtualCircuitEthRxBytesHi Counter32,
         wwpLeosVplsVirtualCircuitEthRxBytesLo Counter32
 }
 
 wwpLeosVplsVirtualCircuitEthTxBytesHi OBJECT-TYPE
     SYNTAX      Counter32
     MAX-ACCESS  read-only
     STATUS      current
     DESCRIPTION
        "This represents the total number of higher 32 bits transmitted for 
         given virtual circuit."
     ::= { wwpLeosVplsVirtualCircuitEthStatsEntry 1 }
     
 wwpLeosVplsVirtualCircuitEthTxBytesLo OBJECT-TYPE
     SYNTAX      Counter32
     MAX-ACCESS  read-only
     STATUS      current
     DESCRIPTION
        "This represents the total number of lower 32 bits transmitted for 
         given virtual circuit."
     ::= { wwpLeosVplsVirtualCircuitEthStatsEntry 2 }
      
 wwpLeosVplsVirtualCircuitEthRxBytesHi OBJECT-TYPE
     SYNTAX      Counter32
     MAX-ACCESS  read-only
     STATUS      current
     DESCRIPTION
        "This represents the total number of higher 32 bits received for 
         given virtual circuit."
     ::= { wwpLeosVplsVirtualCircuitEthStatsEntry 3 }
     
 wwpLeosVplsVirtualCircuitEthRxBytesLo OBJECT-TYPE
     SYNTAX      Counter32
     MAX-ACCESS  read-only
     STATUS      current
     DESCRIPTION
        "This represents the total number of lower 32 bits received for 
         given virtual circuit."
     ::= { wwpLeosVplsVirtualCircuitEthStatsEntry 4 }
 
 --
 --  Virtual Switch Mpls Table
 -- 
 wwpLeosVplsVirtualSwitchMplsTable OBJECT-TYPE
     SYNTAX       SEQUENCE OF WwpLeosVplsVirtualSwitchMplsEntry
     MAX-ACCESS   not-accessible
     STATUS       current
     DESCRIPTION
             "This table is used to manage virtual switch entries
              on the device."
     ::= { wwpLeosVpls 20 }
                
 wwpLeosVplsVirtualSwitchMplsEntry  OBJECT-TYPE
     SYNTAX       WwpLeosVplsVirtualSwitchMplsEntry
     MAX-ACCESS   not-accessible
     STATUS       current
     DESCRIPTION
             "This entry corresponds to single entry in wwpLeosVplsVirtualSwitchMplsTable 
              table.
              To create an entry in the table following criteria must be met.
              Mpls and Ethernet virtual switch name name cannot be same but indexes can be 
              - wwpLeosVplsVirtualSwitchMplsVpnId must be specified.
              - wwpLeosVplsVirtualSwitchMplsType must be specified.
              - wwpLeosVplsVirtualSwitchMplsName must be specified.
              - wwpLeosVplsVirtualSwitchMplsStatus must be specified."
     INDEX { wwpLeosVplsVirtualSwitchMplsIndx }
     ::= { wwpLeosVplsVirtualSwitchMplsTable 1 }
     
 WwpLeosVplsVirtualSwitchMplsEntry ::= SEQUENCE {
     wwpLeosVplsVirtualSwitchMplsIndx                           INTEGER,     
     wwpLeosVplsVirtualSwitchMplsName                           DisplayString,
     wwpLeosVplsVirtualSwitchMplsVpnId                          Unsigned32,     
     wwpLeosVplsVirtualSwitchMplsEncapCosPolicy                 INTEGER,
     wwpLeosVplsVirtualSwitchMplsEncapFixedDot1dPri             INTEGER,
     wwpLeosVplsVirtualSwitchMplsDecapCosPolicy                 INTEGER,
     wwpLeosVplsVirtualSwitchMplsDecapFixedDot1dPri             INTEGER,
     wwpLeosVplsVirtualSwitchMplsCtrlProtocolTunnelState        INTEGER, 
     wwpLeosVplsVirtualSwitchMplsDecapTTLPolicy                 INTEGER,         
     wwpLeosVplsVirtualSwitchMplsType							       INTEGER,
     wwpLeosVplsVirtualSwitchMplsRowStatus                      RowStatus,
     wwpLeosVplsVirtualSwitchMplsMacLrnState                    INTEGER,
     wwpLeosVplsVirtualSwitchMplsTunnelMethod					    INTEGER,
     wwpLeosVplsVirtualSwitchMplsCtrlProtocolDot1dPri			    INTEGER,
     wwpLeosVplsVirtualSwitchMplsSubscriberDot1dPolicy          INTEGER,
     wwpLeosVplsVirtualSwitchMplsCtrlProtTransFrameValidate     INTEGER
 }    
     
 wwpLeosVplsVirtualSwitchMplsIndx    OBJECT-TYPE
     SYNTAX         INTEGER (1..65535)
     MAX-ACCESS     read-only
     STATUS         current
     DESCRIPTION
             "This object specifies the virtual switch index which is used as unique 
              index in the table."
     ::= { wwpLeosVplsVirtualSwitchMplsEntry 1 }         
       
 wwpLeosVplsVirtualSwitchMplsName    OBJECT-TYPE
     SYNTAX         DisplayString (SIZE (1..15))
     MAX-ACCESS     read-write
     STATUS         current
     DESCRIPTION
             "This object specifies the virtual switch name. this object can only be specified at the 
              time of creation and cannot be modified later.
              Mpls and Ethernet virtual switch name name cannot be same but indexes can be."
     ::= { wwpLeosVplsVirtualSwitchMplsEntry 2 }
 
  wwpLeosVplsVirtualSwitchMplsVpnId    OBJECT-TYPE
     SYNTAX         Unsigned32
     MAX-ACCESS     read-write
     STATUS         current
     DESCRIPTION
             "This object specifies the subscriber vlan Id for given virtual switch."
     ::= { wwpLeosVplsVirtualSwitchMplsEntry 3 }

  wwpLeosVplsVirtualSwitchMplsEncapCosPolicy    OBJECT-TYPE
     SYNTAX         INTEGER {
                        fixed(1),                        
                        inheritDot1dPri(2),
                                                inheritIpPrec(3),                                               
                                                inheritPhbg(4)                          
                        }
     MAX-ACCESS     read-write
     STATUS         current
     DESCRIPTION
             "This object specifies the ingress cos policy for given virtual switch."
     DEFVAL { fixed }
     ::= { wwpLeosVplsVirtualSwitchMplsEntry 4 }
 
 wwpLeosVplsVirtualSwitchMplsEncapFixedDot1dPri    OBJECT-TYPE
     SYNTAX         INTEGER (0..7)
     MAX-ACCESS     read-write
     STATUS         current
     DESCRIPTION
             "This object specifies the ingress fixed cos attributes for given virtual switch."
     DEFVAL { 2 }
     ::= { wwpLeosVplsVirtualSwitchMplsEntry 5 }

 wwpLeosVplsVirtualSwitchMplsDecapCosPolicy    OBJECT-TYPE
     SYNTAX         INTEGER {
                        fixed(1),
                        inheritVc(2),
                        inheritTunnel(3),
                        leave(4)                        
                        }
     MAX-ACCESS     read-write
     STATUS         current
     DESCRIPTION
             "This object specifies the egress cos policy for given virtual switch."
     DEFVAL { leave }
     ::= { wwpLeosVplsVirtualSwitchMplsEntry 6 }
 
 wwpLeosVplsVirtualSwitchMplsDecapFixedDot1dPri    OBJECT-TYPE
     SYNTAX         INTEGER (0..7)
     MAX-ACCESS     read-write
     STATUS         current
     DESCRIPTION
             "This object specifies the egress cos attributes for given virtual switch."
     DEFVAL { 2 }
     ::= { wwpLeosVplsVirtualSwitchMplsEntry 7 }    
         
 wwpLeosVplsVirtualSwitchMplsCtrlProtocolTunnelState    OBJECT-TYPE
     SYNTAX         INTEGER {
                        enabled(1),
                        disabled(2)                      
                        }
     MAX-ACCESS     read-write
     STATUS         current
     DESCRIPTION
             "This object enables or disables control protocol tunneling for a given 
              virtual switch."
     DEFVAL { disabled }
     ::= { wwpLeosVplsVirtualSwitchMplsEntry 8 } 
 
 wwpLeosVplsVirtualSwitchMplsDecapTTLPolicy    OBJECT-TYPE
     SYNTAX         INTEGER {
                        pipe(1),
                        uniform(2)
                        }
     MAX-ACCESS     read-write
     STATUS         current
     DESCRIPTION
             "This object specifies the TTL policy for a given virtual switch."
     DEFVAL { pipe }
     ::= { wwpLeosVplsVirtualSwitchMplsEntry 9 }         
     
 wwpLeosVplsVirtualSwitchMplsType    OBJECT-TYPE
     SYNTAX         INTEGER {
                        static(1),
                        dynamic(2)
                        }
     MAX-ACCESS     read-create
     STATUS         current
     DESCRIPTION
             "This object specifies the type of virtual switch."     
     ::= { wwpLeosVplsVirtualSwitchMplsEntry 10 }    
   
 wwpLeosVplsVirtualSwitchMplsRowStatus    OBJECT-TYPE
     SYNTAX         RowStatus
     MAX-ACCESS     read-create
     STATUS         current
     DESCRIPTION
             "This object can be set to 'createAndGo' to create entry in the table. 
              This object can be set to 'destory' to delete entry in the table.
              Following objects must be set to valid values to create entry in the table."
     ::= { wwpLeosVplsVirtualSwitchMplsEntry 11 } 
     
 wwpLeosVplsVirtualSwitchMplsMacLrnState    OBJECT-TYPE
     SYNTAX         INTEGER {
     					enabled (1),
     					disabled (2)
     			    }
     MAX-ACCESS     read-write
     STATUS         current
     DESCRIPTION
             "Setting this object will set the Mac learning state for a given mpls virtual switch."
     DEFVAL			{ enabled }
     ::= { wwpLeosVplsVirtualSwitchMplsEntry 12 }
 
 wwpLeosVplsVirtualSwitchMplsTunnelMethod    OBJECT-TYPE
     SYNTAX         INTEGER {
     					l2pt (1),
     					transparent (2)
     			    }
     MAX-ACCESS     read-write
     STATUS         current
     DESCRIPTION
             "Setting this object will set the tunneling method for a given mpls virtual switch." 
     DEFVAL			{ l2pt }
     ::= { wwpLeosVplsVirtualSwitchMplsEntry 13 }   
  
 wwpLeosVplsVirtualSwitchMplsCtrlProtocolDot1dPri    OBJECT-TYPE
     SYNTAX         INTEGER (0..7)
     MAX-ACCESS     read-write
     STATUS         current
     DESCRIPTION
             "This object specifies the .1d priority to use when encapsulation control frames."
     DEFVAL { 6 }
     ::= { wwpLeosVplsVirtualSwitchMplsEntry 14 }    
   
 wwpLeosVplsVirtualSwitchMplsSubscriberDot1dPolicy   OBJECT-TYPE
     SYNTAX         INTEGER {
     					leave (1),
     					provider-inherit (2)
     			    }
     MAX-ACCESS     read-write
     STATUS         current
     DESCRIPTION
             "Setting this object will configure the policy used to decide whether or not the
              subscriber frame .1d priorty should be left alone, or remarked to the computed provider priority."
     DEFVAL { leave }
     ::= { wwpLeosVplsVirtualSwitchMplsEntry 15 }   

 wwpLeosVplsVirtualSwitchMplsCtrlProtTransFrameValidate    OBJECT-TYPE
     SYNTAX         INTEGER {
     					enabled (1),
     					disabled (2)
     			    }
     MAX-ACCESS     read-write
     STATUS         current
     DESCRIPTION
             "Setting this object will set the transparent-mode validate for a given mpls virtual switch." 
     DEFVAL			{ disabled }
     ::= { wwpLeosVplsVirtualSwitchMplsEntry 16 }   


 --
 --  virtual switch mpls membership Table
 -- 
 wwpLeosVplsVirtualSwitchMplsMemberTable OBJECT-TYPE
     SYNTAX       SEQUENCE OF WwpLeosVplsVirtualSwitchMplsMemberEntry
     MAX-ACCESS   not-accessible
     STATUS       current
     DESCRIPTION
             "This table is used to create mpls virtual switch subscriber port-vlan membership entry."
     ::= { wwpLeosVpls 21 }
                
 wwpLeosVplsVirtualSwitchMplsMemberEntry  OBJECT-TYPE
     SYNTAX       WwpLeosVplsVirtualSwitchMplsMemberEntry
     MAX-ACCESS   not-accessible
     STATUS       current
     DESCRIPTION
             "This entry corresponds to single port-vlan subscriber entry in 
              wwpLeosVplsVirtualSwitchMplsMemberTable table."
     INDEX { wwpLeosVplsVirtualSwitchMplsIndx, wwpLeosVplsVirtualSwitchMplsMemberPortId }
     ::= { wwpLeosVplsVirtualSwitchMplsMemberTable 1 }
     
 WwpLeosVplsVirtualSwitchMplsMemberEntry ::= SEQUENCE {
     wwpLeosVplsVirtualSwitchMplsMemberPortId               INTEGER,
     wwpLeosVplsVirtualSwitchMplsMemberVlanId               INTEGER,
     wwpLeosVplsVirtualSwitchMplsMemberRowStatus            RowStatus
 }    
 
 wwpLeosVplsVirtualSwitchMplsMemberPortId    OBJECT-TYPE
     SYNTAX         INTEGER (1..65535)
     MAX-ACCESS     read-create
     STATUS         current
     DESCRIPTION
             "This object specifes the port number which is to be added as 
              a customer facing port for the mpls virtual switch index
              wwpLeosVplsVirtualSwitchMplsIndx."
     ::= { wwpLeosVplsVirtualSwitchMplsMemberEntry 1 }

 wwpLeosVplsVirtualSwitchMplsMemberVlanId    OBJECT-TYPE
     SYNTAX         INTEGER (0..4094)
     MAX-ACCESS     read-create
     STATUS         current
     DESCRIPTION
             "This object specifies the subscriber vlan attached to this
              mpls virtual switch index wwpLeosVplsVirtualSwitchMplsIndx.
              This object cannot be modified one entry is created in this table.
              This object can only be specifed when creating entries in this table."
     ::= { wwpLeosVplsVirtualSwitchMplsMemberEntry 2 }

  wwpLeosVplsVirtualSwitchMplsMemberRowStatus    OBJECT-TYPE
     SYNTAX         RowStatus
     MAX-ACCESS     read-create
     STATUS         current
     DESCRIPTION
             "Used to manage the creation and deletion of the 
             conceptual rows in this table.
             To create a row in this table, a manager must
             set this object to 'createAndGo'. To delete a row in this
             table, a manager must set this object to 'destroy'.
             If the entry exists, it will be displayed as 'active'."
     ::= { wwpLeosVplsVirtualSwitchMplsMemberEntry 3 }

 --
 -- VPLS MPLS VS Member stats Table
 -- 
 wwpLeosVplsVirtualSwitchMplsMemberStatsTable OBJECT-TYPE
     SYNTAX     SEQUENCE OF WwpLeosVplsVirtualSwitchMplsMemberStatsEntry
     MAX-ACCESS not-accessible
     STATUS     current
     DESCRIPTION
            "The (conceptual) table listing the virtual switch member stats
             table."
     ::= { wwpLeosVpls 22 }
     
 wwpLeosVplsVirtualSwitchMplsMemberStatsEntry  OBJECT-TYPE
     SYNTAX       WwpLeosVplsVirtualSwitchMplsMemberStatsEntry
     MAX-ACCESS   not-accessible
     STATUS       current
     DESCRIPTION
             "The virtual switch member stats table entry index by 
              wwpLeosVplsVirtualSwitchMplsIndx and wwpLeosVplsVirtualSwitchMplsMemberPortId."
     INDEX { wwpLeosVplsVirtualSwitchMplsIndx, wwpLeosVplsVirtualSwitchMplsMemberPortId }
     ::= { wwpLeosVplsVirtualSwitchMplsMemberStatsTable 1 }
     
 WwpLeosVplsVirtualSwitchMplsMemberStatsEntry ::=  SEQUENCE {   
         wwpLeosVplsVirtualSwitchMplsMemberRxBytesHi        Counter32,
         wwpLeosVplsVirtualSwitchMplsMemberRxBytesLo        Counter32
 }
       
 wwpLeosVplsVirtualSwitchMplsMemberRxBytesHi OBJECT-TYPE
     SYNTAX      Counter32
     MAX-ACCESS  read-only
     STATUS      current
     DESCRIPTION
        "This represents the total number of higher 32 bits received for 
         given mpls virtual switch member port."
     ::= { wwpLeosVplsVirtualSwitchMplsMemberStatsEntry 1 }
     
 wwpLeosVplsVirtualSwitchMplsMemberRxBytesLo OBJECT-TYPE
     SYNTAX      Counter32
     MAX-ACCESS  read-only
     STATUS      current
     DESCRIPTION
        "This represents the total number of lower 32 bits received for 
         given virtual switch member port."
     ::= { wwpLeosVplsVirtualSwitchMplsMemberStatsEntry 2 }

 --
 --  virtual switch mpls mesh-vc membership Table
 -- 
 wwpLeosVplsVirtualSwitchMplsMemberMeshVcTable OBJECT-TYPE
     SYNTAX       SEQUENCE OF WwpLeosVplsVirtualSwitchMplsMemberMeshVcEntry
     MAX-ACCESS   not-accessible
     STATUS       current
     DESCRIPTION
             "This table is used to create mpls virtual switch mesh-vc membership entry."
     ::= { wwpLeosVpls 23 }
                
 wwpLeosVplsVirtualSwitchMplsMemberMeshVcEntry  OBJECT-TYPE
     SYNTAX       WwpLeosVplsVirtualSwitchMplsMemberMeshVcEntry
     MAX-ACCESS   not-accessible
     STATUS       current
     DESCRIPTION
             "This entry corresponds to single mesh-vc entry in 
              wwpLeosVplsVirtualSwitchMplsMemberMeshVcTable table."
     INDEX { wwpLeosVplsVirtualSwitchMplsIndx, wwpLeosVplsVirtualSwitchMplsMemberMeshVcMeshVc }
     ::= { wwpLeosVplsVirtualSwitchMplsMemberMeshVcTable 1 }
     
 WwpLeosVplsVirtualSwitchMplsMemberMeshVcEntry ::= SEQUENCE {
     wwpLeosVplsVirtualSwitchMplsMemberMeshVcMeshVc      INTEGER,
     wwpLeosVplsVirtualSwitchMplsMemberMeshVcRowStatus   RowStatus
 }    

 wwpLeosVplsVirtualSwitchMplsMemberMeshVcMeshVc    OBJECT-TYPE
     SYNTAX         INTEGER (1..65535)
     MAX-ACCESS     read-only
     STATUS         current
     DESCRIPTION
             "This object specifes the mesh virtual circuit for this mpls
              virtual switch."
     ::= { wwpLeosVplsVirtualSwitchMplsMemberMeshVcEntry 1 }
 
  wwpLeosVplsVirtualSwitchMplsMemberMeshVcRowStatus    OBJECT-TYPE
     SYNTAX         RowStatus
     MAX-ACCESS     read-create
     STATUS         current
     DESCRIPTION
             "Used to manage the creation and deletion of the 
             conceptual rows in this table.
             To create a row in this table, a manager must
             set this object to 'createAndGo'. To delete a row in this
             table, a manager must set this object to 'destroy'.
             If the entry exists, it will be displayed as 'active'."
     ::= { wwpLeosVplsVirtualSwitchMplsMemberMeshVcEntry 2 }
 
 --
 --  virtual switch mpls ac-vc membership Table
 -- 
 wwpLeosVplsVirtualSwitchMplsMemberAcVcTable OBJECT-TYPE
     SYNTAX       SEQUENCE OF WwpLeosVplsVirtualSwitchMplsMemberAcVcEntry
     MAX-ACCESS   not-accessible
     STATUS       current
     DESCRIPTION
             "This table is used to create mpls virtual switch mesh-vc membership entry."
     ::= { wwpLeosVpls 24 }
                
 wwpLeosVplsVirtualSwitchMplsMemberAcVcEntry  OBJECT-TYPE
     SYNTAX       WwpLeosVplsVirtualSwitchMplsMemberAcVcEntry
     MAX-ACCESS   not-accessible
     STATUS       current
     DESCRIPTION
             "This entry corresponds to single mesh-vc entry in 
              wwpLeosVplsVirtualSwitchMplsMemberAcVcTable table."
     INDEX { wwpLeosVplsVirtualSwitchMplsIndx, wwpLeosVplsVirtualSwitchMplsMemberAcVcAcVc}
     ::= { wwpLeosVplsVirtualSwitchMplsMemberAcVcTable 1 }
     
 WwpLeosVplsVirtualSwitchMplsMemberAcVcEntry ::= SEQUENCE {
     wwpLeosVplsVirtualSwitchMplsMemberAcVcAcVc        INTEGER,
     wwpLeosVplsVirtualSwitchMplsMemberAcVcRowStatus     RowStatus
 }    

 wwpLeosVplsVirtualSwitchMplsMemberAcVcAcVc    OBJECT-TYPE
     SYNTAX         INTEGER (1..65535)
     MAX-ACCESS     read-only
     STATUS         current
     DESCRIPTION
             "This object specifes the attachment virtual circuit for this mpls
              virtual switch."
     ::= { wwpLeosVplsVirtualSwitchMplsMemberAcVcEntry 1 }
 
  wwpLeosVplsVirtualSwitchMplsMemberAcVcRowStatus    OBJECT-TYPE
     SYNTAX         RowStatus
     MAX-ACCESS     read-create
     STATUS         current
     DESCRIPTION
             "Used to manage the creation and deletion of the 
             conceptual rows in this table.
             To create a row in this table, a manager must
             set this object to 'createAndGo'. To delete a row in this
             table, a manager must set this object to 'destroy'.
             If the entry exists, it will be displayed as 'active'."
     ::= { wwpLeosVplsVirtualSwitchMplsMemberAcVcEntry 2 }
  
 --
 -- MPLS VS Control protocol table
 --
 wwpLeosVplsSwitchMplsCtrlProtocolTable OBJECT-TYPE
     SYNTAX     SEQUENCE OF WwpLeosVplsSwitchMplsCtrlProtocolEntry
     MAX-ACCESS not-accessible
     STATUS     current
     DESCRIPTION
            "The (conceptual) table listing the l2 virtual switch control frame 
             protocol status tunnel for a given Vpls."
     ::= { wwpLeosVpls 25 }
     
 wwpLeosVplsSwitchMplsCtrlProtocolEntry  OBJECT-TYPE
     SYNTAX       WwpLeosVplsSwitchMplsCtrlProtocolEntry
     MAX-ACCESS   not-accessible
     STATUS       current
     DESCRIPTION
             "The layer 2 virtual switch control frame protocol tunnel 
              entry for the Vpls."
     INDEX {wwpLeosVplsVirtualSwitchMplsIndx, wwpLeosVplsSwitchMplsCtrlProtocolNum}
     ::= { wwpLeosVplsSwitchMplsCtrlProtocolTable 1 }
     
 WwpLeosVplsSwitchMplsCtrlProtocolEntry ::=  SEQUENCE { 
     wwpLeosVplsSwitchMplsCtrlProtocolNum     INTEGER,
     wwpLeosVplsSwitchMplsCtrlType            INTEGER       
 }

  wwpLeosVplsSwitchMplsCtrlProtocolNum OBJECT-TYPE
     SYNTAX      INTEGER {                     
                     l28021x(1),
                     rstp(2),
                     ciscoCdp(3),
                     ciscoDtp(4),
                     ciscoPagp(5),
                     ciscoPvst(6),
                     ciscoUplinkFast(7),
                     ciscoUdlp(8),
                     ciscoVtp(9),
                     gvrp(10),
                     lacp(11),
                     lacpMarker(12),
                     oam(13),
                     lldp(14),
                     vlanBridge(15)                     
                 }
     MAX-ACCESS  read-only
     STATUS      current
     DESCRIPTION
        "This object represent the list of protocols the device 
         can support."
     ::= { wwpLeosVplsSwitchMplsCtrlProtocolEntry 1 }

  wwpLeosVplsSwitchMplsCtrlType OBJECT-TYPE
     SYNTAX      INTEGER {
                     discard(1),
                     peer(2),
                     tunnel(3)               
                 }
     MAX-ACCESS  read-create
     STATUS      current
     DESCRIPTION
        "Setting this object to 'discard' will cause wwpLeosVplsSwitchMplsCtrlProtocolNum
         frames arriving at the specified UNI to be discarded.  
         Setting this to 'peer' will cause the wwpLeosVplsSwitchMplsCtrlProtocolNum frame
         to be processed by the provider network and cause the provider 
         network to behave as a peer.  
         Setting this to 'tunnel' will cause the wwpLeosVplsSwitchMplsCtrlProtocolNum frame to be 
         tunneled."
     ::= { wwpLeosVplsSwitchMplsCtrlProtocolEntry 2 } 
    
 --
 --  Virtual  Switch Ether Table
 -- 
 wwpLeosVplsVirtualSwitchEthTable OBJECT-TYPE
     SYNTAX       SEQUENCE OF WwpLeosVplsVirtualSwitchEthEntry
     MAX-ACCESS   not-accessible
     STATUS       current
     DESCRIPTION
             "This table is used to manage virtual switch entries
              on the device."
     ::= { wwpLeosVpls 26 }
                
 wwpLeosVplsVirtualSwitchEthEntry  OBJECT-TYPE
     SYNTAX       WwpLeosVplsVirtualSwitchEthEntry
     MAX-ACCESS   not-accessible
     STATUS       current
     DESCRIPTION
             "This entry corresponds to single entry in wwpLeosVplsVirtualSwitchEthernetTable table.
              To create an entry in the table following criteria must be met.
              - wwpLeosVplsVirtualSwitchEthRowStatus must be specified.
              - wwpLeosVplsVirtualSwitchEthernetName must be specified"
     INDEX { wwpLeosVplsVirtualSwitchEthIndx }
     ::= { wwpLeosVplsVirtualSwitchEthTable 1 }
     
 WwpLeosVplsVirtualSwitchEthEntry ::= SEQUENCE {
     wwpLeosVplsVirtualSwitchEthIndx                            INTEGER,     
     wwpLeosVplsVirtualSwitchEthName                            DisplayString,
     wwpLeosVplsVirtualSwitchEthVc                              INTEGER,
     wwpLeosVplsVirtualSwitchEthEncapCosPolicy                  INTEGER,
     wwpLeosVplsVirtualSwitchEthEncapFixedDot1dPri              INTEGER,
     wwpLeosVplsVirtualSwitchEthDecapCosPolicy                  INTEGER,
     wwpLeosVplsVirtualSwitchEthDecapFixedDot1dPri              INTEGER,
     wwpLeosVplsVirtualSwitchEthCtrlProtocolTunnelState         INTEGER,     
     wwpLeosVplsVirtualSwitchEthRowStatus                   	 RowStatus, 
     wwpLeosVplsVirtualSwitchEthMacLrnState						    INTEGER,
     wwpLeosVplsVirtualSwitchEthTunnelMethod					       INTEGER,     
     wwpLeosVplsVirtualSwitchEthCtrlProtocolDot1dPri			    INTEGER,     
     wwpLeosVplsVirtualSwitchEthSubscriberDot1dPolicy			    INTEGER,
     wwpLeosVplsVirtualSwitchEthCtrlProtTransFrameValidate      INTEGER
 }    

 wwpLeosVplsVirtualSwitchEthIndx    OBJECT-TYPE
     SYNTAX         INTEGER (1..65535)
     MAX-ACCESS     read-only
     STATUS         current
     DESCRIPTION
             "This object specifies the virtual switch index which is used as unique 
              index in the table."
     ::= { wwpLeosVplsVirtualSwitchEthEntry 1 }         
       
 wwpLeosVplsVirtualSwitchEthName    OBJECT-TYPE
     SYNTAX         DisplayString (SIZE (1..15))
     MAX-ACCESS     read-create
     STATUS         current
     DESCRIPTION
             "This object specifies the virtual switch name. this object can only be specified at the 
              time of creation and cannot be modified later.
              Mpls and Ethernet virtual switch name name cannot be same but indexes can be."
     ::= { wwpLeosVplsVirtualSwitchEthEntry 2 }
 
 wwpLeosVplsVirtualSwitchEthVc    OBJECT-TYPE
     SYNTAX         INTEGER (0..65535)
     MAX-ACCESS     read-create
     STATUS         current
     DESCRIPTION
             "This object specifies the primary virtual circuit ID associated with this virtual switch.
              To unset it set this to 0."
     ::= { wwpLeosVplsVirtualSwitchEthEntry 3 }

 wwpLeosVplsVirtualSwitchEthEncapCosPolicy    OBJECT-TYPE
     SYNTAX         INTEGER {
                        fixed(1),                        
                        inheritDot1dPri(2),
                        inheritIpPrec(3),                                               
                        inheritPhbg(4)                          
                        }
     MAX-ACCESS     read-write
     STATUS         current
     DESCRIPTION
             "This object specifies the ingress cos policy for given virtual switch."
     DEFVAL { fixed }
     ::= { wwpLeosVplsVirtualSwitchEthEntry 4 }
 
 wwpLeosVplsVirtualSwitchEthEncapFixedDot1dPri    OBJECT-TYPE
     SYNTAX         INTEGER (0..7)
     MAX-ACCESS     read-write
     STATUS         current
     DESCRIPTION
             "This object specifies the ingress fixed cos attributes for given virtual switch."
     DEFVAL { 2 }
     ::= { wwpLeosVplsVirtualSwitchEthEntry 5 }

 wwpLeosVplsVirtualSwitchEthDecapCosPolicy    OBJECT-TYPE
     SYNTAX         INTEGER {
                        fixed(1),
                        inheritVc(2),
                        inheritTunnel(3),
                        leave(4)                        
                        }
     MAX-ACCESS     read-write
     STATUS         current
     DESCRIPTION
             "This object specifies the egress cos policy for given virtual switch."
     DEFVAL { leave }
     ::= { wwpLeosVplsVirtualSwitchEthEntry 6 }
 
 wwpLeosVplsVirtualSwitchEthDecapFixedDot1dPri    OBJECT-TYPE
     SYNTAX         INTEGER (0..7)
     MAX-ACCESS     read-write
     STATUS         current
     DESCRIPTION
             "This object specifies the egress cos attributes for given virtual switch."
     DEFVAL { 2 }
     ::= { wwpLeosVplsVirtualSwitchEthEntry 7 }
          
 wwpLeosVplsVirtualSwitchEthCtrlProtocolTunnelState    OBJECT-TYPE
     SYNTAX         INTEGER {
                        enabled(1),
                        disabled(2)                      
                        }
     MAX-ACCESS     read-write
     STATUS         current
     DESCRIPTION
             "This object enables or disables control protocol tunneling for a given 
              virtual switch."
     DEFVAL { disabled }
     ::= { wwpLeosVplsVirtualSwitchEthEntry 8 } 
 
 wwpLeosVplsVirtualSwitchEthRowStatus    OBJECT-TYPE
     SYNTAX         RowStatus
     MAX-ACCESS     read-create
     STATUS         current
     DESCRIPTION
             "This object can be set to 'createAndGo' to create entry in the table. 
              This object can be set to 'destory' to delete entry in the table.
              Following objects must be set to valid values to create entry in the table."
     ::= { wwpLeosVplsVirtualSwitchEthEntry 9 } 
 
 wwpLeosVplsVirtualSwitchEthMacLrnState    OBJECT-TYPE
     SYNTAX         INTEGER {
     					enabled (1),
     					disabled (2)
     			    }
     MAX-ACCESS     read-write
     STATUS         current
     DESCRIPTION
             "Setting this object will set the Mac learning state for each ethernet virtual switch." 
     DEFVAL			{ enabled }
     ::= { wwpLeosVplsVirtualSwitchEthEntry 10 }   
     
 wwpLeosVplsVirtualSwitchEthTunnelMethod    OBJECT-TYPE
     SYNTAX         INTEGER {
     					l2pt (1),
     					transparent (2)
     			    }
     MAX-ACCESS     read-write
     STATUS         current
     DESCRIPTION
             "Setting this object will set the tunneling method for each ethernet virtual switch."
     DEFVAL			{ l2pt }
     ::= { wwpLeosVplsVirtualSwitchEthEntry 11 } 
 
 wwpLeosVplsVirtualSwitchEthCtrlProtocolDot1dPri    OBJECT-TYPE
     SYNTAX         INTEGER (0..7)
     MAX-ACCESS     read-write
     STATUS         current
     DESCRIPTION
             "This object specifies the .1d priority to use when encapsulation control frames."
     DEFVAL { 6 }
     ::= { wwpLeosVplsVirtualSwitchEthEntry 12 }    
   
 wwpLeosVplsVirtualSwitchEthSubscriberDot1dPolicy   OBJECT-TYPE
     SYNTAX         INTEGER {
     					leave (1),
     					provider-inherit (2)
     			    }
     MAX-ACCESS     read-write
     STATUS         current
     DESCRIPTION
             "Setting this object will configure the policy used to decide whether or not the
              subscriber frame .1d priorty should be left alone, or remarked to the computed provider priority."
     DEFVAL { leave }
     ::= { wwpLeosVplsVirtualSwitchEthEntry 13 }

 wwpLeosVplsVirtualSwitchEthCtrlProtTransFrameValidate    OBJECT-TYPE
     SYNTAX         INTEGER {
     					enabled (1),
     					disabled (2)
     			    }
     MAX-ACCESS     read-write
     STATUS         current
     DESCRIPTION
             "Setting this object will set the transparent-mode validate for a given eth virtual switch." 
     DEFVAL			{ disabled }
     ::= { wwpLeosVplsVirtualSwitchEthEntry 14 }

 --
 --  virtual switch ethernet membership Table
 -- 
 wwpLeosVplsVirtualSwitchEthMemberTable OBJECT-TYPE
     SYNTAX       SEQUENCE OF WwpLeosVplsVirtualSwitchEthMemberEntry
     MAX-ACCESS   not-accessible
     STATUS       current
     DESCRIPTION
             "This table is used to create virtual switch membership entry."
     ::= { wwpLeosVpls 27 }
                
 wwpLeosVplsVirtualSwitchEthMemberEntry  OBJECT-TYPE
     SYNTAX       WwpLeosVplsVirtualSwitchEthMemberEntry
     MAX-ACCESS   not-accessible
     STATUS       current
     DESCRIPTION
             "This entry corresponds to single entry in wwpLeosVplsVirtualSwitchEthernetMemberTable table."
     INDEX { wwpLeosVplsVirtualSwitchEthIndx, wwpLeosVplsVirtualSwitchEthMemberPortId }
     ::= { wwpLeosVplsVirtualSwitchEthMemberTable 1 }
     
 WwpLeosVplsVirtualSwitchEthMemberEntry ::= SEQUENCE {
     wwpLeosVplsVirtualSwitchEthMemberPortId             INTEGER,
     wwpLeosVplsVirtualSwitchEthMemberVlan               INTEGER,
     wwpLeosVplsVirtualSwitchEthMemberRowStatus          RowStatus
 }    
     
 wwpLeosVplsVirtualSwitchEthMemberPortId    OBJECT-TYPE
     SYNTAX         INTEGER (1..65535)
     MAX-ACCESS     read-only
     STATUS         current
     DESCRIPTION
             "This object specifes the port id associated with 
              wwpLeosVplsVirtualSwitchEthIndx."
     ::= { wwpLeosVplsVirtualSwitchEthMemberEntry 1 }
                                                     
 wwpLeosVplsVirtualSwitchEthMemberVlan    OBJECT-TYPE
     SYNTAX         INTEGER (0..4094)
     MAX-ACCESS     read-create
     STATUS         current
     DESCRIPTION
             "This object specifies the subscriber vlan attached to this
              eth virtual switch index wwpLeosVplsVirtualSwitchEthIndx.
              This object cannot be modified one entry is created.
              This object can only be specified when entry is created in this table."
     ::= { wwpLeosVplsVirtualSwitchEthMemberEntry 2 }
                                                          
  wwpLeosVplsVirtualSwitchEthMemberRowStatus    OBJECT-TYPE
     SYNTAX         RowStatus
     MAX-ACCESS     read-create
     STATUS         current
     DESCRIPTION
             "This object can be set to 'createandgo' to add entry in the table.
              This object can be set to 'destroy' to delete entry in the table.
              Refer to description of table entry to see how to create entries 
              in the table."
     ::= { wwpLeosVplsVirtualSwitchEthMemberEntry 3 }  

 --
 -- VPLS MPLS VS Member stats Table
 -- 
 wwpLeosVplsVirtualSwitchEthMemberStatsTable OBJECT-TYPE
     SYNTAX     SEQUENCE OF WwpLeosVplsVirtualSwitchEthMemberStatsEntry
     MAX-ACCESS not-accessible
     STATUS     current
     DESCRIPTION
            "The (conceptual) table listing the virtual switch member stats
             table."
     ::= { wwpLeosVpls 28 }
     
 wwpLeosVplsVirtualSwitchEthMemberStatsEntry  OBJECT-TYPE
     SYNTAX       WwpLeosVplsVirtualSwitchEthMemberStatsEntry
     MAX-ACCESS   not-accessible
     STATUS       current
     DESCRIPTION
             "The virtual switch member stats table entry index by 
              wwpLeosVplsVirtualSwitchEthIndx and wwpLeosVplsVirtualSwitchEthMemberPortId."
     INDEX { wwpLeosVplsVirtualSwitchEthIndx, wwpLeosVplsVirtualSwitchEthMemberPortId }
     ::= { wwpLeosVplsVirtualSwitchEthMemberStatsTable 1 }
     
 WwpLeosVplsVirtualSwitchEthMemberStatsEntry ::=  SEQUENCE {   
         wwpLeosVplsVirtualSwitchEthMemberRxBytesHi        Counter32,
         wwpLeosVplsVirtualSwitchEthMemberRxBytesLo        Counter32
 }
       
 wwpLeosVplsVirtualSwitchEthMemberRxBytesHi OBJECT-TYPE
     SYNTAX      Counter32
     MAX-ACCESS  read-only
     STATUS      current
     DESCRIPTION
        "This represents the total number of higher 32 bits received for 
         given virtual switch member port."
     ::= { wwpLeosVplsVirtualSwitchEthMemberStatsEntry 1 }
     
 wwpLeosVplsVirtualSwitchEthMemberRxBytesLo OBJECT-TYPE
     SYNTAX      Counter32
     MAX-ACCESS  read-only
     STATUS      current
     DESCRIPTION
        "This represents the total number of lower 32 bits received for 
         given virtual switch member port."
     ::= { wwpLeosVplsVirtualSwitchEthMemberStatsEntry 2 }
 
 --
 -- Eth VS Control protocol table
 --
 wwpLeosVplsSwitchEthCtrlProtocolTable OBJECT-TYPE
     SYNTAX     SEQUENCE OF WwpLeosVplsSwitchEthCtrlProtocolEntry
     MAX-ACCESS not-accessible
     STATUS     current
     DESCRIPTION
            "The (conceptual) table listing the l2 virtual switch control frame 
             protocol status tunnel for a given Vpls."
     ::= { wwpLeosVpls 29 }
     
 wwpLeosVplsSwitchEthCtrlProtocolEntry  OBJECT-TYPE
     SYNTAX       WwpLeosVplsSwitchEthCtrlProtocolEntry
     MAX-ACCESS   not-accessible
     STATUS       current
     DESCRIPTION
             "The layer 2 virtual switch control frame protocol tunnel 
              entry for the Vpls."
     INDEX {wwpLeosVplsVirtualSwitchEthIndx, wwpLeosVplsSwitchEthCtrlProtocolNum}
     ::= { wwpLeosVplsSwitchEthCtrlProtocolTable 1 }
     
 WwpLeosVplsSwitchEthCtrlProtocolEntry ::=  SEQUENCE { 
     wwpLeosVplsSwitchEthCtrlProtocolNum     INTEGER,
     wwpLeosVplsSwitchEthCtrlType            INTEGER       
 }

  wwpLeosVplsSwitchEthCtrlProtocolNum OBJECT-TYPE
     SYNTAX      INTEGER {                     
                     l28021x(1),
                     rstp(2),
                     ciscoCdp(3),
                     ciscoDtp(4),
                     ciscoPagp(5),
                     ciscoPvst(6),
                     ciscoUplinkFast(7),
                     ciscoUdlp(8),
                     ciscoVtp(9),
                     gvrp(10),
                     lacp(11),
                     lacpMarker(12),
                     oam(13),
                     lldp(14),
                     vlanBridge(15)                     
                 }
     MAX-ACCESS  read-only
     STATUS      current
     DESCRIPTION
        "This object represent the list of protocols the device 
         can support."
     ::= { wwpLeosVplsSwitchEthCtrlProtocolEntry 1 }

  wwpLeosVplsSwitchEthCtrlType OBJECT-TYPE
     SYNTAX      INTEGER {
                     discard(1),
                     peer(2),
                     tunnel(3)               
                 }
     MAX-ACCESS  read-create
     STATUS      current
     DESCRIPTION
        "Setting this object to 'discard' will cause wwpLeosVplsSwitchEthCtrlProtocolNum
         frames arriving at the specified UNI to be discarded.  
         Setting this to 'peer' will cause the wwpLeosVplsSwitchEthCtrlProtocolNum frame
         to be processed by the provider network and cause the provider 
         network to behave as a peer.  
         Setting this to 'tunnel' will cause the wwpLeosVplsSwitchEthCtrlProtocolNum frame to be 
         tunneled."
     ::= { wwpLeosVplsSwitchEthCtrlProtocolEntry 2 } 
 
 
 END
