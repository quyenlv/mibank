TIMETRA-VRTR-MIB DEFINITIONS ::= BEGIN

IMPORTS
        MODULE-IDENTITY, OBJECT-TYPE,
        NOTIFICATION-TYPE,
        Unsigned32, IpAddress, TimeTicks,
        Integer32,  Gauge32, Counter32          FROM SNMPv2-SMI

        MODULE-COMPLIANCE, OBJECT-GROUP,
        NOTIFICATION-GROUP                      FROM SNMPv2-CONF

        TEXTUAL-CONVENTION, DisplayString,
        RowStatus, TruthValue, MacAddress,
        TimeStamp, TestAndIncr                  FROM SNMPv2-TC

        InetAddress, InetAddressType,
        InetAddressPrefixLength,
        InetAddressIPv6z,
        InetAddressIPv6                         FROM INET-ADDRESS-MIB

        InterfaceIndex, InterfaceIndexOrZero    FROM IF-MIB

--      ALACTEL CHANG
-- 	ipCidrRouteEntry, inetCidrRouteEntry    FROM IP-FORWARD-MIB
   	ipCidrRouteEntry                        FROM IP-FORWARD-MIB
--                      ^^^^^^^^^^^^^^^^^^^
--      ALACTEL CHANG

--      ALCATEL CHANG
--      ipNetToMediaEntry, ipNetToPhysicalEntry FROM IP-MIB
        ipNetToMediaEntry                       FROM IP-MIB
--                       ^^^^^^^^^^^^^^^^^^^^^
--      ALCATEL CHANG

        TmnxVRtrID, IpAddressPrefixLength,
        TmnxBgpAutonomousSystem,
        TmnxVRtrIDOrZero,
        TmnxAdminState, TmnxOperState,
        TmnxStatus, TmnxPortID, TmnxEncapVal,
        TNamedItem, TNamedItemOrEmpty,
        TItemDescription,
        TItemLongDescription,
        TmnxServId, TmnxCustId,
        TmnxTunnelType, TmnxTunnelID,
        TPolicyStatementNameOrEmpty,
        TmnxVPNRouteDistinguisher,
        TCpmProtPolicyID, TDSCPValue,
        TDSCPValueOrNone, TFCType,
        TmnxDHCP6MsgType, Dot1PPriority         FROM TIMETRA-TC-MIB

        timetraSRMIBModules, tmnxSRObjs,
        tmnxSRNotifyPrefix, tmnxSRConfs         FROM TIMETRA-GLOBAL-MIB

        TNetworkPolicyID                        FROM TIMETRA-QOS-MIB

        TIPFilterID, TFilterID                  FROM TIMETRA-FILTER-MIB

        TmnxSlotNum                             FROM TIMETRA-CHASSIS-MIB

        tmnxPortNotifyPortId, tmnxPortType      FROM TIMETRA-PORT-MIB

        svcDhcpLseStateNewCiAddr,
        svcDhcpLseStateNewChAddr,
        svcDhcpClientLease                      FROM TIMETRA-SERV-MIB
        sapPortId, sapEncapValue                FROM TIMETRA-SAP-MIB
        ;

timetraVRtrMIBModule MODULE-IDENTITY
        LAST-UPDATED    "0801010000Z"
        ORGANIZATION    "Alcatel"
        CONTACT-INFO
            "Alcatel 7x50 Support
             Web: http://www.alcatel.com/comps/pages/carrier_support.jhtml"
        DESCRIPTION
            "This document  is the SNMP MIB  module to manage and provision
             the  Alcatel  7x50 device transport and virtual routers, their
             interfaces, and other related features.

             Copyright 2003-2008 Alcatel-Lucent. All rights reserved.
             Reproduction of  this document is authorized  on the condition
             that the foregoing copyright notice is included.

             This   SNMP  MIB  module  (Specification)  embodies  Alcatel's
             proprietary  intellectual  property. Alcatel retains all title
             and ownership in the Specification, including any revisions.

             Alcatel  grants all interested parties a non-exclusive license
             to use and distribute an unmodified copy of this Specification
             in connection with management of Alcatel products, and without
             fee,  provided this copyright notice and license appear on all
             copies.

             This  Specification  is supplied `as is', and Alcatel makes no
             warranty, either express or implied, as to the use, operation,
             condition, or performance of the Specification."

--
--  Revision History
--
        REVISION        "0801010000Z"
        DESCRIPTION     "Rev 6.0                01 Jan 2008 00:00
                         6.0 release of the TIMETRA-VRTR-MIB."

        REVISION        "0701010000Z"
        DESCRIPTION     "Rev 5.0                01 Jan 2007 00:00
                         5.0 release of the TIMETRA-VRTR-MIB."

        REVISION        "0602280000Z"
        DESCRIPTION     "Rev 4.0                28 Feb 2006 00:00
                         4.0 release of the TIMETRA-VRTR-MIB."

        REVISION        "0508310000Z"
        DESCRIPTION     "Rev 3.0                31 Aug 2005 00:00
                         3.0 release of the TIMETRA-VRTR-MIB."

        REVISION        "0501240000Z"
        DESCRIPTION     "Rev 2.1                24 Jan 2005 00:00
                         2.1 release of the TIMETRA-VRTR-MIB."

        REVISION        "0401150000Z"
        DESCRIPTION     "Rev 2.0                15 Jan 2004 00:00
                         2.0 release of the TIMETRA-VRTR-MIB."

        REVISION        "0308150000Z"
        DESCRIPTION     "Rev 1.2                15 Aug 2003 00:00
                         1.2 release of the TIMETRA-VRTR-MIB."

        REVISION        "0301200000Z"
        DESCRIPTION     "Rev 1.0                20 Jan 2003 00:00
                         1.0 Release of the TIMETRA-VRTR-MIB."

        REVISION        "0008140000Z"
        DESCRIPTION     "Rev 0.1                14 Aug 2000 00:00
                         Initial version of the TIMETRA-VRTR-MIB."

        ::= { timetraSRMIBModules 3 }

tmnxVRtrObjs            OBJECT IDENTIFIER ::= { tmnxSRObjs 3 }
tmnxVRtrConformance     OBJECT IDENTIFIER ::= { tmnxSRConfs 3 }
tmnxVRtrNotifyPrefix    OBJECT IDENTIFIER ::= { tmnxSRNotifyPrefix 3}
  tmnxVRtrNotifications     OBJECT IDENTIFIER ::= { tmnxVRtrNotifyPrefix 0 }

--%%%%%%%%%%%%%%%%%%%%%%%%%%%%%%%%%%%%%%%%%%%%%%%%%%%%%%%%%%%%%%%%%%%%%
--
--      TIMETRA-VRTR-MIB textual conventions
--

TmnxVPNId ::= TEXTUAL-CONVENTION
    STATUS      current
    DESCRIPTION
        "The purpose of a VPN-ID is to identify a VPN.
         The global VPN Identifier format is:
            3-octet VPN Authority, organizationally unique ID followed by a
            4-octet VPN index identifying the VPN according to OUI."
    REFERENCE
        "RFC 2685, Fox & Gleeson, 'Virtual Private Networks Identifier',
         September 1999."
    SYNTAX      OCTET STRING (SIZE (0..7))

TmnxInetAddrState ::= TEXTUAL-CONVENTION
    STATUS      current
    DESCRIPTION
        "The TmnxInetAddrState is the state of an ipv6 address."
    SYNTAX      INTEGER {
                    unknown      (0),
                    tentative    (1),
                    duplicated   (2),
                    inaccessible (3),
                    deprecated   (4),
                    preferred    (5)
                }

TDSCPAppId ::=  TEXTUAL-CONVENTION
    STATUS       current
    DESCRIPTION
        "DSCP Application identifiers for protocols that generate control traffic
         on the the Alcatel 7x50 SR router."
    SYNTAX      INTEGER {
                    bgp                (1),
                    cflowd             (2),
                    dhcp               (3),
                    dns                (4),
                    ftp                (5),
                    icmp               (6),
                    igmp               (7),
                    ldp                (8),
                    mld                (9),
                    msdp              (10),
                    ndis              (11),
                    ntp               (12),
                    ospf              (13),
                    pim               (14),
                    radius            (15),
                    rip               (16),
                    rsvp              (17),
                    snmp              (18),
                    snmp-notification (19),
                    srrp              (20),
                    ssh               (21),
                    syslog            (22),
                    tacplus           (23),
                    telnet            (24),
                    tftp              (25),
                    traceroute        (26),
                    vrrp              (27)
                 }

TDot1pAppId ::=  TEXTUAL-CONVENTION
    STATUS       current
    DESCRIPTION
        "IEEE 802.1p priority (Dot1p) Application identifiers for Layer-2
         protocols that generate control traffic on the the Alcatel
         7x50 SR router."
    SYNTAX      INTEGER {
                    arp               (1),
                    isis              (2),
                    pppoe             (3)
                 }

--%%%%%%%%%%%%%%%%%%%%%%%%%%%%%%%%%%%%%%%%%%%%%%%%%%%%%%%%%%%%%%%%%%%%%
--
--      The ALcatel 7x50 SR series Virtual Router Group
--

--
--      Virtual Router Table
--

tmnxVRtrGlobalObjs      OBJECT IDENTIFIER ::= { tmnxVRtrObjs 15 }

vRtrNextVRtrID  OBJECT-TYPE
    SYNTAX      TestAndIncr
    MAX-ACCESS  read-create
    STATUS      current
    DESCRIPTION
        "The vRtrNextVRtrID object is used to assign values to vRtrID
         to be used to create a new row in the vRtrConfTable as described
         in 'Textual Conventions for SNMPv2'.  The network manager reads
         the object, and then writes the value back in the SET request
         that creates a new instance of vRtrConfEntry.  If the SET fails
         with the code 'inconsistentValue', then the process must be
         repeated.  If the the SET succeeds, then the object is
         incremented and the new instance is created according to the
         manager's directions."
    ::= { tmnxVRtrGlobalObjs 1 }

vRtrConfiguredVRtrs  OBJECT-TYPE
    SYNTAX      Gauge32
    MAX-ACCESS  read-only
    STATUS      current
    DESCRIPTION
        "The value of vRtrConfiguredVRtrs indicates the current number of
         virtual routers configured in the system and represented as rows
         in the vRtrConfTable."
    ::= { tmnxVRtrGlobalObjs 2 }

vRtrActiveVRtrs  OBJECT-TYPE
    SYNTAX      Gauge32
    MAX-ACCESS  read-only
    STATUS      current
    DESCRIPTION
        "The value of vRtrActiveVRtrs indicates the current number of virtual
         routers in the system with vRtrAdminStatus equal 'inService'."
    ::= { tmnxVRtrGlobalObjs 3 }

vRtrRouteThresholdSoakTime  OBJECT-TYPE
    SYNTAX      Unsigned32
    UNITS       "seconds"
    MAX-ACCESS  read-write
    STATUS      current
    DESCRIPTION
        "Following the generation of a tmnxVRtrHighRouteTCA notification, the
         value of vRtrRouteThresholdSoakTime indicates the soak interval in
         seconds before another tmnxVRtrHighRouteTCA notification will be
         re-issued.  Imposing this soak period prevents continuous generation of
         notifications by the agent in the event that routes are continually
         added to a VRF after it has reached its maximum capacity.  When this
         object has a value of 0, it indicates that the agent should issue a
         single notification at the time that the value of
         vRtrHighRouteThreshold is exceeded and another notification should not
         be sent until the number of routes has fallen below the value
         configured in vRtrMidRouteThreshold."
    DEFVAL { 600 }      -- 10 minutes
    ::= { tmnxVRtrGlobalObjs 4 }

vRtrMaxARPEntries  OBJECT-TYPE
    SYNTAX      Unsigned32
    MAX-ACCESS  read-only
    STATUS      current
    DESCRIPTION
        "vRtrMaxARPEntries indicates the maximum number of active
         and inactive ARP entries supported across all virtual routers
         in the system."
    ::= { tmnxVRtrGlobalObjs 5 }

vRtrIPv6RouteThresholdSoakTime  OBJECT-TYPE
    SYNTAX      Unsigned32
    UNITS       "seconds"
    MAX-ACCESS  read-write
    STATUS      current
    DESCRIPTION
        "The value of object vRtrIPv6RouteThresholdSoakTime specifies
         the soak interval in seconds before another
         tmnxVRtrIPv6HighRouteTCA notification will be re-issued,
         after the generation of a tmnxVRtrIPv6HighRouteTCA notification.
         
         Imposing this soak period prevents continuous generation of
         notifications by the agent, in the event that routes are continually
         added to a VRF after it has reached its maximum capacity.
         
         When this object has a value of 0, it indicates that the agent should
         issue a single notification at the time that the value of
         vRtrIPv6HighRouteThreshold is exceeded and another notification should
         not be sent until the number of routes has fallen below the value
         configured in vRtrIPv6MidRouteThreshold."
    DEFVAL { 600 }      -- 10 minutes
    ::= { tmnxVRtrGlobalObjs 6 }

vRtrConfTable  OBJECT-TYPE
    SYNTAX      SEQUENCE OF VRtrConfEntry
    MAX-ACCESS  not-accessible
    STATUS      current
    DESCRIPTION
        "The vRtrConfTable has an entry for each virtual router configured
         in the system."
    ::= { tmnxVRtrObjs 1 }

vRtrConfEntry  OBJECT-TYPE
    SYNTAX      VRtrConfEntry
    MAX-ACCESS  not-accessible
    STATUS      current
    DESCRIPTION
        "Each row entry represents a virtual router in the system. Entries can
         be created and deleted via SNMP SET operations.  Creation requires a
         SET request containing vRtrRowStatus, vRtrName and vRtrType.
         Note that rows in this table are usually created by the agent itself
         as a side affect of some other configuration; for example, when a
         service vprn is created by setting the appropriate objects in the
         TIMETRA-SERV-MIB.

         There will always be at least two row entries in this table, one of
         these entries represents the base or transport router and the other
         represents the management router.  These entries are created when the
         system is initialized and can never be deleted."
    INDEX { vRtrID }
    ::= { vRtrConfTable 1 }

VRtrConfEntry ::=
    SEQUENCE {
        vRtrID                          TmnxVRtrID,
        vRtrRowStatus                   RowStatus,
        vRtrAdminState                  TmnxAdminState,
        vRtrName                        TNamedItemOrEmpty,
        vRtrMaxNumRoutes                Integer32,
        vRtrBgpStatus                   TmnxStatus,
        vRtrMplsStatus                  TmnxStatus,
        vRtrOspfStatus                  TmnxStatus,
        vRtrRipStatus                   TmnxStatus,
        vRtrRsvpStatus                  TmnxStatus,
        vRtrEcmpMaxRoutes               Unsigned32,
        vRtrAS                          TmnxBgpAutonomousSystem,
        vRtrNewIfIndex                  TestAndIncr,
        vRtrLdpStatus                   TmnxStatus,
        vRtrIsIsStatus                  TmnxStatus,
        vRtrRouterId                    IpAddress,
        vRtrTriggeredPolicy             TruthValue,
        vRtrConfederationAS             TmnxBgpAutonomousSystem,
        vRtrRouteDistinguisher          TmnxVPNRouteDistinguisher,
        vRtrMidRouteThreshold           Unsigned32,
        vRtrHighRouteThreshold          Unsigned32,
        vRtrIllegalLabelThreshold       Unsigned32,
        vRtrVpnId                       TmnxVPNId,
        vRtrDescription                 TItemDescription,
        vRtrGracefulRestart             TruthValue,
        vRtrGracefulRestartType         INTEGER,
        vRtrType                        INTEGER,
        vRtrServiceId                   TmnxServId,
        vRtrCustId                      TmnxCustId,
        vRtrIgmpStatus                  TmnxStatus,
        vRtrMaxNumRoutesLogOnly         TruthValue,
        vRtrVrfTarget                   TNamedItemOrEmpty,
        vRtrVrfExportTarget             TNamedItemOrEmpty,
        vRtrVrfImportTarget             TNamedItemOrEmpty,
        vRtrPimStatus                   TmnxStatus,
        vRtrMaxMcastNumRoutes           Integer32,
        vRtrMaxMcastNumRoutesLogOnly    TruthValue,
        vRtrMcastMidRouteThreshold      Unsigned32,
        vRtrIgnoreIcmpRedirect          TruthValue,
        vRtrOspfv3Status                TmnxStatus,
        vRtrMsdpStatus                  TmnxStatus,
        vRtrVprnType                    INTEGER,
        vRtrSecondaryVrfId              TmnxVRtrIDOrZero,
        vRtrMldStatus                   TmnxStatus,
        vRtrIPv6MaxNumRoutes            Integer32,
        vRtrIPv6MidRouteThreshold       Unsigned32,
        vRtrIPv6HighRouteThreshold      Unsigned32,
        vRtrIPv6MaxNumRoutesLogOnly     TruthValue,
        vRtrIPv6IgnoreIcmpRedirect      TruthValue,
        vRtrMcPathMgmtPlcyName          TNamedItem
    }

vRtrID  OBJECT-TYPE
    SYNTAX      TmnxVRtrID
    MAX-ACCESS  accessible-for-notify
    STATUS      current
    DESCRIPTION
        "The  unique value which identifies this virtual router in the Tmnx
         system.  The  vRtrID  value  for  each  virtual router must remain
         constant  at least   from  one  re-initialization  of  the  system
         management  processor  (CPM)  to the next. There will always be at
         least  one  router  entry defined by the agent with vRtrID=1 which
         represents the transport router."
    ::= { vRtrConfEntry 1 }

vRtrRowStatus  OBJECT-TYPE
    SYNTAX      RowStatus
    MAX-ACCESS  read-create
    STATUS      current
    DESCRIPTION
        "The row status. The creation or deletion of a virtual router entry
         causes creation or deletion of corresponding entries in other Tmnx
         MIB tables with the same vRtrID value. Note that it is not allowed
         to 'destroy' the row entry for vRtrID = 1.

         In  order  for  row  creation  to succeed, values for vRtrName and
         vRtrType   must   be   included  in  the  same  SNMP  SET  PDU  as
         vRtrRowStatus."
    ::= { vRtrConfEntry 2 }

vRtrAdminState  OBJECT-TYPE
    SYNTAX      TmnxAdminState
    MAX-ACCESS  read-create
    STATUS      current
    DESCRIPTION
        "The desired administrative state for this virtual router.
         Note that it is not allowed to set vRtrAdminState to 'outOfService
         for the row entry with vRtrID = 1."
    DEFVAL { outOfService }
    ::= { vRtrConfEntry 3 }

vRtrName  OBJECT-TYPE
    SYNTAX      TNamedItemOrEmpty
    MAX-ACCESS  read-create
    STATUS      current
    DESCRIPTION
        "The administritive name for this virtual router. The router
         name must be unique among all virtual routers in the system.
         When a row is created in the vRtrConfTable for a service vprn,
         the agent assigns the name 'VR-<service-id>'.  Note that for
         row creation to succeed, a value must be specified for vRtrName."
    ::= { vRtrConfEntry 4 }

vRtrMaxNumRoutes OBJECT-TYPE
    SYNTAX      Integer32 (-1..'7FFFFFFF'h)
    MAX-ACCESS  read-create
    STATUS      current
    DESCRIPTION
        "The maximum number of routes that can be configured on
         this virtual router.  If the value is -1, then there
         is no limit."
    DEFVAL { -1 }
    ::= { vRtrConfEntry 5 }

vRtrBgpStatus  OBJECT-TYPE
    SYNTAX      TmnxStatus
    MAX-ACCESS  read-create
    STATUS      current
    DESCRIPTION
        "The desired state for BGP on this virtual router.  An attempt
         to set vRtrBgpStatus to 'delete' will fail if the BGP protocol
         is not in the administrative outOfService state."
    DEFVAL { delete }
    ::= { vRtrConfEntry 6 }

vRtrMplsStatus  OBJECT-TYPE
    SYNTAX      TmnxStatus
    MAX-ACCESS  read-create
    STATUS      current
    DESCRIPTION
        "The desired state for MPLS on this virtual router.  An attempt
         to set vRtrMplsStatus to 'delete' will fail if the MPLS
         protocol is not in the administrative outOfService state,
         i.e. TIMETRA-MPLS-MIB::vRtrMplsGeneralAdminState must be 
         set to 'outOfService'."
    DEFVAL { delete }
    ::= { vRtrConfEntry 7 }

vRtrOspfStatus  OBJECT-TYPE
    SYNTAX      TmnxStatus
    MAX-ACCESS  read-create
    STATUS      obsolete
    DESCRIPTION
        "The desired state for OSPFv2 on this virtual router.  An attempt
         to set vRtrOspfStatus to 'delete' will fail if the OSPFv2
         protocol is not in the administrative outOfService state,
         i.e. TIMETRA-OSPF-NG-MIB::tmnxOspfAdminState must be set 
         to 'disabled'.

         This object was obsoleted in release 5.0."
    DEFVAL { delete }
    ::= { vRtrConfEntry 8 }

vRtrRipStatus  OBJECT-TYPE
    SYNTAX      TmnxStatus
    MAX-ACCESS  read-create
    STATUS      current
    DESCRIPTION
        "The desired state for RIP on this virtual router.  An attempt
         to set vRtrRipStatus to 'delete' will fail if the RIP
         protocol is not in the admininistrative outOfService state."
    DEFVAL { delete }
    ::= { vRtrConfEntry 9 }

vRtrRsvpStatus  OBJECT-TYPE
    SYNTAX      TmnxStatus
    MAX-ACCESS  read-create
    STATUS      current
    DESCRIPTION
        "The desired state for RSVP on this virtual router.  An attempt
         to set vRtrRsvpStatus to 'delete' will fail if the RSVP
         protocol is not in the administrative outOfService state,
         i.e. TIMETRA-RSVP-MIB::vRtrRsvpGeneralAdminState must be set 
         to 'outOfService'."
    DEFVAL { delete }
    ::= { vRtrConfEntry 10 }

vRtrEcmpMaxRoutes  OBJECT-TYPE
    SYNTAX      Unsigned32 (0..16)
    MAX-ACCESS  read-create
    STATUS      current
    DESCRIPTION
        "The value of vRtrEcmpMaxRoutes specifies the maximum number
         of equal cost routes allowed on this routing table instance.
         When the number ecmp routes available at the best preference
         value exceed the number of vRtrEcmpMaxRoutes allowed, then
         the lowest next-hop IP address algorithm is used to select
         the ecmp routes used.

         When vRtrEcmpMaxRoutes is set to zero (0), and multiple routes
         are available with the same best preference value and equal
         cost values, then the route with the lowest next-hop IP address
         is used."
    DEFVAL { 1 }
    ::= { vRtrConfEntry 11 }

vRtrAS  OBJECT-TYPE
    SYNTAX      TmnxBgpAutonomousSystem
    MAX-ACCESS  read-create
    STATUS      current
    DESCRIPTION
        "The value of vRtrAS specifies the autonomous system number to be
         advertised to this peer.  This object is MUST be set before BGP
         can be activated."
    REFERENCE ""
    DEFVAL { 0 }
    ::= { vRtrConfEntry 12 }

vRtrNewIfIndex  OBJECT-TYPE
    SYNTAX      TestAndIncr
    MAX-ACCESS  read-create
    STATUS      current
    DESCRIPTION
        "This object is used to assign values to vRtrIfIndex as
         described in 'Textual Conventions for SNMPv2'.  The network
         manager reads the object, and then writes the value back
         in the SET request that creates a new instance of vRtrIfEntry.
         If the SET fails with the code 'inconsistentValue', then
         the process must be repeated.  If the the SET succeeds, then
         the object is incremented and the new instance is created
         according to the manager's directions."
    ::= { vRtrConfEntry 13 }

vRtrLdpStatus  OBJECT-TYPE
    SYNTAX      TmnxStatus
    MAX-ACCESS  read-create
    STATUS      current
    DESCRIPTION
        "The desired state for LDP on this virtual router.  An attempt
         to set vRtrLdpStatus to 'delete' will fail if the LDP
         protocol is not in the administrative outOfService state,
         i.e. TIMETRA-LDP-MIB::vRtrLdpGenAdminState must be set 
         to 'outOfService'."
    DEFVAL { delete }
    ::= { vRtrConfEntry 14 }

vRtrIsIsStatus  OBJECT-TYPE
    SYNTAX      TmnxStatus
    MAX-ACCESS  read-create
    STATUS      current
    DESCRIPTION
        "The desired state for ISIS on this virtual router.  An attempt
         to set vRtrIsIsStatus to 'delete' will fail if the ISIS
         protocol is not in the administrative outOfService state."
    DEFVAL { delete }
    ::= { vRtrConfEntry 15 }

vRtrRouterId  OBJECT-TYPE
    SYNTAX      IpAddress
    MAX-ACCESS  read-create
    STATUS      current
    DESCRIPTION
        "A 32-bit integer uniquely identifying the router in the
         Autonomous System.  By convention, to ensure uniqueness, this
         should default to the value of one of the router's IP interface
         addresses."
    ::= { vRtrConfEntry 16 }

vRtrTriggeredPolicy  OBJECT-TYPE
    SYNTAX      TruthValue
    MAX-ACCESS  read-create
    STATUS      current
    DESCRIPTION
        "If the value of vRtrTriggeredPolicy is 'false', all routing
         protocols automatically reevaluate their routes when the route
         policies are changed. If this value is 'true', then the user
         must trigger the recalculation of routes when the route policies
         are changed."
    DEFVAL { false }
    ::= { vRtrConfEntry 17 }

vRtrConfederationAS  OBJECT-TYPE
    SYNTAX      TmnxBgpAutonomousSystem
    MAX-ACCESS  read-create
    STATUS      current
    DESCRIPTION
        "The value of vRtrConfederationAS specifies the confederation AS
         number for the virtual router. A value of 0 means no confederation
         AS."
    DEFVAL { 0 }
    ::= { vRtrConfEntry 18 }

vRtrRouteDistinguisher  OBJECT-TYPE
    SYNTAX      TmnxVPNRouteDistinguisher
    MAX-ACCESS  read-create
    STATUS      current
    DESCRIPTION
        "The value of vRtrRouteDistinguisher is an identifier attached to
         routes that distinguishes to which VPN it belongs.  The VPRN
         cannot be operationally 'inService' until a route distinguisher
         has been assigned."
    DEFVAL { '0000000000000000'H }
    ::= { vRtrConfEntry 19 }

vRtrMidRouteThreshold  OBJECT-TYPE
    SYNTAX      Unsigned32 (0..100)
    UNITS       "percent"
    MAX-ACCESS  read-create
    STATUS      current
    DESCRIPTION
        "The value of vRtrMidRouteThreshold specifies the mid-level
         water marker for the number of routes which this VRF may hold.
         When this limit is exceeded a tmnxVRtrMidRouteTCA
         notification is generated.

         A value of 0 (zero) for this object indicates that the threshold
         is infinite, and the notification will never be sent."
    DEFVAL { 0 }
    ::= { vRtrConfEntry 20 }

vRtrHighRouteThreshold  OBJECT-TYPE
    SYNTAX      Unsigned32 (0..100)
    UNITS       "percent"
    MAX-ACCESS  read-only
    STATUS      current
    DESCRIPTION
        "The value of vRtrHighRouteThreshold specifies the high-level
         water marker for the number of routes which this VRF may hold.
         When this limit is exceeded a tmnxVRtrHighRouteTCA
         notification is generated.

         A value of 0 (zero) for this object indicates that the threshold
         is infinite, and the notification will never be sent."
    ::= { vRtrConfEntry 21 }

vRtrIllegalLabelThreshold  OBJECT-TYPE
    SYNTAX      Unsigned32
    MAX-ACCESS  read-create
    STATUS      current
    DESCRIPTION
        "The value of vRtrIllegalLabelThreshold specifies the
         allowed limit for illegal label violations on this VRF.
         When this limit is exceeded a tmnxVRtrIllegalLabelTCA
         notification is generated.

         A value of 0 (zero) for this object indicates that the threshold
         is infinite, and the notification will never be sent."
    DEFVAL { 0 }
    ::= { vRtrConfEntry 22 }

vRtrVpnId  OBJECT-TYPE
    SYNTAX      TmnxVPNId
    MAX-ACCESS  read-create
    STATUS      current
    DESCRIPTION
        "The value of vRtrVpnId is the Virtual Private Network Identifier
         of this virtual router."
    DEFVAL { ''H }      -- the empty string
    ::= { vRtrConfEntry 23 }

vRtrDescription  OBJECT-TYPE
    SYNTAX      TItemDescription
    MAX-ACCESS  read-create
    STATUS      current
    DESCRIPTION
        "The value of vRtrDescription is a user provided description
         string for this virtual router.  It can consist of any printable,
         seven-bit ASCII characters up to 80 characters in length."
    DEFVAL { ''H }      -- the empty string
    ::= { vRtrConfEntry 25 }

vRtrGracefulRestart  OBJECT-TYPE
    SYNTAX      TruthValue
    MAX-ACCESS  read-create
    STATUS      current
    DESCRIPTION
        "The value of vRtrGracefulRestart indicates whether or not
         graceful restart capabilities are enabled on this virtual
         router.  In order for any protocol to perform graceful
         restart vRtrGracefulRestart must have a value of 'true'.
         Graceful restart capabilities can then be enabled or disabled
         on an individual protocol basis."
    DEFVAL { false }
    ::= { vRtrConfEntry 26 }

vRtrGracefulRestartType  OBJECT-TYPE
    SYNTAX      INTEGER {
                    never     (0),
                    manual    (1),
                    automatic (2)
                }
    MAX-ACCESS  read-create
    STATUS      current
    DESCRIPTION
        "The value of vRtrGracefulRestartType specifies when to include
         grace restart of routing protocols as a result of a switchover
         from primary CPM in a redundant system.
            'never'     - always switch without graceful restart
            'manual'    - perform graceful restart only on a forced switchover
            'automatic' - perform graceful restart on either a switchover
                          caused by an error or a forced switchover"
    DEFVAL { never }
    ::= { vRtrConfEntry 27 }

vRtrType  OBJECT-TYPE
    SYNTAX      INTEGER {
                    unknown    (0),
                    baseRouter (1),
                    vprn       (2),
                    vr         (3)
                }
    MAX-ACCESS  read-create
    STATUS      current
    DESCRIPTION
        "The value of vRtrType specifies the type of virtual router
         represented by this row entry.  When a row is created in this
         table using 'createAndGo', vRtrType must be specified or the
         row creation will fail.

         Only the value of 'vr (3)' can be set with a SNMP SET request.
         The other values are used for row entries created internally by
         the agent.

         The value of vRtrType cannot be modified if vRtrRowStatus has
         a value of 'active'."
    ::= { vRtrConfEntry 28 }

vRtrServiceId  OBJECT-TYPE
    SYNTAX      TmnxServId
    MAX-ACCESS  read-only
    STATUS      current
    DESCRIPTION
        "When vRtrType has a value of 'vprn', the value of vRtrServiceId
         indicates the service-id of the associated service that created
         this row entry."
    ::= { vRtrConfEntry 29 }

vRtrCustId  OBJECT-TYPE
    SYNTAX      TmnxCustId
    MAX-ACCESS  read-only
    STATUS      current
    DESCRIPTION
        "When vRtrType has a value of 'vprn', the value of vRtrCustId
         indicates the customer-id of the associated service that created
         this row entry."
    ::= { vRtrConfEntry 30 }

vRtrIgmpStatus  OBJECT-TYPE
    SYNTAX      TmnxStatus
    MAX-ACCESS  read-create
    STATUS      current
    DESCRIPTION
        "The desired state for IGMP on this virtual router.  An attempt
         to set vRtrIgmpStatus to 'delete' will fail if the IGMP
         protocol is not in the administrative outOfService state,
         i.e. TIMETRA-IGMP-MIB::vRtrIgmpGenAdminState must be set to
         'outOfService'."
    DEFVAL { delete }
    ::= { vRtrConfEntry 31 }

vRtrMaxNumRoutesLogOnly  OBJECT-TYPE
    SYNTAX      TruthValue
    MAX-ACCESS  read-create
    STATUS      current
    DESCRIPTION
        "The value of vRtrMaxNumRoutesLogOnly specifies the action to
         be taken when the maximum number of routes that can be held
         within a given VRF context is reached.  If the value is 'true'
         the event is logged (a trap is sent) and the learning of
         new routes is not disabled.  If the value is 'false' the event
         is logged and the learning of new routes is disabled."
    DEFVAL { false }
    ::= { vRtrConfEntry 32 }

vRtrVrfTarget  OBJECT-TYPE
    SYNTAX      TNamedItemOrEmpty
    MAX-ACCESS  read-create
    STATUS      current
    DESCRIPTION
        "The value of vRtrVrfTarget specifies the extended community
         name for the default vrf-import or vrf-export policy to use for
         the vRtrID if no entries are configured in the vRtrPolicyTable for
         this vRtrID instance.

         This object can not be set if either vRtrVrfExportTarget or
         vRtrVrfImportTarget has been set."
    ::= { vRtrConfEntry 33 }

vRtrVrfExportTarget  OBJECT-TYPE
    SYNTAX      TNamedItemOrEmpty
    MAX-ACCESS  read-create
    STATUS      current
    DESCRIPTION
        "The value of vRtrVrfExportTarget specifies the extended community
         name for the default vrf-export policy to use for the vRtrID if no
         entries are configured in the vRtrPolicyTable for this vRtrID
         instance.

         This object can not be set if vRtrVrfTarget has been set."
    ::= { vRtrConfEntry 34 }

vRtrVrfImportTarget  OBJECT-TYPE
    SYNTAX      TNamedItemOrEmpty
    MAX-ACCESS  read-create
    STATUS      current
    DESCRIPTION
        "The value of vRtrVrfImportTarget specifies the extended community
         name for the default vrf-import policy to use for the vRtrID if no
         entries are configured in the vRtrPolicyTable for this vRtrID
         instance.

         This object can not be set if vRtrVrfTarget has been set."
    ::= { vRtrConfEntry 35 }

vRtrPimStatus  OBJECT-TYPE
    SYNTAX      TmnxStatus
    MAX-ACCESS  read-create
    STATUS      current
    DESCRIPTION
        "The desired state for PIM on this virtual router. When the object
         is set to 'create', PIM protocol instance is enabled on the
         virtual router. Setting the value to 'delete' disables PIM on the
         virtual router."
    DEFVAL { delete }
    ::= { vRtrConfEntry 36 }

vRtrMaxMcastNumRoutes  OBJECT-TYPE
    SYNTAX      Integer32 (-1..'7FFFFFFF'h)
    MAX-ACCESS  read-create
    STATUS      current
    DESCRIPTION
        "The maximum number of multicast routes that can be configured on
         this virtual router.  If the value is -1, then there
         is no limit."
    DEFVAL { -1 }
    ::= { vRtrConfEntry 37 }

vRtrMaxMcastNumRoutesLogOnly  OBJECT-TYPE
    SYNTAX      TruthValue
    MAX-ACCESS  read-create
    STATUS      current
    DESCRIPTION
        "The value of vRtrMaxMcastNumRoutesLogOnly specifies the action to
         be taken when the maximum number of multicast routes that can be held
         within a given VRF context is reached.  If the value is 'true'
         the event is logged (a trap is sent) and the learning of
         new multicast routes is not disabled.  If the value is 'false' the
         event is logged and the learning of new routes is disabled."
    DEFVAL { false }
    ::= { vRtrConfEntry 38 }

vRtrMcastMidRouteThreshold  OBJECT-TYPE
    SYNTAX      Unsigned32 (0..100)
    UNITS       "percent"
    MAX-ACCESS  read-create
    STATUS      current
    DESCRIPTION
        "The value of vRtrMcastMidRouteThreshold specifies the mid-level
         water marker for the number of multicast routes which this VRF may
         hold. When this limit is exceeded a tmnxVRtrMcastMidRouteTCA
         notification is generated.

         A value of 0 (zero) for this object indicates that the threshold
         is infinite, and the notification will never be sent."
    DEFVAL { 0 }
    ::= { vRtrConfEntry 39 }

vRtrIgnoreIcmpRedirect  OBJECT-TYPE
    SYNTAX      TruthValue
    MAX-ACCESS  read-create
    STATUS      current
    DESCRIPTION
        "If the value of vRtrIgnoreIcmpRedirect is 'true', the virtual
         router will drop all ICMP Redirects received on the management
         interface. If the value of vRtrIgnoreIcmpRedirect is 'false'
         and an ICMP Redirect is received on the management interface,
         a /32 route will be created in the route table.

         If the value of vRtrName is not 'management', an SNMP set
         request to vRtrIgnoreIcmpRedirect will fail with an
         'inconsistentValue' error."
    DEFVAL { true }
    ::= { vRtrConfEntry 40 }

vRtrOspfv3Status  OBJECT-TYPE
    SYNTAX      TmnxStatus
    MAX-ACCESS  read-create
    STATUS      obsolete
    DESCRIPTION
        "The desired state for OSPFv3 on this virtual router.  An attempt
         to set vRtrOspfv3Status to 'delete' will fail if the OSPFv3
         protocol is not in the administrative outOfService state,
         i.e. TIMETRA-OSPF-NG-MIB::tmnxOspfAdminState must be set 
         to 'disabled'.

         This object was obsoleted in release 5.0."
    DEFVAL { delete }
    ::= { vRtrConfEntry 41 }

vRtrMsdpStatus  OBJECT-TYPE
    SYNTAX      TmnxStatus
    MAX-ACCESS  read-create
    STATUS      current
    DESCRIPTION
        "The desired state for Msdp on this virtual router.  An attempt
         to set vRtrMsdpStatus to 'delete' will fail if the Msdp
         protocol is not in the administrative outOfService state,
         i.e. TIMETRA-MSDP-MIB::tmnxMsdpAdminState must be 
         set to 'outOfService'."
    DEFVAL { delete }
    ::= { vRtrConfEntry 42 }

vRtrVprnType    OBJECT-TYPE
    SYNTAX      INTEGER {
                    regular (1),
                    hub (2),
                    spoke (3),
                    subscriberSplitHorizon (4)
                }
    MAX-ACCESS  read-create
    STATUS      current
    DESCRIPTION
        "The value of vRtrVprnType specifies how traffic is routed.

        regular (1)                - All traffic is routed to all
                                     destinations.

        hub (2)                    - Network traffic is routed only to
                                     the access side. Access traffic is
                                     routed to all destinations.

        spoke (3)                  - Networks traffic is routed to all
                                     destinations. Access traffic is
                                     routed only to the network side.

        subscriberSplitHorizon (4) - Subscriber-interface traffic is
                                     routed only to the network side.
                                     All other traffic is routed to
                                     all destinations.

        This object cannot be modified if vRtrType is not 'vprn'."
    DEFVAL      { regular }
    ::= { vRtrConfEntry 43 }

vRtrSecondaryVrfId OBJECT-TYPE
    SYNTAX      TmnxVRtrIDOrZero
    MAX-ACCESS  read-only
    STATUS      current
    DESCRIPTION
        "The unique value of vRtrSecondaryVrfId specifies the secondary vrf-id
         for hub and spoke vprn.

         Non-zero value of vRtrSecondaryVrfId indicates that two
         route-tables exist for hub and spoke vprn system one each for hub and
         spoke. One of which is indexed by vRtrSecondaryVrfId.

         If the value of  vRtrSecondaryVrfId  is zero, it indicates that
         there is only one route-table for hub and spoke vprn system."
    ::= { vRtrConfEntry 44 }

vRtrMldStatus  OBJECT-TYPE
    SYNTAX      TmnxStatus
    MAX-ACCESS  read-create
    STATUS      current
    DESCRIPTION
        "The desired state for Multicast Listener Discovery (MLD) Protocol
         on this virtual router.  An attempt to set vRtrMldStatus to 'delete' 
         will fail if the MLD protocol is not in the administrative 
         outOfService state, i.e. TIMETRA-MLD-MIB::vRtrMldGenAdminState 
         must be set to 'outOfService'."
    DEFVAL { delete }
    ::= { vRtrConfEntry 45 }

vRtrIPv6MaxNumRoutes OBJECT-TYPE
    SYNTAX      Integer32 (-1..'7FFFFFFF'h)
    MAX-ACCESS  read-create
    STATUS      current
    DESCRIPTION
        "The maximum number of IPv6 routes that can be configured on
         this virtual router.  If the value is -1, then there
         is no limit.

         This object is not supported on SR-1, where the value of
         TIMETRA-CHASSIS-MIB::tmnxChassisType is '5'."
    DEFVAL { -1 }
    ::= { vRtrConfEntry 46 }

vRtrIPv6MidRouteThreshold  OBJECT-TYPE
    SYNTAX      Unsigned32 (0..100)
    UNITS       "percent"
    MAX-ACCESS  read-create
    STATUS      current
    DESCRIPTION
        "The value of vRtrIPv6MidRouteThreshold specifies the mid-level
         water marker for the number of IPv6 routes which this VRF may hold.
         When this limit is exceeded a tmnxVRtrIPv6MidRouteTCA
         notification is generated.

         A value of 0 (zero) for this object indicates that the threshold
         is infinite, and the notification will never be sent."
    DEFVAL { 0 }
    ::= { vRtrConfEntry 47 }

vRtrIPv6HighRouteThreshold  OBJECT-TYPE
    SYNTAX      Unsigned32 (0..100)
    UNITS       "percent"
    MAX-ACCESS  read-only
    STATUS      current
    DESCRIPTION
        "The value of vRtrIPv6HighRouteThreshold specifies the high-level
         water marker for the number of IPv6 routes which this VRF may hold.
         When this limit is exceeded a tmnxVRtrIPv6HighRouteTCA
         notification is generated.

         A value of 0 (zero) for this object indicates that the threshold
         is infinite, and the notification will never be sent."
    ::= { vRtrConfEntry 48 }

vRtrIPv6MaxNumRoutesLogOnly  OBJECT-TYPE
    SYNTAX      TruthValue
    MAX-ACCESS  read-create
    STATUS      current
    DESCRIPTION
        "The value of vRtrIPv6MaxNumRoutesLogOnly specifies the action to
         be taken when the maximum number of IPv6 routes that can be held
         within a given VRF context is reached.  If the value is 'true'
         the event is logged (a trap is sent) and the learning of
         new routes is not disabled.  If the value is 'false' the event
         is logged and the learning of new routes is disabled."
    DEFVAL { false }
    ::= { vRtrConfEntry 49 }

vRtrIPv6IgnoreIcmpRedirect  OBJECT-TYPE
    SYNTAX      TruthValue
    MAX-ACCESS  read-create
    STATUS      current
    DESCRIPTION
        "If the value of vRtrIPv6IgnoreIcmpRedirect is 'true', the virtual
         router will drop all IPv6 ICMP Redirects received on the management
         interface. If the value of vRtrIPv6IgnoreIcmpRedirect is 'false'
         and an IPv6 ICMP Redirect is received on the management interface,
         a /128 route will be created in the route table.

         If the value of vRtrName is not 'management', an SNMP set
         request to vRtrIPv6IgnoreIcmpRedirect will fail with an
         'inconsistentValue' error."
    DEFVAL { true }
    ::= { vRtrConfEntry 50 }

vRtrMcPathMgmtPlcyName     OBJECT-TYPE
    SYNTAX      TNamedItem
    MAX-ACCESS  read-create
    STATUS      current
    DESCRIPTION
        "The value of vRtrMcPathMgmtPlcyName specifies the multicast policy 
         name configured on this virtual router."
    DEFVAL { "default" }
    ::= { vRtrConfEntry 51 }

--
--  Alcatel 7x50 SR series Virtual Router Policy Table
--
--  Augmentation of the vRtrTable.
--  Use of AUGMENTS clause implies a one-to-one dependent relationship between
--  the base table, vRtrTable, and the augmenting table, vRtrPolicyTable.
--  This in effect extends the vRtrTable with additional columns.
--  Creation (or deletion) of a row in the vRtrTable results in the same
--  fate for the row in the vRtrPolicyTable.
--

vRtrPolicyTable  OBJECT-TYPE
    SYNTAX      SEQUENCE OF VRtrPolicyEntry
    MAX-ACCESS  not-accessible
    STATUS      current
    DESCRIPTION
        "The vRtrPolicyTable has an entry for each virtual router configured
         in the system."
    ::= { tmnxVRtrObjs 16 }

vRtrPolicyEntry  OBJECT-TYPE
    SYNTAX      VRtrPolicyEntry
    MAX-ACCESS  not-accessible
    STATUS      current
    DESCRIPTION
        "Each row entry represents a collection of statistics for a
         virtual router in the system.
         Entries cannot be created and deleted via SNMP SET operations."
    AUGMENTS { vRtrConfEntry }
    ::= { vRtrPolicyTable 1 }

VRtrPolicyEntry ::=
    SEQUENCE {
        vRtrImportPolicy1           TPolicyStatementNameOrEmpty,
        vRtrImportPolicy2           TPolicyStatementNameOrEmpty,
        vRtrImportPolicy3           TPolicyStatementNameOrEmpty,
        vRtrImportPolicy4           TPolicyStatementNameOrEmpty,
        vRtrImportPolicy5           TPolicyStatementNameOrEmpty,
        vRtrExportPolicy1           TPolicyStatementNameOrEmpty,
        vRtrExportPolicy2           TPolicyStatementNameOrEmpty,
        vRtrExportPolicy3           TPolicyStatementNameOrEmpty,
        vRtrExportPolicy4           TPolicyStatementNameOrEmpty,
        vRtrExportPolicy5           TPolicyStatementNameOrEmpty
    }

vRtrImportPolicy1  OBJECT-TYPE
    SYNTAX      TPolicyStatementNameOrEmpty
    MAX-ACCESS  read-create
    STATUS      current
    DESCRIPTION
        "The value of vRtrImportPolicy1 is the name of the first
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 1 }

vRtrImportPolicy2  OBJECT-TYPE
    SYNTAX      TPolicyStatementNameOrEmpty
    MAX-ACCESS  read-create
    STATUS      current
    DESCRIPTION
        "The value of vRtrImportPolicy2 is the name of the second
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 2 }

vRtrImportPolicy3  OBJECT-TYPE
    SYNTAX      TPolicyStatementNameOrEmpty
    MAX-ACCESS  read-create
    STATUS      current
    DESCRIPTION
        "The value of vRtrImportPolicy3 is the name of the third
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 3 }

vRtrImportPolicy4  OBJECT-TYPE
    SYNTAX      TPolicyStatementNameOrEmpty
    MAX-ACCESS  read-create
    STATUS      current
    DESCRIPTION
        "The value of vRtrImportPolicy4 is the name of the fourth
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 4 }

vRtrImportPolicy5  OBJECT-TYPE
    SYNTAX      TPolicyStatementNameOrEmpty
    MAX-ACCESS  read-create
    STATUS      current
    DESCRIPTION
        "The value of vRtrImportPolicy5 is the name of the fifth
         policy to be used for determining which routes are imported
         into the VRF for this virtual router.  If no import policy
         is defined, no routes are accepted into the VRF.

         If multiple policy names are specified, the policies are evaluated
         in the order they are specified.  The first policy that matches
         is applied.

         The import policy name list, vRtrImportPolicy1 through
         vRtrImportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 5 }

vRtrExportPolicy1  OBJECT-TYPE
    SYNTAX      TPolicyStatementNameOrEmpty
    MAX-ACCESS  read-create
    STATUS      current
    DESCRIPTION
        "The value of vRtrExportPolicy1 is the name of the first
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 6 }

vRtrExportPolicy2  OBJECT-TYPE
    SYNTAX      TPolicyStatementNameOrEmpty
    MAX-ACCESS  read-create
    STATUS      current
    DESCRIPTION
        "The value of vRtrExportPolicy2 is the name of the second
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 7 }

vRtrExportPolicy3  OBJECT-TYPE
    SYNTAX      TPolicyStatementNameOrEmpty
    MAX-ACCESS  read-create
    STATUS      current
    DESCRIPTION
        "The value of vRtrExportPolicy3 is the name of the third
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 8 }

vRtrExportPolicy4  OBJECT-TYPE
    SYNTAX      TPolicyStatementNameOrEmpty
    MAX-ACCESS  read-create
    STATUS      current
    DESCRIPTION
        "The value of vRtrExportPolicy4 is the name of the fourth
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 9 }

vRtrExportPolicy5  OBJECT-TYPE
    SYNTAX      TPolicyStatementNameOrEmpty
    MAX-ACCESS  read-create
    STATUS      current
    DESCRIPTION
        "The value of vRtrExportPolicy4 is the name of the fifth
         policy to be used for determining which routes are exported
         from the VRF for this virtual router.  If no export policy
         is defined, no routes are exported from the VRF.

         If multiple policy names are specified, the policies are evaluated
         in the order they are specified.  The first policy that matches
         is applied.

         The export policy name list, vRtrExportPolicy1 through
         vRtrExportPolicy5, is handled by the SNMP agent as a single
         entity.  When an SNMP SET request is received to modify one or
         more of the policy names, all the policy variables are first
         set to the empty string, ''H, and then the new names are set
         into the specified policy variables within a single SNMP SET PDU."
    DEFVAL { ''H }      -- the empty string
    ::= { vRtrPolicyEntry 10 }


--
--  Alcatel 7x50 SR series Virtual Router Statistics Table
--
--  Augmentation of the vRtrTable.
--  Use of AUGMENTS clause implies a one-to-one dependent relationship between
--  the base table, vRtrTable, and the augmenting table, vRtrStatTable.
--  This in effect extends the vRtrTable with additional columns.
--  Creation (or deletion) of a row in the vRtrTable results in the same
--  fate for the row in the vRtrStatTable.
--

vRtrStatTable OBJECT-TYPE
    SYNTAX  SEQUENCE OF VRtrStatEntry
    MAX-ACCESS  not-accessible
    STATUS      current
    DESCRIPTION
        "The vRtrStatTable has an entry for each virtual router configured
        in the system."
    ::= { tmnxVRtrObjs 2 }

vRtrStatEntry  OBJECT-TYPE
    SYNTAX      VRtrStatEntry
    MAX-ACCESS  not-accessible
    STATUS      current
    DESCRIPTION
        "Each row entry represents a collection of statistics for a
        virtual router in the system.

        Entries cannot be created and deleted via SNMP SET operations."
    AUGMENTS { vRtrConfEntry }
    ::= { vRtrStatTable 1 }

VRtrStatEntry ::=
        SEQUENCE {
                vRtrOperState                 TmnxOperState,
                vRtrDirectRoutes              Gauge32,
                vRtrDirectActiveRoutes        Gauge32,
                vRtrStaticRoutes              Gauge32,
                vRtrStaticActiveRoutes        Gauge32,
                vRtrOSPFRoutes                Gauge32,
                vRtrOSPFActiveRoutes          Gauge32,
                vRtrBGPRoutes                 Gauge32,
                vRtrBGPActiveRoutes           Gauge32,
                vRtrISISRoutes                Gauge32,
                vRtrISISActiveRoutes          Gauge32,
                vRtrRIPRoutes                 Gauge32,
                vRtrRIPActiveRoutes           Gauge32,
                vRtrAggregateRoutes           Gauge32,
                vRtrAggregateActiveRoutes     Gauge32,
                vRtrStatConfiguredIfs         Gauge32,
                vRtrStatActiveIfs             Gauge32,
                vRtrStatIllegalLabels         Counter32,
                vRtrStatCurrNumRoutes         Gauge32,
                vRtrStatBGPVpnRoutes          Gauge32,
                vRtrStatBGPVpnActiveRoutes    Gauge32,
                vRtrStatTotalLdpTunnels       Gauge32,
                vRtrStatTotalSdpTunnels       Gauge32,
                vRtrStatActiveLdpTunnels      Gauge32,
                vRtrStatActiveSdpTunnels      Gauge32,
                vRtrMulticastRoutes           Gauge32,
                vRtrStatActiveARPEntries      Gauge32,
                vRtrStatTotalARPEntries       Gauge32,
                vRtrV6DirectRoutes            Gauge32,
                vRtrV6DirectActiveRoutes      Gauge32,
                vRtrV6StaticRoutes            Gauge32,
                vRtrV6StaticActiveRoutes      Gauge32,
                vRtrV6OSPFRoutes              Gauge32,
                vRtrV6OSPFActiveRoutes        Gauge32,
                vRtrV6BGPRoutes               Gauge32,
                vRtrV6BGPActiveRoutes         Gauge32,
                vRtrV6ISISRoutes              Gauge32,
                vRtrV6ISISActiveRoutes        Gauge32,
                vRtrV6RIPRoutes               Gauge32,
                vRtrV6RIPActiveRoutes         Gauge32,
                vRtrV6AggregateRoutes         Gauge32,
                vRtrV6AggregateActiveRoutes   Gauge32,
                vRtrV6StatConfiguredIfs       Gauge32,
                vRtrV6StatActiveIfs           Gauge32,
                vRtrV6StatIllegalLabels       Counter32,
                vRtrV6StatCurrNumRoutes       Gauge32,
                vRtrV6StatBGPVpnRoutes        Gauge32,
                vRtrV6StatBGPVpnActiveRoutes  Gauge32,
                vRtrV6StatTotalLdpTunnels     Gauge32,
                vRtrV6StatTotalSdpTunnels     Gauge32,
                vRtrV6StatActiveLdpTunnels    Gauge32,
                vRtrV6StatActiveSdpTunnels    Gauge32,
                vRtrV6MulticastRoutes         Gauge32,
                vRtrV6StatActiveNbrEntries    Gauge32,
                vRtrV6StatTotalNbrEntries     Gauge32,
                vRtrSubMgmtRoutes             Gauge32,
                vRtrSubMgmtActiveRoutes       Gauge32,
                vRtrStatTotalRsvpTunnels      Gauge32,
                vRtrStatActiveRsvpTunnels     Gauge32,
                vRtrV6StatTotalRsvpTunnels    Gauge32,                   
                vRtrV6StatActiveRsvpTunnels   Gauge32,
                vRtrHostRoutes                Gauge32,
                vRtrHostActiveRoutes          Gauge32,
                vRtrV6HostRoutes              Gauge32,
                vRtrV6HostActiveRoutes        Gauge32,
                vRtrStatLocalARPEntries       Gauge32,
                vRtrStatStaticARPEntries      Gauge32,
                vRtrStatDynamicARPEntries     Gauge32,
                vRtrStatManagedARPEntries     Gauge32,
                vRtrStatInternalARPEntries    Gauge32,
                vRtrManagedRoutes             Gauge32,
                vRtrManagedActiveRoutes       Gauge32
        }

vRtrOperState   OBJECT-TYPE
    SYNTAX      TmnxOperState
    MAX-ACCESS  read-only
    STATUS      current
    DESCRIPTION
        "vRtrOperState indicates current operational status of this
        virtual router."
    ::= { vRtrStatEntry 1 }

vRtrDirectRoutes  OBJECT-TYPE
    SYNTAX      Gauge32
    MAX-ACCESS  read-only
    STATUS      current
    DESCRIPTION
        "vRtrDirectRoutes indicates the current number of direct routes
        for this instance of the route table."
    ::= { vRtrStatEntry 2 }

vRtrDirectActiveRoutes  OBJECT-TYPE
    SYNTAX      Gauge32
    MAX-ACCESS  read-only
    STATUS      current
    DESCRIPTION
        "vRtrDirectActiveRoutes indicates the current number of active direct
        routes for this instance of the route table."
    ::= { vRtrStatEntry 3 }

vRtrStaticRoutes  OBJECT-TYPE
    SYNTAX      Gauge32
    MAX-ACCESS  read-only
    STATUS      current
    DESCRIPTION
        "vRtrStaticRoutes indicates the current number of static routes for
        this instance of the route table."
    ::= { vRtrStatEntry 4 }

vRtrStaticActiveRoutes  OBJECT-TYPE
    SYNTAX      Gauge32
    MAX-ACCESS  read-only
    STATUS      current
    DESCRIPTION
        "vRtrStaticActiveRoutes indicates the current number of active static
        routes for this instance of the route table."
    ::= { vRtrStatEntry 5 }

vRtrOSPFRoutes  OBJECT-TYPE
    SYNTAX      Gauge32
    MAX-ACCESS  read-only
    STATUS      current
    DESCRIPTION
        "vRtrOSPFRoutes indicates the current number of ospf routes for this
        instance of the route table."
    ::= { vRtrStatEntry 6 }

vRtrOSPFActiveRoutes  OBJECT-TYPE
    SYNTAX      Gauge32
    MAX-ACCESS  read-only
    STATUS      current
    DESCRIPTION
        "vRtrOSPFActiveRoutes indicates the current number of active ospf
        routes for this instance of the route table."
    ::= { vRtrStatEntry 7 }

vRtrBGPRoutes  OBJECT-TYPE
    SYNTAX      Gauge32
    MAX-ACCESS  read-only
    STATUS      current
    DESCRIPTION
        "vRtrBGPRoutes indicates the current number of bgp routes for this
        instance of the route table."
    ::= { vRtrStatEntry 8 }

vRtrBGPActiveRoutes  OBJECT-TYPE
    SYNTAX      Gauge32
    MAX-ACCESS  read-only
    STATUS      current
    DESCRIPTION
        "vRtrBGPActiveRoutes indicates the current number of active bgp
        routes for this instance of the route table."
    ::= { vRtrStatEntry 9 }

vRtrISISRoutes  OBJECT-TYPE
    SYNTAX      Gauge32
    MAX-ACCESS  read-only
    STATUS      current
    DESCRIPTION
        "vRtrISISRoutes indicates the current number of isis routes for this
        instance of the route table."
    ::= { vRtrStatEntry 10 }

vRtrISISActiveRoutes  OBJECT-TYPE
    SYNTAX      Gauge32
    MAX-ACCESS  read-only
    STATUS      current
    DESCRIPTION
        "vRtrISISActiveRoutes indicates the current number of active
        isis routes for this instance of the route table."
    ::= { vRtrStatEntry 11 }

vRtrRIPRoutes  OBJECT-TYPE
    SYNTAX      Gauge32
    MAX-ACCESS  read-only
    STATUS      current
    DESCRIPTION
        "vRtrRIPRoutes indicates the current number of rip routes for this
        instance of the route table."
    ::= { vRtrStatEntry 12 }

vRtrRIPActiveRoutes  OBJECT-TYPE
    SYNTAX      Gauge32
    MAX-ACCESS  read-only
    STATUS      current
    DESCRIPTION
        "vRtrRIPActiveRoutes indicates the current number of active rip
        routes for this instance of the route table."
    ::= { vRtrStatEntry 13 }

vRtrAggregateRoutes  OBJECT-TYPE
    SYNTAX      Gauge32
    MAX-ACCESS  read-only
    STATUS      current
    DESCRIPTION
        "vRtrAggregateRoutes indicates the current number of aggregate
        routes for this instance of the route table."
    ::= { vRtrStatEntry 14 }

vRtrAggregateActiveRoutes  OBJECT-TYPE
    SYNTAX      Gauge32
    MAX-ACCESS  read-only
    STATUS      current
    DESCRIPTION
        "vRtrAggregateActiveRoutes indicates the current number of active
        aggregate routes for this instance of the route table."
    ::= { vRtrStatEntry 15 }

vRtrStatConfiguredIfs  OBJECT-TYPE
    SYNTAX      Gauge32
    MAX-ACCESS  read-only
    STATUS      current
    DESCRIPTION
        "vRtrStatConfiguredIfs indicates the current number of router interfaces
         configured on this virtual router."
    ::= { vRtrStatEntry 16 }

vRtrStatActiveIfs  OBJECT-TYPE
    SYNTAX      Gauge32
    MAX-ACCESS  read-only
    STATUS      current
    DESCRIPTION
        "vRtrStatActiveIfs indicates the current number of router interfaces
         with vRtrIfAdminState equal 'inService' on this virtual router."
    ::= { vRtrStatEntry 17 }

vRtrStatIllegalLabels  OBJECT-TYPE
    SYNTAX      Counter32
    MAX-ACCESS  read-only
    STATUS      current
    DESCRIPTION
        "vRtrStatIllegalLabels indicates the number of illegally received
         labels on this virtual router."
    ::= { vRtrStatEntry 18 }

vRtrStatCurrNumRoutes  OBJECT-TYPE
    SYNTAX      Gauge32
    MAX-ACCESS  read-only
    STATUS      current
    DESCRIPTION
        "vRtrStatCurrNumRoutes indicates the current number of routes
         in the VRF for this virtual router."
    ::= { vRtrStatEntry 19 }

vRtrStatBGPVpnRoutes  OBJECT-TYPE
    SYNTAX      Gauge32
    MAX-ACCESS  read-only
    STATUS      current
    DESCRIPTION
        "vRtrStatBGPVpnRoutes indicates the current number of VPN-IPV4 routes
         learned by MP-BGP for this virtual router."
    ::= { vRtrStatEntry 20 }

vRtrStatBGPVpnActiveRoutes  OBJECT-TYPE
    SYNTAX      Gauge32
    MAX-ACCESS  read-only
    STATUS      current
    DESCRIPTION
        "vRtrStatBGPVpnActiveRoutes indicates the current number of active
         VPN-IPV4 routes learned by MP-BGP for this virtual router."
    ::= { vRtrStatEntry 21 }

vRtrStatTotalLdpTunnels  OBJECT-TYPE
    SYNTAX      Gauge32
    MAX-ACCESS  read-only
    STATUS      current
    DESCRIPTION
        "vRtrStatTotalLdpTunnels indicates the current number of both active
         and inactive LDP tunnels."
    ::= { vRtrStatEntry 22 }

vRtrStatTotalSdpTunnels  OBJECT-TYPE
    SYNTAX      Gauge32
    MAX-ACCESS  read-only
    STATUS      current
    DESCRIPTION
        "vRtrStatTotalSdpTunnels indicates the current number of both active
         and inactive SDP tunnels."
    ::= { vRtrStatEntry 23 }

vRtrStatActiveLdpTunnels  OBJECT-TYPE
    SYNTAX      Gauge32
    MAX-ACCESS  read-only
    STATUS      current
    DESCRIPTION
        "vRtrStatActiveLdpTunnels indicates the current number of rows in
         the vRtrTunnelTable where vRtrTunnelType has a value of 'ldp'."
    ::= { vRtrStatEntry 24 }

vRtrStatActiveSdpTunnels  OBJECT-TYPE
    SYNTAX      Gauge32
    MAX-ACCESS  read-only
    STATUS      current
    DESCRIPTION
        "vRtrStatActiveSdpTunnels indicates the current number of rows in
         the vRtrTunnelTable where vRtrTunnelType has a value of 'sdp'."
    ::= { vRtrStatEntry 25 }

vRtrMulticastRoutes  OBJECT-TYPE
    SYNTAX      Gauge32
    MAX-ACCESS  read-only
    STATUS      current
    DESCRIPTION
        "vRtrMulticastRoutes indicates the current number of rows in
         the vRtrPimGrpSrcTable."
    ::= { vRtrStatEntry 26 }

vRtrStatActiveARPEntries  OBJECT-TYPE
    SYNTAX      Gauge32
    MAX-ACCESS  read-only
    STATUS      current
    DESCRIPTION
        "vRtrStatActiveARPEntries indicates the number of active
         ARP entries for the specified virtual router in the system."
    ::= { vRtrStatEntry 27 }

vRtrStatTotalARPEntries  OBJECT-TYPE
    SYNTAX      Gauge32
    MAX-ACCESS  read-only
    STATUS      current
    DESCRIPTION
        "vRtrStatTotalARPEntries indicates the total number of active
         and inactive ARP entries for the specified virtual router in
         the system."
    ::= { vRtrStatEntry 28 }

vRtrV6DirectRoutes  OBJECT-TYPE
    SYNTAX      Gauge32
    MAX-ACCESS  read-only
    STATUS      current
    DESCRIPTION
        "vRtrV6DirectRoutes indicates the current number of v6 direct
         routes for this instance of the route table."
    ::= { vRtrStatEntry 29 }

vRtrV6DirectActiveRoutes  OBJECT-TYPE
    SYNTAX      Gauge32
    MAX-ACCESS  read-only
    STATUS      current
    DESCRIPTION
        "vRtrV6DirectActiveRoutes indicates the current number of
        v6 active direct routes for this instance of the route table."
    ::= { vRtrStatEntry 30 }

vRtrV6StaticRoutes  OBJECT-TYPE
    SYNTAX      Gauge32
    MAX-ACCESS  read-only
    STATUS      current
    DESCRIPTION
        "vRtrV6StaticRoutes indicates the current number of v6 static
         routes for this instance of the route table."
    ::= { vRtrStatEntry 31 }

vRtrV6StaticActiveRoutes  OBJECT-TYPE
    SYNTAX      Gauge32
    MAX-ACCESS  read-only
    STATUS      current
    DESCRIPTION
        "vRtrV6StaticActiveRoutes indicates the current number of v6
        active static routes for this instance of the route table."
    ::= { vRtrStatEntry 32 }

vRtrV6OSPFRoutes  OBJECT-TYPE
    SYNTAX      Gauge32
    MAX-ACCESS  read-only
    STATUS      current
    DESCRIPTION
        "vRtrV6OSPFRoutes indicates the current number of v6 ospf
        routes for this instance of the route table."
    ::= { vRtrStatEntry 33 }

vRtrV6OSPFActiveRoutes  OBJECT-TYPE
    SYNTAX      Gauge32
    MAX-ACCESS  read-only
    STATUS      current
    DESCRIPTION
        "vRtrV6OSPFActiveRoutes indicates the current number of
        v6 active ospf routes for this instance of the route table."
    ::= { vRtrStatEntry 34 }

vRtrV6BGPRoutes  OBJECT-TYPE
    SYNTAX      Gauge32
    MAX-ACCESS  read-only
    STATUS      current
    DESCRIPTION
        "vRtrV6BGPRoutes indicates the current number of v6 bgp
        routes for this instance of the route table."
    ::= { vRtrStatEntry 35 }

vRtrV6BGPActiveRoutes  OBJECT-TYPE
    SYNTAX      Gauge32
    MAX-ACCESS  read-only
    STATUS      current
    DESCRIPTION
        "vRtrV6BGPActiveRoutes indicates the current number of
        v6 active bgp routes for this instance of the route table."
    ::= { vRtrStatEntry 36 }

vRtrV6ISISRoutes  OBJECT-TYPE
    SYNTAX      Gauge32
    MAX-ACCESS  read-only
    STATUS      current
    DESCRIPTION
        "vRtrV6ISISRoutes indicates the current number of v6
         isis routes for this instance of the route table."
    ::= { vRtrStatEntry 37 }

vRtrV6ISISActiveRoutes  OBJECT-TYPE
    SYNTAX      Gauge32
    MAX-ACCESS  read-only
    STATUS      current
    DESCRIPTION
        "vRtrV6ISISActiveRoutes indicates the current number
        of v6 active isis routes for this instance of the route table."
    ::= { vRtrStatEntry 38 }

vRtrV6RIPRoutes  OBJECT-TYPE
    SYNTAX      Gauge32
    MAX-ACCESS  read-only
    STATUS      current
    DESCRIPTION
        "vRtrV6RIPRoutes indicates the current number of v6 rip routes
        for this instance of the route table."
    ::= { vRtrStatEntry 39 }

vRtrV6RIPActiveRoutes  OBJECT-TYPE
    SYNTAX      Gauge32
    MAX-ACCESS  read-only
    STATUS      current
    DESCRIPTION
        "vRtrV6RIPActiveRoutes indicates the current number of active
        v6 rip routes for this instance of the route table."
    ::= { vRtrStatEntry 40 }

vRtrV6AggregateRoutes  OBJECT-TYPE
    SYNTAX      Gauge32
    MAX-ACCESS  read-only
    STATUS      current
    DESCRIPTION
        "vRtrV6AggregateRoutes indicates the current number of
        v6 aggregate routes for this instance of the route table."
    ::= { vRtrStatEntry 41 }

vRtrV6AggregateActiveRoutes  OBJECT-TYPE
    SYNTAX      Gauge32
    MAX-ACCESS  read-only
    STATUS      current
    DESCRIPTION
        "vRtrV6AggregateActiveRoutes indicates the current number of
        active v6 aggregate routes for this instance of the route table."
    ::= { vRtrStatEntry 42 }

vRtrV6StatConfiguredIfs  OBJECT-TYPE
    SYNTAX      Gauge32
    MAX-ACCESS  read-only
    STATUS      current
    DESCRIPTION
        "vRtrV6StatConfiguredIfs indicates the current number of
         v6 router interfaces configured on this virtual router."
    ::= { vRtrStatEntry 43 }

vRtrV6StatActiveIfs  OBJECT-TYPE
    SYNTAX      Gauge32
    MAX-ACCESS  read-only
    STATUS      current
    DESCRIPTION
        "vRtrV6StatActiveIfs indicates the current number of
         v6 router interfaces with vRtrIfAdminState equal
         'inService' on this virtual router."
    ::= { vRtrStatEntry 44 }

vRtrV6StatIllegalLabels  OBJECT-TYPE
    SYNTAX      Counter32
    MAX-ACCESS  read-only
    STATUS      current
    DESCRIPTION
        "vRtrV6StatIllegalLabels indicates the number of illegally
         received v6 labels on this virtual router."
    ::= { vRtrStatEntry 45 }

vRtrV6StatCurrNumRoutes  OBJECT-TYPE
    SYNTAX      Gauge32
    MAX-ACCESS  read-only
    STATUS      current
    DESCRIPTION
        "vRtrV6StatCurrNumRoutes indicates the current number of v6 routes
         in the VRF for this virtual router."
    ::= { vRtrStatEntry 46 }

vRtrV6StatBGPVpnRoutes  OBJECT-TYPE
    SYNTAX      Gauge32
    MAX-ACCESS  read-only
    STATUS      current
    DESCRIPTION
        "vRtrV6StatBGPVpnRoutes indicates the current number of VPN-IPV6 routes
         learned by MP-BGP for this virtual router."
    ::= { vRtrStatEntry 47 }

vRtrV6StatBGPVpnActiveRoutes  OBJECT-TYPE
    SYNTAX      Gauge32
    MAX-ACCESS  read-only
    STATUS      current
    DESCRIPTION
        "vRtrV6StatBGPVpnActiveRoutes indicates the current number of active
         VPN-IPV6 routes learned by MP-BGP for this virtual router."
    ::= { vRtrStatEntry 48 }

vRtrV6StatTotalLdpTunnels  OBJECT-TYPE
    SYNTAX      Gauge32
    MAX-ACCESS  read-only
    STATUS      current
    DESCRIPTION
        "vRtrV6StatTotalLdpTunnels indicates the current number of both active
         and inactive v6 LDP tunnels."
    ::= { vRtrStatEntry 49 }

vRtrV6StatTotalSdpTunnels  OBJECT-TYPE
    SYNTAX      Gauge32
    MAX-ACCESS  read-only
    STATUS      current
    DESCRIPTION
        "vRtrV6StatTotalSdpTunnels indicates the current number of both active
         and inactive v6 SDP tunnels."
    ::= { vRtrStatEntry 50 }

vRtrV6StatActiveLdpTunnels  OBJECT-TYPE
    SYNTAX      Gauge32
    MAX-ACCESS  read-only
    STATUS      current
    DESCRIPTION
        "vRtrV6StatActiveLdpTunnels indicates the current number of v6 rows in
         the vRtrTunnelTable where vRtrTunnelType has a value of 'ldp'."
    ::= { vRtrStatEntry 51 }

vRtrV6StatActiveSdpTunnels  OBJECT-TYPE
    SYNTAX      Gauge32
    MAX-ACCESS  read-only
    STATUS      current
    DESCRIPTION
        "vRtrV6StatActiveSdpTunnels indicates the current number of v6 rows in
         the vRtrTunnelTable where vRtrTunnelType has a value of 'sdp'."
    ::= { vRtrStatEntry 52 }

vRtrV6MulticastRoutes  OBJECT-TYPE
    SYNTAX      Gauge32
    MAX-ACCESS  read-only
    STATUS      current
    DESCRIPTION
        "vRtrV6MulticastRoutes indicates the current number of v6 rows in
         the vRtrPimGrpSrcTable."
    ::= { vRtrStatEntry 53 }

vRtrV6StatActiveNbrEntries  OBJECT-TYPE
    SYNTAX      Gauge32
    MAX-ACCESS  read-only
    STATUS      current
    DESCRIPTION
        "vRtrV6StatActiveNbrEntries indicates the number of active V6 neighbor
         discovery entries for the specified virtual router in the system."
    ::= { vRtrStatEntry 54 }

vRtrV6StatTotalNbrEntries  OBJECT-TYPE
    SYNTAX      Gauge32
    MAX-ACCESS  read-only
    STATUS      current
    DESCRIPTION
        "vRtrV6StatTotalNbrEntries indicates the total number of active
         and inactive v6 neighbor discovery entries for the specified
          virtual router in the system."
    ::= { vRtrStatEntry 55 }

vRtrSubMgmtRoutes        OBJECT-TYPE
    SYNTAX      Gauge32
    MAX-ACCESS  read-only
    STATUS      current
    DESCRIPTION
        "The value of vRtrSubMgmtRoutes  indicates the total number of
         subscriber management routes in the route Table."
    ::= { vRtrStatEntry 56 }

vRtrSubMgmtActiveRoutes        OBJECT-TYPE
    SYNTAX      Gauge32
    MAX-ACCESS  read-only
    STATUS      current
    DESCRIPTION
        "The value of vRtrSubMgmtActiveRoutes indicates the number of
         active subscriber management routes."
    ::= { vRtrStatEntry 57 }

vRtrStatTotalRsvpTunnels  OBJECT-TYPE
    SYNTAX      Gauge32
    MAX-ACCESS  read-only
    STATUS      current
    DESCRIPTION
        "The value of vRtrStatTotalRsvpTunnels indicates the current 
         number of both active and inactive RSVP tunnels."
    ::= { vRtrStatEntry 58 }

vRtrStatActiveRsvpTunnels  OBJECT-TYPE
    SYNTAX      Gauge32
    MAX-ACCESS  read-only
    STATUS      current
    DESCRIPTION
        "The value of vRtrStatActiveRsvpTunnels indicates the current 
         number of rows in the vRtrTunnelTable where vRtrTunnelType has a 
         value of 'rsvp'."
    ::= { vRtrStatEntry 59 }

vRtrV6StatTotalRsvpTunnels  OBJECT-TYPE
    SYNTAX      Gauge32
    MAX-ACCESS  read-only
    STATUS      current
    DESCRIPTION
        "The value of vRtrV6StatTotalRsvpTunnels indicates the current 
         number of both active and inactive IPv6 RSVP tunnels."
    ::= { vRtrStatEntry 60 }

vRtrV6StatActiveRsvpTunnels  OBJECT-TYPE
    SYNTAX      Gauge32
    MAX-ACCESS  read-only
    STATUS      current
    DESCRIPTION
        "The value of vRtrV6StatActiveRsvpTunnels indicates the current 
         number of IPv6 rows in the vRtrTunnelTable where vRtrTunnelType 
         has a value of 'rsvp'."
    ::= { vRtrStatEntry 61 }  

vRtrHostRoutes  OBJECT-TYPE
    SYNTAX      Gauge32
    MAX-ACCESS  read-only
    STATUS      current
    DESCRIPTION
        "The value of vRtrHostRoutes indicates the current number of
         direct routes with prefix value 32 for this instance of the 
         route table."
    ::= { vRtrStatEntry 62 }

vRtrHostActiveRoutes  OBJECT-TYPE
    SYNTAX      Gauge32
    MAX-ACCESS  read-only
    STATUS      current
    DESCRIPTION
        "The value of vRtrHostActiveRoutes indicates the current number of 
         active direct routes with prefix value 32 for this instance of the 
         route table."
    ::= { vRtrStatEntry 63 }

vRtrV6HostRoutes  OBJECT-TYPE
    SYNTAX      Gauge32
    MAX-ACCESS  read-only
    STATUS      current
    DESCRIPTION
        "The value of vRtrV6HostRoutes indicates the current number of v6 
         direct routes with prefix value 128 for this instance of the 
         route table."
    ::= { vRtrStatEntry 64 }

vRtrV6HostActiveRoutes  OBJECT-TYPE
    SYNTAX      Gauge32
    MAX-ACCESS  read-only
    STATUS      current
    DESCRIPTION
        "The value of vRtrV6HostActiveRoutes indicates the current number of
         v6 active direct routes with prefix value 128 for this instance 
         of the route table."
    ::= { vRtrStatEntry 65 }

vRtrStatLocalARPEntries  OBJECT-TYPE
    SYNTAX      Gauge32
    MAX-ACCESS  read-only
    STATUS      current
    DESCRIPTION
        "The value of vRtrStatLocalARPEntries indicates the total number of
         active and inactive local ARP entries for the specified virtual
         router in the system."
    ::= { vRtrStatEntry 66 }

vRtrStatStaticARPEntries  OBJECT-TYPE
    SYNTAX      Gauge32
    MAX-ACCESS  read-only
    STATUS      current
    DESCRIPTION
        "The value of vRtrStatStaticARPEntries indicates the total number of
         active and inactive static ARP entries for the specified virtual
         router in the system."
    ::= { vRtrStatEntry 67 }

vRtrStatDynamicARPEntries  OBJECT-TYPE
    SYNTAX      Gauge32
    MAX-ACCESS  read-only
    STATUS      current
    DESCRIPTION
        "The value of vRtrStatDynamicARPEntries indicates the total number of
         active and inactive dynamic ARP entries for the specified virtual
         router in the system."
    ::= { vRtrStatEntry 68 }

vRtrStatManagedARPEntries  OBJECT-TYPE
    SYNTAX      Gauge32
    MAX-ACCESS  read-only
    STATUS      current
    DESCRIPTION
        "The value of vRtrStatManagedARPEntries indicates the total number of
         active and inactive managed ARP entries for the specified virtual
         router in the system."
    ::= { vRtrStatEntry 69 }

vRtrStatInternalARPEntries  OBJECT-TYPE
    SYNTAX      Gauge32
    MAX-ACCESS  read-only
    STATUS      current
    DESCRIPTION
        "The value of vRtrStatInternalARPEntries indicates the total number of
         active and inactive internal ARP entries for the specified virtual
         router in the system."
    ::= { vRtrStatEntry 70 }

vRtrManagedRoutes OBJECT-TYPE
    SYNTAX      Gauge32
    MAX-ACCESS  read-only
    STATUS      current
    DESCRIPTION
        "The value of vRtrManagedRoutes indicates the total number of
         active and inactive managed routes for the specified virtual
         router in the system."
    ::= { vRtrStatEntry 71 }

vRtrManagedActiveRoutes OBJECT-TYPE
    SYNTAX      Gauge32
    MAX-ACCESS  read-only
    STATUS      current
    DESCRIPTION
        "The value of vRtrManagedActiveRoutes indicates the total number of
         active managed routes for the specified virtual
         router in the system."
    ::= { vRtrStatEntry 72 }

--
--  Virtual Router Interfaces Table
--

vRtrIfTotalNumber  OBJECT-TYPE
    SYNTAX      INTEGER (0..65535)
    MAX-ACCESS  read-only
    STATUS      current
    DESCRIPTION
        "The number of router interfaces configured in this system."
    ::= { tmnxVRtrObjs 3 }

vRtrIfTable  OBJECT-TYPE
    SYNTAX      SEQUENCE OF VRtrIfEntry
    MAX-ACCESS  not-accessible
    STATUS      current
    DESCRIPTION
        "The vRtrIfTable has an entry for each router interface configured in
         the system."
    ::= { tmnxVRtrObjs 4 }

vRtrIfEntry  OBJECT-TYPE
    SYNTAX      VRtrIfEntry
    MAX-ACCESS  not-accessible
    STATUS      current
    DESCRIPTION
        "Each row entry represents a virtual router interface in the system.
         Entries can be created and deleted via SNMP SET operations using the
         vRtrIfRowStatus variable."
        INDEX { vRtrID, vRtrIfIndex }
        ::= { vRtrIfTable 1 }

VRtrIfEntry ::=
    SEQUENCE {
        vRtrIfIndex                     InterfaceIndex,
        vRtrIfRowStatus                 RowStatus,
        vRtrIfType                      INTEGER,
        vRtrIfName                      TNamedItem,
        vRtrIfPortID                    TmnxPortID,
        vRtrIfChannelID                 Unsigned32,
        vRtrIfEncapValue                TmnxEncapVal,
        vRtrIfAdminState                TmnxAdminState,
        vRtrIfOperState                 TmnxOperState,
        vRtrIfAlias                     DisplayString,
        vRtrIfPhysicalAddress           MacAddress,
        vRtrIfArpTimeout                Unsigned32,
        vRtrIfIcmpMaskReply             TruthValue,
        vRtrIfIcmpRedirects             TruthValue,
        vRtrIfIcmpNumRedirects          Unsigned32,
        vRtrIfIcmpRedirectsTime         Unsigned32,
        vRtrIfIcmpUnreachables          TruthValue,
        vRtrIfIcmpNumUnreachables       Unsigned32,
        vRtrIfIcmpUnreachablesTime      Unsigned32,
        vRtrIfIcmpTtlExpired            TruthValue,
        vRtrIfIcmpNumTtlExpired         Unsigned32,
        vRtrIfIcmpTtlExpiredTime        Unsigned32,
        vRtrIfNtpBroadcast              TruthValue,
        vRtrIfUnnumbered                IpAddress,
        vRtrIfMtu                       Unsigned32,
        vRtrIfQosPolicyId               TNetworkPolicyID,
        vRtrIfIngressFilterId           TIPFilterID,
        vRtrIfEgressFilterId            TIPFilterID,
        vRtrIfDirectedBroadcast         TruthValue,
        vRtrIfMplsStatus                TmnxStatus,
        vRtrIfUnnumberedIf              DisplayString,
        vRtrIfCflowd                    INTEGER,
        vRtrIfVPNClass                  INTEGER,
        vRtrIfDescription               TItemLongDescription,
        vRtrIfProtocol                  BITS,
        vRtrIfTosMarkingTrusted         TruthValue,
        vRtrIfServiceId                 TmnxServId,
        vRtrIfArpPopulate               INTEGER,
        vRtrIfIPv6ConfigAllowed         TruthValue,
        vRtrIfIPv6OperState             TmnxOperState,
        vRtrIfIPv6IngressFilterId       TIPFilterID,
        vRtrIfIPv6EgressFilterId        TIPFilterID,
        vRtrIfIcmpV6Redirects           TruthValue,
        vRtrIfIcmpV6NumRedirects        Unsigned32,
        vRtrIfIcmpV6RedirectsTime       Unsigned32,
        vRtrIfIcmpV6Unreachables        TruthValue,
        vRtrIfIcmpV6NumUnreachables     Unsigned32,
        vRtrIfIcmpV6UnreachablesTime    Unsigned32,
        vRtrIfIcmpV6TimeExceeded        TruthValue,
        vRtrIfIcmpV6NumTimeExceeded     Unsigned32,
        vRtrIfIcmpV6TimeExceededTime    Unsigned32,
        vRtrIfIcmpV6PktTooBig           TruthValue,
        vRtrIfIcmpV6NumPktTooBig        Unsigned32,
        vRtrIfIcmpV6PktTooBigTime       Unsigned32,
        vRtrIfIcmpV6ParamProblem        TruthValue,
        vRtrIfIcmpV6NumParamProblem     Unsigned32,
        vRtrIfIcmpV6ParamProblemTime    Unsigned32,
        vRtrIfLinkLocalAddressType      InetAddressType,
        vRtrIfLinkLocalAddress          InetAddress,
        vRtrIfLinkLocalAddressState     TmnxInetAddrState,
        vRtrIfLastOperStateChange       TimeStamp,
        vRtrIfOperMtu                   Unsigned32,
        vRtrIfGlobalIndex               Unsigned32,
        vRtrIfDelaySeconds              Unsigned32,
        vRtrIfDelayUpTimer              Integer32,
        vRtrIfLocalDhcpServerName       TNamedItemOrEmpty,
        vRtrIfInitDelayEnable           TruthValue,
        vRtrIfCpmProtPolicyId           TCpmProtPolicyID,
        vRtrIfCpmProtUncfgdProtoDropCnt Gauge32,
        vRtrIfLdpSyncTimer              Unsigned32
        }

vRtrIfIndex  OBJECT-TYPE
    SYNTAX      InterfaceIndex
    MAX-ACCESS  accessible-for-notify
    STATUS      current
    DESCRIPTION
        "The unique value which identifies this interface of this virtual
         router in the Tmnx system. This field provides an identifier for
         virtual router interfaces similar to the ifIndex values used in the
         mib-2 interfaces table for physical interfaces. The vRtrIfIndex values
         can be reused for different virtual routers, but are unique within
         those entries with the same vRtrID.

         The vRtrIfIndex value for each virtual interface must remain constant
         at least from one re-initialization of the system management processor
         to the next."
    ::= { vRtrIfEntry 1 }

vRtrIfRowStatus  OBJECT-TYPE
    SYNTAX      RowStatus
    MAX-ACCESS  read-create
    STATUS      current
    DESCRIPTION
        "The row status.  The creation or deletion of a router interface entry
         causes creation or deletion of corresponding entries in other Tmnx MIB
         tables with the same vRtrID and vRtrIfIndex values, such as the
         vRtrIpAddrTable.  The router interface is associated to a physical port
         interface through the vRtrIfPortID and vRtrIfEncapValue variables. The
         RowStatus cannot be SET to 'active' unless vRtrIfName has been
         initialized."
    ::= { vRtrIfEntry 2 }

vRtrIfType OBJECT-TYPE
    SYNTAX      INTEGER {
                    network(1),
                    service(2),
                    serviceIes(3),
                    serviceRtdVpls(4), --obsolete
                    serviceVprn(5),
                    serviceIesSubscriber(6),
                    serviceIesGroup(7),
                    serviceVprnSubscriber(8),
                    serviceVprnGroup(9),
                    serviceIesRedundant(10),
                    serviceVprnRedundant(11),
                    serviceVpls(12),
                    serviceIesCem(13), --not supported
                    serviceVprnCem(14), --not supported
                    serviceVprnIPsec(15),
                    serviceVprnIPMirror(16)
                }
    MAX-ACCESS  read-create
    STATUS      current
    DESCRIPTION
        "The value of vRtrIfType specifies the type of this interface. Different
         virtual router interface types are defined as follows:

         network               - defined on a network port.
         service               - used internally.
         serviceIes            - defined on a SAP or Spoke SDP.
         serviceRtdVpls        - obsoleted.
         serviceVprn           - defined on a SAP or Spoke SDP.
         serviceIesSubscriber  - used internally.
         serviceIesGroup       - defined on a SAP
         serviceVprnSubscriber - used internally.
         serviceVprnGroup      - defined on a SAP.
         serviceIesRedundant   - defined on a Spoke SDP.
         serviceVprnRedundant  - defined on a Spoke SDP.
         serviceVpls           - defined on an IP endpoint for VPLS. 
         serviceIesCem         - defined on a SAP. --not supported
         serviceVprnCem        - defined on a SAP. --not supported
         serviceVprnIPsec      - defined on a SAP.
         serviceVprnIPMirror   - defined on a Mirror."
    ::= { vRtrIfEntry 3 }

vRtrIfName  OBJECT-TYPE
    SYNTAX      TNamedItem
    MAX-ACCESS  read-create
    STATUS      current
    DESCRIPTION
        "The administrative name assigned this router interface. The interface
         name must be unique among entries with the same vRtrID value.
         In order for row creation to succeed, a value must also be assigned
         to vRtrIfName."
    ::= { vRtrIfEntry 4 }

vRtrIfPortID  OBJECT-TYPE
    SYNTAX      TmnxPortID
    MAX-ACCESS  read-create
    STATUS      current
    DESCRIPTION
        "The physical port to which this interface is bound. If vRtrIfPortID is
         zero (0), then there is no binding between this virtual router
         interface and a physical port. Once an interface has been bound to a
         port, several steps are required to change the binding to some other
         TmnxPortID value.
         vRtrIfAdminState must be 'outOfService'; vRtrIfPortID must be set to
         zero (0) to disassociate the interface from the original port binding;
         finally, set vRtrIfPortID to the value for the new port binding.

         Setting vRtrIfPortID to 0x20000001 indicates that this interface is the
         system interface for the device."
    DEFVAL { 0 }
    ::= { vRtrIfEntry 5 }

vRtrIfChannelID  OBJECT-TYPE
    SYNTAX      Unsigned32 (0..64)
    MAX-ACCESS  read-create
    STATUS      obsolete
    DESCRIPTION
        "When the physical port, vRtrIfPortID, is a SONET port, vRtrIfChannelID
         is the STSx channel number used by this interface. If vRtrIfPortID is
         not a SONET port or the interface has not yet been bound to a physical
         port, vRtrIfChannelID will be zero (0).

         This object was obsoleted in release 5.0."
    DEFVAL { 0 }
    ::= { vRtrIfEntry 6 }

vRtrIfEncapValue  OBJECT-TYPE
    SYNTAX      TmnxEncapVal
    MAX-ACCESS  read-create
    STATUS      current
    DESCRIPTION
        "The value of the label used along with vRtrIfPortID to identify a SAP
         on the specified access port."
    ::= { vRtrIfEntry 7 }

vRtrIfAdminState  OBJECT-TYPE
    SYNTAX      TmnxAdminState
    MAX-ACCESS  read-create
    STATUS      current
    DESCRIPTION
        "The desired administrative state for this router interface."
    DEFVAL { outOfService }
    ::= { vRtrIfEntry 8 }

vRtrIfOperState  OBJECT-TYPE
    SYNTAX      TmnxOperState
    MAX-ACCESS  read-only
    STATUS      current
    DESCRIPTION
        "The current operational status of this router interface."
    ::= { vRtrIfEntry 9 }

vRtrIfAlias  OBJECT-TYPE
    SYNTAX      DisplayString (SIZE(0..32))
    MAX-ACCESS  read-create
    STATUS      current
    DESCRIPTION
        "An alternative administrative name assigned this router interface."
    ::= { vRtrIfEntry 10 }

vRtrIfPhysicalAddress OBJECT-TYPE
    SYNTAX      MacAddress
    MAX-ACCESS  read-create
    STATUS      current
    DESCRIPTION
        "The interface's address at its protocol sub-layer. For example, for an
         802.x interface, this object normally contains a MAC address. The
         interface's media-specific MIB must define the bit and byte ordering
         and the format of the value of this object. For interfaces which do
         not have such an address (e.g., a serial line), this object should
         contain an octet string of zero length."
    ::= { vRtrIfEntry 11 }

vRtrIfArpTimeout  OBJECT-TYPE
    SYNTAX      Unsigned32 (0..65535)
    UNITS       "seconds"
    MAX-ACCESS  read-create
    STATUS      current
    DESCRIPTION
        "The value of vRtrIfArpTimeout determines how long an ARP entry
         associated with this interface remains in the ARP cache. When
         vRtrIfArpTimeout has a value of zero, '0', the entry will never be
         cleared from the cache."
    DEFVAL { 14400 }
    ::= { vRtrIfEntry 12 }

vRtrIfIcmpMaskReply  OBJECT-TYPE
    SYNTAX      TruthValue
    MAX-ACCESS  read-create
    STATUS      current
    DESCRIPTION
        "When vRtrIfIcmpMaskReply is set to 'true', a reply will be
         issued when this node is requested for the network mask for this
         subnet.  The requesting node must be attached to the local
         network.  When vRtrIfIcmpMaskReply is set to 'false', no reply
         is  issued if an ICMP mask request is received."
    DEFVAL { true }
    ::= { vRtrIfEntry 13 }

vRtrIfIcmpRedirects  OBJECT-TYPE
    SYNTAX      TruthValue
    MAX-ACCESS  read-create
    STATUS      current
    DESCRIPTION
        "When vRtrIfIcmpRedirects is set to 'true', ICMP redirects are
         generated when routes are not optimal on this router and another
         router on the same subnetwork has a better route in order to
         alert that node that a better route is available.  When
         vRtrIfIcmpRedirects is set to 'false', ICMP redirects are not
         generated."
    DEFVAL { true }
    ::= { vRtrIfEntry 14 }

vRtrIfIcmpNumRedirects  OBJECT-TYPE
    SYNTAX      Unsigned32 (10..1000)
    MAX-ACCESS  read-create
    STATUS      current
    DESCRIPTION
        "The value of vRtrIfIcmpNumRedirects limits the number of redirects
         issued per the time frame specified in vRtrIfIcmpRedirectsTime."
    DEFVAL { 100 }
    ::= { vRtrIfEntry 15 }

vRtrIfIcmpRedirectsTime  OBJECT-TYPE
    SYNTAX      Unsigned32 (1..60)
    UNITS       "seconds"
    MAX-ACCESS  read-create
    STATUS      current
    DESCRIPTION
        "The value of vRtrIfIcmpRedirectsTime determines the time frame
         in seconds that is used to limit the number of redirects issued
         per time frame."
    DEFVAL { 10 }
    ::= { vRtrIfEntry 16 }

vRtrIfIcmpUnreachables  OBJECT-TYPE
    SYNTAX      TruthValue
    MAX-ACCESS  read-create
    STATUS      current
    DESCRIPTION
        "When vRtrIfIcmpUnreachables is set to 'true', ICMP host and
         network unreachable messages are generated by this interface.
         When vRtrIfIcmpUnreachables is set to 'false', ICMP host and
         network unreachable messages are not sent."
    DEFVAL { true }
    ::= { vRtrIfEntry 17 }

vRtrIfIcmpNumUnreachables  OBJECT-TYPE
    SYNTAX      Unsigned32 (10..1000)
    MAX-ACCESS  read-create
    STATUS      current
    DESCRIPTION
        "The value of vRtrIfIcmpNumUnreachables determines how many
         destination unreachable messages are issued in the time frame
         specified by vRtrIfIcmpUnreachablesTime."
    DEFVAL { 100 }
    ::= { vRtrIfEntry 18 }

vRtrIfIcmpUnreachablesTime  OBJECT-TYPE
    SYNTAX      Unsigned32 (1..60)
    UNITS       "seconds"
    MAX-ACCESS  read-create
    STATUS      current
    DESCRIPTION
        "The value of vRtrIfIcmpUnreachablesTime sets the time frame in
         seconds that is used to limit the number of destination
         unreachable messages issued per time frame."
    DEFVAL { 10 }
    ::= { vRtrIfEntry 19 }

vRtrIfIcmpTtlExpired  OBJECT-TYPE
    SYNTAX      TruthValue
    MAX-ACCESS  read-create
    STATUS      current
    DESCRIPTION
        "When vRtrIfIcmpTtlExpired is set to 'true', the rate that
         ttl-expired messages by this interface is throttled based on
         the values of vRtrIfIcmpNumTtlExpired and vRtrIfIcmpTtlExpiredTime.
         When vRtrIfIcmpTtlExpired is set to 'false', unlimited ttl-expired
         messages are sent."
    DEFVAL { true }
    ::= { vRtrIfEntry 20 }

vRtrIfIcmpNumTtlExpired  OBJECT-TYPE
    SYNTAX      Unsigned32 (10..1000)
    MAX-ACCESS  read-create
    STATUS      current
    DESCRIPTION
        "The value of vRtrIfIcmpNumTtlExpired defines how many ttl-expired
         messages will be issued in the time frame specified by
         vRtrIfIcmpTtlExpiredTime."
    DEFVAL { 100 }
    ::= { vRtrIfEntry 21 }

vRtrIfIcmpTtlExpiredTime  OBJECT-TYPE
    SYNTAX      Unsigned32 (1..60)
    UNITS       "seconds"
    MAX-ACCESS  read-create
    STATUS      current
    DESCRIPTION
        "The value of vRtrIfIcmpTtlExpiredTime sets the time frame in
         seconds that is used to limit the number of ttl-expired messages
         issued by this interface with the specified time frame."
    DEFVAL { 10 }
    ::= { vRtrIfEntry 22 }

vRtrIfNtpBroadcast OBJECT-TYPE
    SYNTAX      TruthValue
    MAX-ACCESS  read-create
    STATUS      current
    DESCRIPTION
        "When vRtrIfNtpBroadcast is set to 'true', the NTP broadcasts
         will be transmitted on this interface."
    DEFVAL { false }
    ::= { vRtrIfEntry 23 }

vRtrIfUnnumbered  OBJECT-TYPE
    SYNTAX      IpAddress
    MAX-ACCESS  read-create
    STATUS      current
    DESCRIPTION
        "The IP address to be used when generating packets on this interface.
         This variable is complemented by vRtrIfUnnumbered. If
         vRtrIfUnnumberedIf is a null-string and vRtrIfUnnumbered
         is '0.0.0.0' it implies that no unnumbered interface is configured.
         At any instant only one of the two members can be non-null.

         A value of '255.255.255.255' implies the use of system-ip. It is
         strongly suggested to use the node's system IP address as it is not
         associated with a particular physical interface and is therefore always
         reachable."
    DEFVAL { '00000000'H }  -- 0.0.0.0
    ::= { vRtrIfEntry 24 }

vRtrIfMtu  OBJECT-TYPE
    SYNTAX      Unsigned32(0|512..9000)
    UNITS       "bytes"
    MAX-ACCESS  read-create
    STATUS      current
    DESCRIPTION
        "The value of vRtrIfMtu is used to reflect the MTU size of this
         interface in the header of an ICMP MTU exceeded message when
         a packet is too large to be transmitted on this interface.
         The default size is calculated by subtracting the DLC header
         size from the physical MTU size of the interface.

         When a SNMP SET request is received with a value of zero (0), the
         agent actually sets vRtrIfMtu to the calculated default size."
    DEFVAL { 0 }
    ::= { vRtrIfEntry 25 }

vRtrIfQosPolicyId  OBJECT-TYPE
    SYNTAX      TNetworkPolicyID
    MAX-ACCESS  read-create
    STATUS      current
    DESCRIPTION
        "The value of vRtrIfQosPolicyId associates a pre-existing
         network-policy-id to a network interface. Packets are marked
         using qos policies on edge switches; invoking a qos policy on
         a network port allows for the packets that match the policy
         criteria to be remarked.

         If this entry indicates a service virtual router interface or
         the special out-of-band management interface, this object is
         meaningless and is not applied to the interface."
    DEFVAL { 1 }
    ::= { vRtrIfEntry 26 }

vRtrIfIngressFilterId  OBJECT-TYPE
    SYNTAX      TIPFilterID
    MAX-ACCESS  read-create
    STATUS      current
    DESCRIPTION
        "The value of vRtrIfIngressFilterId associates an ip-filter-id
         with an ingress interface. Filters control the forwarding and
         dropping of packets based on IP criteria.  A value of zero (0)
         indicates that there is no ip-filter-id associated with this
         interface.

         If this entry indicates a service virtual router interface or
         the special out-of-band management interface, this object is
         meaningless and is not applied to the interface."
    DEFVAL { 0 }
    ::= { vRtrIfEntry 27 }

vRtrIfEgressFilterId  OBJECT-TYPE
    SYNTAX      TIPFilterID
    MAX-ACCESS  read-create
    STATUS      current
    DESCRIPTION
        "The value of vRtrIfEgressFilterId associates an ip-filter-id
         with an egress interface. Filters control the forwarding and
         dropping of packets based on IP criteria.  A value of zero (0)
         indicates that there is no ip-filter-id associated with this
         interface.

         If this entry indicates a service virtual router interface or
         the special out-of-band management interface, this object is
         meaningless and is not applied to the interface."
    DEFVAL { 0 }
    ::= { vRtrIfEntry 28 }

vRtrIfDirectedBroadcast  OBJECT-TYPE
    SYNTAX      TruthValue
    MAX-ACCESS  read-create
    STATUS      current
    DESCRIPTION
        "When vRtrIfDirectedBroadcast is set to 'true', allows broadcasts
         directed to this interface to be accepted.  When 'false',
         directed broadcasts are dropped.  This is of particular use
         when preventing denial of service attacks."
    DEFVAL { false }
    ::= { vRtrIfEntry 29 }

vRtrIfMplsStatus  OBJECT-TYPE
    SYNTAX      TmnxStatus
    MAX-ACCESS  read-create
    STATUS      current
    DESCRIPTION
        "Setting this variable to 'create' causes this interface to be
         used with MPLS.  It also causes a row to be created in the
         vRtrMplsIfTable.  Setting it to 'delete' removes the interface
         from MPLS and causes the corresponding row in the vRtrMplsIfTable
         to be removed.  However, an attempt to set vRtrIfMplsStatus to
         'delete' will fail if MPLS activity on this interface is not
         administratively in the outOfService state, i.e. vRtrMplsIfAdminState
         of the vRtrMplsIfTable must be set to 'outOfService'."
    DEFVAL { delete }
    ::= { vRtrIfEntry 30 }

vRtrIfUnnumberedIf  OBJECT-TYPE
    SYNTAX      DisplayString (SIZE(0..32))
    MAX-ACCESS  read-create
    STATUS      current
    DESCRIPTION
        "The name of the interface to which this unnumbered interface will
         refer to. This variable is complemented by vRtrIfUnnumbered. If
         vRtrIfUnnumberedIf is a null-string and vRtrIfUnnumbered is '0' it
         implies that no unnumbered interface is configured. At any instant
         only one of the two members can be non-null."
    ::= { vRtrIfEntry 31 }

vRtrIfCflowd  OBJECT-TYPE
    SYNTAX      INTEGER {
                    none      (1),
                    acl       (2),
                    interface (3)
                }
    MAX-ACCESS  read-create
    STATUS      current
    DESCRIPTION
        "The value of vRtrIfCflowd specifies the type of Cflowd analysis
         applied to this interface. A Cflowd profile controls the sampling
         and analysis of data flows through the router.  A value of none (1)
         indicates that there is no Cflowd analysis associated with this
         interface."
    DEFVAL { none }
    ::= { vRtrIfEntry 32 }

vRtrIfVPNClass  OBJECT-TYPE
    SYNTAX      INTEGER {
                    unknown          (0),
                    carrierOfCarrier (1),
                    enterprise       (2),
                    interProvider    (3)
                }
    MAX-ACCESS  read-only
    STATUS      current
    DESCRIPTION
        "The value of vRtrIfVPNClass specifies the type of VPN scenario
         supported on this virtual router interface."
    ::= { vRtrIfEntry 33 }

vRtrIfDescription  OBJECT-TYPE
    SYNTAX      TItemLongDescription
    MAX-ACCESS  read-create
    STATUS      current
    DESCRIPTION
        "The value of vRtrIfDescription is a user provided description
         string for this virtual router interface.  It can consist of
         any printable, seven-bit ASCII characters up to 80 characters in
         length."
    DEFVAL { ''H }      -- the empty string
    ::= { vRtrIfEntry 34 }

vRtrIfProtocol  OBJECT-TYPE
    SYNTAX      BITS {
                    ospfv2  (0),
                    rip     (1),
                    isis    (2),
                    bgp     (3),
                    mpls    (4),
                    rsvp    (5),
                    ldp     (6),
                    igmp    (7),
                    pim     (8),
                    ospf3   (9),
                    mld     (10) 
                }
    MAX-ACCESS  read-only
    STATUS      current
    DESCRIPTION
        "The value of vRtrIfProtocol indicates which protocols are running
         on this virtual router interface. If the bit corresponding to a
         protocol is set, then the protocol is enabled on this interface."
    ::= { vRtrIfEntry 35 }

vRtrIfTosMarkingTrusted  OBJECT-TYPE
    SYNTAX      TruthValue
    MAX-ACCESS  read-create
    STATUS      current
    DESCRIPTION
        "The value of vRtrIfTosMarkingTrusted specifies whether the TOS
         bits on the packets ingressing on the interface should be
         trusted by the system or not. If the value is set to 'true', the
         TOS bits should be trusted.

         If the system does not trust these packets, it will remark the
         packets upon egress as indicated by the value of the egress
         remark flag, TIMETRA-QOS-MIB:: tNetworkPolicyEgressRemark.
         The egress remark flag is part of the QoS policy applied to the
         network interface.

         The interfaces belonging to the IES service have the egress
         remark flag set to not trusted, 'false', by default. For all other
         interface types, the TOS bits are trusted by default."
    DEFVAL { true }
    ::= { vRtrIfEntry 36 }

vRtrIfServiceId  OBJECT-TYPE
     SYNTAX      TmnxServId
     MAX-ACCESS  read-create
     STATUS      current
     DESCRIPTION
         "The value of vRtrIfServiceId specifies the service id for this
          interface. This object must always be set at row creation when
          the vRtrIfType is not network(1). This object cannot be modified
          once the row is created."
     DEFVAL { 0 }
     ::= { vRtrIfEntry 37 }

vRtrIfArpPopulate  OBJECT-TYPE
    SYNTAX      INTEGER {
                    disabled (1),
                    enabled  (2)
                }
    MAX-ACCESS  read-create
    STATUS      current
    DESCRIPTION
        "The value of the object vRtrIfArpPopulate specifies the ARP
         populate action.
         The value disabled means that the normal ARP protocol is active.
         The value enabled means that the system will not originate ARP
         requests on this interface. The ARP cache is only populated with MAC
         addresses learned via the DHCP protocol.
         If the value of vRtrIfType is network, this object can only be set
         to disabled."
    DEFVAL { disabled }
    ::= { vRtrIfEntry 38 }

vRtrIfIPv6ConfigAllowed  OBJECT-TYPE
    SYNTAX      TruthValue
    MAX-ACCESS  read-create
    STATUS      current
    DESCRIPTION
        "The value of vRtrIfIPv6ConfigAllowed specifies whether IPv6 can be
         configured on this router interface. When the value is 'true', IPv6
         can be configured on this interface. When it is 'false', IPv6
         cannot be configured."
    DEFVAL { false }
    ::= { vRtrIfEntry 39 }

vRtrIfIPv6OperState  OBJECT-TYPE
    SYNTAX      TmnxOperState
    MAX-ACCESS  read-only
    STATUS      current
    DESCRIPTION
        "The current operational status for IPv6 on this router interface."
    ::= { vRtrIfEntry 40 }

vRtrIfIPv6IngressFilterId  OBJECT-TYPE
    SYNTAX      TIPFilterID
    MAX-ACCESS  read-create
    STATUS      current
    DESCRIPTION
        "The value of vRtrIfIPv6IngressFilterId associates an ip-filter-id
         with an ingress v6 interface. Filters control the forwarding and
         dropping of packets based on IP criteria.  A value of zero (0)
         indicates that there is no ip-filter-id associated with this
         interface.

         If this entry indicates a service virtual router interface or
         the special out-of-band management interface, this object is
         meaningless and is not applied to the interface."
    DEFVAL { 0 }
    ::= { vRtrIfEntry 41 }

vRtrIfIPv6EgressFilterId  OBJECT-TYPE
    SYNTAX      TIPFilterID
    MAX-ACCESS  read-create
    STATUS      current
    DESCRIPTION
        "The value of vRtrIfIPv6EgressFilterId associates an ip-filter-id
         with an egress v6 interface. Filters control the forwarding and
         dropping of packets based on IP criteria.  A value of zero (0)
         indicates that there is no ip-filter-id associated with this
         interface.

         If this entry indicates a service virtual router interface or
         the special out-of-band management interface, this object is
         meaningless and is not applied to the interface."
    DEFVAL { 0 }
    ::= { vRtrIfEntry 42 }

vRtrIfIcmpV6Redirects  OBJECT-TYPE
    SYNTAX      TruthValue
    MAX-ACCESS  read-create
    STATUS      current
    DESCRIPTION
        "When vRtrIfIcmpV6Redirects is set to 'true', ICMPv6 redirects are
         generated when routes are not optimal on this router and another
         router on the same subnetwork has a better route in order to
         alert that node that a better route is available.  When
         vRtrIfIcmpV6Redirects is set to 'false', ICMPv6 redirects are not
         generated."
    DEFVAL { true }
    ::= { vRtrIfEntry 43 }

vRtrIfIcmpV6NumRedirects  OBJECT-TYPE
    SYNTAX      Unsigned32 (10..1000)
    MAX-ACCESS  read-create
    STATUS      current
    DESCRIPTION
        "The value of vRtrIfIcmpV6NumRedirects limits the number of v6 redirects
         issued per the time frame specified in vRtrIfIcmpV6RedirectsTime."
    DEFVAL { 100 }
    ::= { vRtrIfEntry 44 }

vRtrIfIcmpV6RedirectsTime  OBJECT-TYPE
    SYNTAX      Unsigned32 (1..60)
    UNITS       "seconds"
    MAX-ACCESS  read-create
    STATUS      current
    DESCRIPTION
        "The value of vRtrIfIcmpV6RedirectsTime determines the time frame
         in seconds that is used to limit the number of v6 redirects issued
         per time frame."
    DEFVAL { 10 }
    ::= { vRtrIfEntry 45 }

vRtrIfIcmpV6Unreachables  OBJECT-TYPE
    SYNTAX      TruthValue
    MAX-ACCESS  read-create
    STATUS      current
    DESCRIPTION
        "When vRtrIfIcmpV6Unreachables is set to 'true', ICMPv6 host and
         network unreachable messages are generated by this interface.
         When vRtrIfIcmpV6Unreachables is set to 'false', ICMPv6 host and
         network unreachable messages are not sent."
    DEFVAL { true }
    ::= { vRtrIfEntry 46 }

vRtrIfIcmpV6NumUnreachables  OBJECT-TYPE
    SYNTAX      Unsigned32 (10..1000)
    MAX-ACCESS  read-create
    STATUS      current
    DESCRIPTION
        "The value of vRtrIfIcmpV6NumUnreachables determines how many
         destination unreachable ICMPv6 messages are issued in the time
         frame specified by vRtrIfIcmpV6UnreachablesTime."
    DEFVAL { 100 }
    ::= { vRtrIfEntry 47 }

vRtrIfIcmpV6UnreachablesTime  OBJECT-TYPE
    SYNTAX      Unsigned32 (1..60)
    UNITS       "seconds"
    MAX-ACCESS  read-create
    STATUS      current
    DESCRIPTION
        "The value of vRtrIfIcmpV6UnreachablesTime sets the time frame in
         seconds that is used to limit the number of destination
         unreachable ICMPv6 messages issued per time frame."
    DEFVAL { 10 }
    ::= { vRtrIfEntry 48 }

vRtrIfIcmpV6TimeExceeded  OBJECT-TYPE
    SYNTAX      TruthValue
    MAX-ACCESS  read-create
    STATUS      current
    DESCRIPTION
        "The value of vRtrIfIcmpV6TimeExceeded specifies whether
         time-exceeded ICMP messages should be sent. When it is set to
         'true', ICMPv6 time-exceeded messages are generated by this
         interface. When vRtrIfIcmpV6TimeExceeded is set to 'false',
         ICMPv6 time-exceeded messages are not sent."
    DEFVAL { true }
    ::= { vRtrIfEntry 49 }

vRtrIfIcmpV6NumTimeExceeded  OBJECT-TYPE
    SYNTAX      Unsigned32 (10..1000)
    MAX-ACCESS  read-create
    STATUS      current
    DESCRIPTION
        "The value of vRtrIfIcmpV6NumTimeExceeded specifies how many
         time-exceeded ICMPv6 messages are issued in the time
         frame specified by vRtrIfIcmpV6TimeExceededTime."
    DEFVAL { 100 }
    ::= { vRtrIfEntry 50 }

vRtrIfIcmpV6TimeExceededTime  OBJECT-TYPE
    SYNTAX      Unsigned32 (1..60)
    UNITS       "seconds"
    MAX-ACCESS  read-create
    STATUS      current
    DESCRIPTION
        "The value of vRtrIfIcmpV6TimeExceededTime specifies the time frame
         in seconds that is used to limit the number of time-exceeded
         ICMPv6 messages issued per time frame."
    DEFVAL { 10 }
    ::= { vRtrIfEntry 51 }

vRtrIfIcmpV6PktTooBig  OBJECT-TYPE
    SYNTAX      TruthValue
    MAX-ACCESS  read-create
    STATUS      current
    DESCRIPTION
        "The value of vRtrIfIcmpV6PktTooBig specifies whether
         packet-too-big ICMP messages should be sent. When it is set to
         'true', ICMPv6 packet-too-big messages are generated by this
         interface. When vRtrIfIcmpV6PktTooBig is set to 'false',
         ICMPv6 packet-too-big messages are not sent."
    DEFVAL { true }
    ::= { vRtrIfEntry 52 }

vRtrIfIcmpV6NumPktTooBig  OBJECT-TYPE
    SYNTAX      Unsigned32 (10..1000)
    MAX-ACCESS  read-create
    STATUS      current
    DESCRIPTION
        "The value of vRtrIfIcmpV6NumPktTooBig specifies how many
         packet-too-big ICMPv6 messages are issued in the time
         frame specified by vRtrIfIcmpV6PktTooBigTime."
    DEFVAL { 100 }
    ::= { vRtrIfEntry 53 }

vRtrIfIcmpV6PktTooBigTime  OBJECT-TYPE
    SYNTAX      Unsigned32 (1..60)
    UNITS       "seconds"
    MAX-ACCESS  read-create
    STATUS      current
    DESCRIPTION
        "The value of vRtrIfIcmpV6PktTooBigTime specifies the time frame
         in seconds that is used to limit the number of packet-too-big
         ICMPv6 messages issued per time frame."
    DEFVAL { 10 }
    ::= { vRtrIfEntry 54 }

vRtrIfIcmpV6ParamProblem  OBJECT-TYPE
    SYNTAX      TruthValue
    MAX-ACCESS  read-create
    STATUS      current
    DESCRIPTION
        "The value of vRtrIfIcmpV6ParamProblem specifies whether
         parameter-problem ICMP messages should be sent. When it is set to
         'true', ICMPv6 parameter-problem messages are generated by this
         interface. When vRtrIfIcmpV6ParamProblem is set to 'false',
         ICMPv6 parameter-problem messages are not sent."
    DEFVAL { true }
    ::= { vRtrIfEntry 55 }

vRtrIfIcmpV6NumParamProblem  OBJECT-TYPE
    SYNTAX      Unsigned32 (10..1000)
    MAX-ACCESS  read-create
    STATUS      current
    DESCRIPTION
        "The value of vRtrIfIcmpV6NumParamProblem specifies how many
         parameter-problem ICMPv6 messages are issued in the time
         frame specified by vRtrIfIcmpV6ParamProblemTime."
    DEFVAL { 100 }
    ::= { vRtrIfEntry 56 }

vRtrIfIcmpV6ParamProblemTime  OBJECT-TYPE
    SYNTAX      Unsigned32 (1..60)
    UNITS       "seconds"
    MAX-ACCESS  read-create
    STATUS      current
    DESCRIPTION
        "The value of vRtrIfIcmpV6ParamProblemTime specifies the time frame
         in seconds that is used to limit the number of parameter-problem
         ICMPv6 messages issued per time frame."
    DEFVAL { 10 }
    ::= { vRtrIfEntry 57 }

vRtrIfLinkLocalAddressType  OBJECT-TYPE
    SYNTAX      InetAddressType
    MAX-ACCESS  read-only
    STATUS      current
    DESCRIPTION
        "The value of vRtrIfLinkLocalAddressType indicates the IP address
         type of the link local address of this virtual router interface.
         When the value of vRtrIfIPv6OperState is 'inService', this object
         will have a value of 'ipv6z', and 'unknown' otherwise."
    ::= { vRtrIfEntry 58 }

vRtrIfLinkLocalAddress  OBJECT-TYPE
    SYNTAX      InetAddress (SIZE(0|20))
    MAX-ACCESS  read-only
    STATUS      current
    DESCRIPTION
        "The value of vRtrIfLinkLocalAddress indicates the link local IP
         address of this virtual router interface. This address valid when
         the value of vRtrIfIPv6OperState is 'inService'."
    ::= { vRtrIfEntry 59 }

vRtrIfLinkLocalAddressState  OBJECT-TYPE
    SYNTAX      TmnxInetAddrState
    MAX-ACCESS  read-only
    STATUS      current
    DESCRIPTION
        "The value of vRtrIfLinkLocalAddressState indicates the address
         state of vRtrIfLinkLocalAddress. When vRtrIfIPv6OperState is
         'outOfService', the value of this object is 'unknown'."
    ::= { vRtrIfEntry 60 }

vRtrIfLastOperStateChange       OBJECT-TYPE
    SYNTAX      TimeStamp
    MAX-ACCESS  read-only
    STATUS      current
    DESCRIPTION
        "The value of vRtrIfLastOperStateChange indicates the sysUpTime when
         the operational state of this interface last changed."
    ::= { vRtrIfEntry 61 }

vRtrIfOperMtu   OBJECT-TYPE
    SYNTAX      Unsigned32
    UNITS       "bytes"
    MAX-ACCESS  read-only
    STATUS      current
    DESCRIPTION
        "The value of vRtrIfOperMtu indicates the operational value of the
         IP MTU on this interface. It is the minimum of the vRtrIfMtu and
         the MTU of the physical port this interface is bound to."
    ::= { vRtrIfEntry 62 }

vRtrIfGlobalIndex  OBJECT-TYPE
    SYNTAX      Unsigned32 (0..65535)
    MAX-ACCESS  read-only
    STATUS      current
    DESCRIPTION
        "The value of vRtrIfGlobalIndex uniquely identifies this interface
         in the tmnx system. This field provides an identifier for router
         interfaces similar to the vRtrIfIndex value, except that vRtrIfIndex
         is unique within each virtual router. The vRtrIfGlobalIndex is unique
         system wide regardless of the vRtrID.

         The vRtrIfGlobalIndex value for each virtual interface must remain
         constant at least from one re-initialization of the system management
         processor to the next."
    ::= { vRtrIfEntry 63 }

vRtrIfDelaySeconds  OBJECT-TYPE
    SYNTAX      Unsigned32 (0..1200) 
    UNITS       "seconds"
    MAX-ACCESS  read-create
    STATUS      current
    DESCRIPTION
        "The value of vRtrIfDelaySeconds specifies the time in seconds
         that is used to bring up the interface.

         When interface comes up, it will not become operational until
         after the specified delay.

         The default value of vRtrIfDelaySeconds is 0. It indicates
         that the interface will become operational as soon as
         it is enabled."
    DEFVAL { 0 }
    ::= { vRtrIfEntry 64 }

vRtrIfDelayUpTimer  OBJECT-TYPE
    SYNTAX      Integer32
    UNITS       "seconds"
    MAX-ACCESS  read-only
    STATUS      current
    DESCRIPTION
        "The value of vRtrIfDelayUpTimer indicates the time left before the
         interface comes up when vRtrIfDelaySeconds is configured to a
         non-zero value.

         When the interface is down, this object will return the value -1.
         It's value can be in the range 0 to vRtrIfDelaySeconds's value
         if the interface is 'about to come up'.

         If the interface is up, the value of vRtrIfDelayUpTimer will be 0."
    ::= { vRtrIfEntry 65 }

vRtrIfLocalDhcpServerName  OBJECT-TYPE
    SYNTAX      TNamedItemOrEmpty
    MAX-ACCESS  read-create
    STATUS      current
    DESCRIPTION
        "The value of vRtrIfLocalDhcpServerName specifies the local DHCP server
         that can be reached via this interface.

         The server itself is configured on virtual router level in object
         TIMETRA-DHCP-SERVER-MIB::tmnxDhcpServerCfgServerName. Assigning
         an ip-address to it is done here by linking it to an interface.
         A server can be linked to several interfaces on the same virtual
         router."
    DEFVAL { ''H }
    ::= { vRtrIfEntry 66 }

vRtrIfInitDelayEnable OBJECT-TYPE
    SYNTAX      TruthValue
    MAX-ACCESS  read-create
    STATUS      current
    DESCRIPTION 
        "The value of vRtrIfInitDelayEnable specifies whether vRtrIfDelaySeconds
         is used only the next time or everytime the system attempts to bring 
         the interface operationally up.
         
         The value of vRtrIfInitDelayEnable is ignored if the value of 
         vRtrIfDelaySeconds is set to 0.

         The value of vRtrIfInitDelayEnable is only set when interface is of 
         type subscriber-interface.

         When the value vRtrIfInitDelayEnable is set to 'false', everytime 
         the system attempts to bring the interface operationally up, 
         it will be delayed by the value of vRtrIfDelaySeconds.

         When the value vRtrIfInitDelayEnable is set to 'true', only the next 
         time the system attempts to bring the interface operationally up, 
         it will be delayed by the value of vRtrIfDelaySeconds."
    DEFVAL { false }
    ::= { vRtrIfEntry 67 }

vRtrIfCpmProtPolicyId  OBJECT-TYPE
    SYNTAX      TCpmProtPolicyID
    MAX-ACCESS  read-create
    STATUS      current
    DESCRIPTION
        "The value of vRtrIfCpmProtPolicyId associates a CPM Protection policy
         with an interface. 
         
         A value of zero (0) specifies that no CPM Protection policy is
         associated with this interface.

         A value of one (1) specifies that the default CPM Protection policy is
         associated with this interface.

         If no value for vRtrIfCpmProtPolicyId is specified when the 
         vRtrIfEntry is created, the system assigns a default value, 
         derived from the value of the object vRtrIfType, as follows:

         vRtrIfType              vRtrIfCpmProtPolicyId
         ---------------------------------------------------------------------
         network                 1
         service                 used internally.
         serviceIes              1
         serviceRtdVpls          obsoleted.
         serviceVprn             1
         serviceIesSubscriber    0
         serviceIesGroup         0
         serviceVprnSubscriber   used internally.
         serviceVprnGroup        0
         serviceIesRedundant     0
         serviceVprnRedundant    0
         serviceVpls             0 
         serviceIesCem           defined on a SAP. --not supported
         serviceVprnCem          defined on a SAP. --not supported
         serviceVprnIPsec        0
         serviceVprnIPMirror     0

         If an interface would get a default value of 'one', it is not
         allowed to set the value of vRtrIfCpmProtPolicyId to 'zero'.

         If an interface would get a default value of 'zero', it is not
         allowed to modify the value of vRtrIfCpmProtPolicyId.

         This object is not supported on SR-1 and ESS-1, where the 
         value of TIMETRA-CHASSIS-MIB::tmnxChassisType is '5',
         and 7710, where the value of TIMETRA-CHASSIS-MIB::tmnxChassisType is
         '7' or '9'."
    ::= { vRtrIfEntry 68 }

vRtrIfCpmProtUncfgdProtoDropCnt  OBJECT-TYPE
    SYNTAX      Gauge32
    MAX-ACCESS  read-only
    STATUS      current
    DESCRIPTION
        "The value of vRtrIfCpmProtUncfgdProtoDropCnt indicates the number of  
         network control protocol messages dropped due to the operation of the
         protocol protection facility. 
         
         The protocol protection facility can be enabled and disabled by means
         of the object TIMETRA-SECURITY-MIB::tmnxCpmProtDropUncfgdProtocolMsg.

         When the protocol protection facility is enabled,
         network control protocol traffic received on this virtual router 
         interface is dropped if the protocol is not configured on this virtual
         router interface.

         The value of vRtrIfProtocol indicates which protocols are configured
         on this virtual router interface.

         This object is not supported on SR-1 and ESS-1, where the 
         value of TIMETRA-CHASSIS-MIB::tmnxChassisType is '5',
         and 7710, where the value of TIMETRA-CHASSIS-MIB::tmnxChassisType is
         '7' or '9'."
    ::= { vRtrIfEntry 69 }

vRtrIfLdpSyncTimer  OBJECT-TYPE
    SYNTAX      Unsigned32 (0|1..1800)
    UNITS       "seconds"
    MAX-ACCESS  read-create
    STATUS      current
    DESCRIPTION
        "The value of vRtrIfLdpSyncTimer specifies a time interval used 
         for IGP-LDP synchronization. The timer is started from the time the LDP 
         session to the neighbor is up over the interface. This is to allow 
         for the label FEC bindings to be exchanged. 

         When the timer expires, the link cost is restored and is re-advertised.
         IGP will announce a new best next-hop and LDP will use it if the 
         label binding for the neighbor's FEC is available."
    DEFVAL { 0 }
    ::= { vRtrIfEntry 70 }


--
-- Virtual Router ICMPv6 Statistics Table
--

vRtrIcmp6Table OBJECT-TYPE
    SYNTAX     SEQUENCE OF VRtrIcmp6Entry
    MAX-ACCESS not-accessible
    STATUS     current
    DESCRIPTION
        "The vRtrIcmp6Table table contains statistics
         of ICMPv6 messages that are received and sourced by
         a router instance."
    ::= { tmnxVRtrObjs 31 }

vRtrIcmp6Entry OBJECT-TYPE
    SYNTAX     VRtrIcmp6Entry
    MAX-ACCESS not-accessible
    STATUS     current
    DESCRIPTION
        "Each row entry represents the ICMP statistics of a
         virtual router instance. Entries are created and deleted
         when entries in the vRtrConfEntry are created and deleted."
    AUGMENTS { vRtrConfEntry  }
    ::= { vRtrIcmp6Table 1 }

VRtrIcmp6Entry ::=
    SEQUENCE {
        vRtrIcmp6InMsgs                    Counter32,
        vRtrIcmp6InErrors                  Counter32,
        vRtrIcmp6InDestUnreachs            Counter32,
        vRtrIcmp6InAdminProhibs            Counter32,
        vRtrIcmp6InTimeExcds               Counter32,
        vRtrIcmp6InParmProblems            Counter32,
        vRtrIcmp6InPktTooBigs              Counter32,
        vRtrIcmp6InEchos                   Counter32,
        vRtrIcmp6InEchoReplies             Counter32,
        vRtrIcmp6InRtrSolicits             Counter32,
        vRtrIcmp6InRtrAdvertisements       Counter32,
        vRtrIcmp6InNbrSolicits             Counter32,
        vRtrIcmp6InNbrAdvertisements       Counter32,
        vRtrIcmp6InRedirects               Counter32,
        vRtrIcmp6InGrpMembQueries          Counter32,
        vRtrIcmp6InGrpMembResponses        Counter32,
        vRtrIcmp6InGrpMembReductions       Counter32,
        vRtrIcmp6OutMsgs                   Counter32,
        vRtrIcmp6OutErrors                 Counter32,
        vRtrIcmp6OutDestUnreachs           Counter32,
        vRtrIcmp6OutAdminProhibs           Counter32,
        vRtrIcmp6OutTimeExcds              Counter32,
        vRtrIcmp6OutParmProblems           Counter32,
        vRtrIcmp6OutPktTooBigs             Counter32,
        vRtrIcmp6OutEchos                  Counter32,
        vRtrIcmp6OutEchoReplies            Counter32,
        vRtrIcmp6OutRtrSolicits            Counter32,
        vRtrIcmp6OutRtrAdvertisements      Counter32,
        vRtrIcmp6OutNbrSolicits            Counter32,
        vRtrIcmp6OutNbrAdvertisements      Counter32,
        vRtrIcmp6OutRedirects              Counter32,
        vRtrIcmp6OutGrpMembQueries         Counter32,
        vRtrIcmp6OutGrpMembResponses       Counter32,
        vRtrIcmp6OutGrpMembReductions      Counter32
        }

vRtrIcmp6InMsgs OBJECT-TYPE
    SYNTAX     Counter32
    MAX-ACCESS read-only
    STATUS     current
    DESCRIPTION
        "The value of vRtrIcmp6InMsgs indicates the total number
         of ICMP messages received by this router instance which
         includes all those counted by vRtrIcmp6InErrors."
    ::= { vRtrIcmp6Entry 1 }

vRtrIcmp6InErrors OBJECT-TYPE
    SYNTAX     Counter32
    MAX-ACCESS read-only
    STATUS     current
    DESCRIPTION
        "The value of vRtrIcmp6InErrors indicates the number of
         ICMP messages which this router instance received but determined
         as having ICMP-specific errors (bad ICMP checksums, bad length
         , etc.)."
    ::= { vRtrIcmp6Entry 2 }

vRtrIcmp6InDestUnreachs OBJECT-TYPE
    SYNTAX     Counter32
    MAX-ACCESS read-only
    STATUS     current
    DESCRIPTION
        "The value of vRtrIcmp6InDestUnreachs indicates the number of
         ICMP Destination Unreachable messages received by this router
         instance."
    ::= { vRtrIcmp6Entry 3 }

vRtrIcmp6InAdminProhibs OBJECT-TYPE
    SYNTAX     Counter32
    MAX-ACCESS read-only
    STATUS     current
    DESCRIPTION
        "The value of vRtrIcmp6InAdminProhibs indicates the number of
         ICMP destination unreachable/communication administratively
         prohibited messages received by this router instance."
    ::= { vRtrIcmp6Entry 4 }

vRtrIcmp6InTimeExcds OBJECT-TYPE
    SYNTAX     Counter32
    MAX-ACCESS read-only
    STATUS     current
    DESCRIPTION
         "The value of vRtrIcmp6InTimeExcds indicates the number of
          ICMP Time Exceeded messages received by this router instance."
    ::= { vRtrIcmp6Entry 5 }

vRtrIcmp6InParmProblems OBJECT-TYPE
    SYNTAX     Counter32
    MAX-ACCESS read-only
    STATUS     current
    DESCRIPTION
        "The value of vRtrIcmp6InParmProblems indicates the number of
         ICMP Parameter Problem messages received by this router instance."
    ::= { vRtrIcmp6Entry 6 }

vRtrIcmp6InPktTooBigs OBJECT-TYPE
    SYNTAX     Counter32
    MAX-ACCESS read-only
    STATUS     current
    DESCRIPTION
        "The value of vRtrIcmp6InPktTooBigs indicates the number of
         ICMP Packet Too Big messages received by this router instance."
    ::= { vRtrIcmp6Entry 7 }

vRtrIcmp6InEchos OBJECT-TYPE
    SYNTAX     Counter32
    MAX-ACCESS read-only
    STATUS     current
    DESCRIPTION
        "The value of vRtrIcmp6InEchos indicates the number of ICMP
         Echo (request) messages received by this router instance."
    ::= { vRtrIcmp6Entry 8 }

vRtrIcmp6InEchoReplies OBJECT-TYPE
    SYNTAX     Counter32
    MAX-ACCESS read-only
    STATUS     current
    DESCRIPTION
        "The value of vRtrIcmp6InEchoReplies indicates the number of ICMP
         Echo Reply messages received by this router instance."
    ::= { vRtrIcmp6Entry 9 }

vRtrIcmp6InRtrSolicits OBJECT-TYPE
    SYNTAX     Counter32
    MAX-ACCESS read-only
    STATUS     current
    DESCRIPTION
        "The value of vRtrIcmp6InRtrSolicits indicates the number of ICMP
         Router Solicit messages received by this router instance."
    ::= { vRtrIcmp6Entry 10 }

vRtrIcmp6InRtrAdvertisements OBJECT-TYPE
    SYNTAX     Counter32
    MAX-ACCESS read-only
    STATUS     current
    DESCRIPTION
        "The value of vRtrIcmp6InRtrAdvertisements indicates the number of
         ICMP Router Advertisement messages received by this router instance."
    ::= { vRtrIcmp6Entry 11 }

vRtrIcmp6InNbrSolicits OBJECT-TYPE
    SYNTAX     Counter32
    MAX-ACCESS read-only
    STATUS     current
    DESCRIPTION
        "The value of vRtrIcmp6InNbrSolicits indicates the number of ICMP
         Neighbor Solicit messages received by this router instance."
    ::= { vRtrIcmp6Entry 12 }

vRtrIcmp6InNbrAdvertisements OBJECT-TYPE
    SYNTAX     Counter32
    MAX-ACCESS read-only
    STATUS     current
    DESCRIPTION
        "The value of vRtrIcmp6InNbrAdvertisements indicates the number
         of ICMP Neighbor Advertisement messages received by this router
         instance."
    ::= { vRtrIcmp6Entry 13 }

vRtrIcmp6InRedirects OBJECT-TYPE
    SYNTAX     Counter32
    MAX-ACCESS read-only
    STATUS     current
    DESCRIPTION
        "The value of vRtrIcmp6InRedirects indicates number of ICMP
         Redirect messages received by this router instance."
    ::= { vRtrIcmp6Entry 14 }

vRtrIcmp6InGrpMembQueries OBJECT-TYPE
    SYNTAX     Counter32
    MAX-ACCESS read-only
    STATUS     current
    DESCRIPTION
        "The value of vRtrIcmp6InGrpMembQueries indicates the number of
         ICMP Group Membership Query messages received by this router
         instance."
    ::= { vRtrIcmp6Entry 15 }

vRtrIcmp6InGrpMembResponses OBJECT-TYPE
    SYNTAX     Counter32
    MAX-ACCESS read-only
    STATUS     current
    DESCRIPTION
        "The value of vRtrIcmp6InGrpMembResponses indicates the number of
         ICMP Group Membership Response messages received by this router
         instance."
    ::= { vRtrIcmp6Entry 16 }

vRtrIcmp6InGrpMembReductions OBJECT-TYPE
    SYNTAX     Counter32
    MAX-ACCESS read-only
    STATUS     current
    DESCRIPTION
        "The value of vRtrIcmp6InGrpMembReductions indicates the number of
         ICMP Group Membership Reduction messages received by this router
         instance."
    ::= { vRtrIcmp6Entry 17 }

vRtrIcmp6OutMsgs OBJECT-TYPE
    SYNTAX     Counter32
    MAX-ACCESS read-only
    STATUS     current
    DESCRIPTION
        "The value of vRtrIcmp6OutMsgs indicates the total number of ICMP
         messages which this router instance attempted to send.  Note that
         this counter includes all those counted by icmpOutErrors."
    ::= { vRtrIcmp6Entry 18 }

vRtrIcmp6OutErrors OBJECT-TYPE
    SYNTAX     Counter32
    MAX-ACCESS read-only
    STATUS     current
    DESCRIPTION
        "The value of vRtrIcmp6OutErrors indicates the number of ICMP
         messages which this router instance did not send due to problems
         discovered within ICMP such as a lack of buffers.  This value
         should not include errors discovered outside the ICMP layer such
         as the inability of VRtrIpv6 to route the resultant datagram.  In
         some implementations there may be no types of error which contribute
         to this counter's value."
    ::= { vRtrIcmp6Entry 19 }

vRtrIcmp6OutDestUnreachs OBJECT-TYPE
    SYNTAX     Counter32
    MAX-ACCESS read-only
    STATUS     current
    DESCRIPTION
        "The value of vRtrIcmp6OutDestUnreachs indicates the number of ICMP
         Destination Unreachable messages sent by this router instance."
    ::= { vRtrIcmp6Entry 20 }

vRtrIcmp6OutAdminProhibs OBJECT-TYPE
    SYNTAX     Counter32
    MAX-ACCESS read-only
    STATUS     current
    DESCRIPTION
        "The value of vRtrIcmp6OutAdminProhibs indicates the number of ICMP
         destination unreachable/communication administratively prohibited
         messages sent by this router instance."
    ::= { vRtrIcmp6Entry 21 }

vRtrIcmp6OutTimeExcds OBJECT-TYPE
    SYNTAX     Counter32
    MAX-ACCESS read-only
    STATUS     current
    DESCRIPTION
        "The value of vRtrIcmp6OutTimeExcds indicates the number of ICMP
         Time Exceeded messages sent by this router instance."
    ::= { vRtrIcmp6Entry 22 }

vRtrIcmp6OutParmProblems OBJECT-TYPE
    SYNTAX     Counter32
    MAX-ACCESS read-only
    STATUS     current
    DESCRIPTION
        "The value of vRtrIcmp6OutParmProblems indicates the number of ICMP
         Parameter Problem messages sent by this router instance."
    ::= { vRtrIcmp6Entry 23 }

vRtrIcmp6OutPktTooBigs OBJECT-TYPE
    SYNTAX     Counter32
    MAX-ACCESS read-only
    STATUS     current
    DESCRIPTION
        "The value of vRtrIcmp6OutPktTooBigs indicates the number
         of ICMP Packet Too Big messages sent by this router
         instance."
    ::= { vRtrIcmp6Entry 24 }

vRtrIcmp6OutEchos OBJECT-TYPE
    SYNTAX     Counter32
    MAX-ACCESS read-only
    STATUS     current
    DESCRIPTION
        "The value of vRtrIcmp6OutEchos indicates the number of ICMP
         Echo Request messages sent by this router instance."
    ::= { vRtrIcmp6Entry 25 }

vRtrIcmp6OutEchoReplies OBJECT-TYPE
    SYNTAX     Counter32
    MAX-ACCESS read-only
    STATUS     current
    DESCRIPTION
        "The value of vRtrIcmp6OutEchoReplies indicates the number
         of ICMP Echo Reply messages sent by this router instance."
    ::= { vRtrIcmp6Entry 26 }

vRtrIcmp6OutRtrSolicits OBJECT-TYPE
    SYNTAX     Counter32
    MAX-ACCESS read-only
    STATUS     current
    DESCRIPTION
        "The value of vRtrIcmp6OutRtrSolicits indicates the number
         of ICMP Router Solicitation messages sent by this router
         instance."
    ::= { vRtrIcmp6Entry 27 }

vRtrIcmp6OutRtrAdvertisements OBJECT-TYPE
    SYNTAX     Counter32
    MAX-ACCESS read-only
    STATUS     current
    DESCRIPTION
        "The value of vRtrIcmp6OutRtrAdvertisements indicates the
         number of ICMP Router Advertisement messages
         sent by this router instance."
    ::= { vRtrIcmp6Entry 28 }

vRtrIcmp6OutNbrSolicits OBJECT-TYPE
    SYNTAX     Counter32
    MAX-ACCESS read-only
    STATUS     current
    DESCRIPTION
        "The value of vRtrIcmp6OutNbrSolicits indicates the number
         of ICMP Neighbor Solicitation messages sent by this router
         instance."
    ::= { vRtrIcmp6Entry 29 }

vRtrIcmp6OutNbrAdvertisements OBJECT-TYPE
    SYNTAX     Counter32
    MAX-ACCESS read-only
    STATUS     current
    DESCRIPTION
        "The value of vRtrIcmp6OutNbrAdvertisements indicates the number
         of ICMP Neighbor Advertisement messages sent by this router
         instance."
    ::= { vRtrIcmp6Entry 30 }

vRtrIcmp6OutRedirects OBJECT-TYPE
    SYNTAX     Counter32
    MAX-ACCESS read-only
    STATUS     current
    DESCRIPTION
        "The value of vRtrIcmp6OutRedirects indicates the number of
         ICMP Redirect messages sent by this router instance."
    ::= { vRtrIcmp6Entry 31 }

vRtrIcmp6OutGrpMembQueries OBJECT-TYPE
    SYNTAX     Counter32
    MAX-ACCESS read-only
    STATUS     current
    DESCRIPTION
        "The value of vRtrIcmp6OutGrpMembQueries indicates the number of
         ICMP Group Membership Query messages sent by this router instance."
    ::= { vRtrIcmp6Entry 32 }

vRtrIcmp6OutGrpMembResponses OBJECT-TYPE
    SYNTAX     Counter32
    MAX-ACCESS read-only
    STATUS     current
    DESCRIPTION
        "The value of vRtrIcmp6OutGrpMembResponses indicates the number of
         ICMP Group Membership Response messages sent by this router
         instance."
    ::= { vRtrIcmp6Entry 33 }

vRtrIcmp6OutGrpMembReductions OBJECT-TYPE
    SYNTAX     Counter32
    MAX-ACCESS read-only
    STATUS     current
    DESCRIPTION
        "The value of vRtrIcmp6OutGrpMembReductions indicates the number of
         ICMP Group Membership Reduction messages sent by this router
         instance."
    ::= { vRtrIcmp6Entry 34 }

--
-- Virtual Router Interface ICMPv6 Statistics Table
--

vRtrIfIcmp6Table OBJECT-TYPE
    SYNTAX     SEQUENCE OF VRtrIfIcmp6Entry
    MAX-ACCESS not-accessible
    STATUS     current
    DESCRIPTION
        "The vRtrIfIcmp6Table table contains statistics
         of ICMPv6 messages that are received and sourced by
         a router interface."
    ::= { tmnxVRtrObjs 32 }

vRtrIfIcmp6Entry OBJECT-TYPE
    SYNTAX     VRtrIfIcmp6Entry
    MAX-ACCESS not-accessible
    STATUS     current
    DESCRIPTION
        "Each row entry represents the ICMP statistics of a
         virtual router interface. Entries are created and deleted
         when entries in the vRtrIfTable are created and deleted."
    AUGMENTS { vRtrIfEntry }
    ::= { vRtrIfIcmp6Table 1 }

VRtrIfIcmp6Entry ::=
    SEQUENCE {
        vRtrIfIcmp6InMsgs                    Counter32,
        vRtrIfIcmp6InErrors                  Counter32,
        vRtrIfIcmp6InDestUnreachs            Counter32,
        vRtrIfIcmp6InAdminProhibs            Counter32,
        vRtrIfIcmp6InTimeExcds               Counter32,
        vRtrIfIcmp6InParmProblems            Counter32,
        vRtrIfIcmp6InPktTooBigs              Counter32,
        vRtrIfIcmp6InEchos                   Counter32,
        vRtrIfIcmp6InEchoReplies             Counter32,
        vRtrIfIcmp6InRtrSolicits             Counter32,
        vRtrIfIcmp6InRtrAdvertisements       Counter32,
        vRtrIfIcmp6InNbrSolicits             Counter32,
        vRtrIfIcmp6InNbrAdvertisements       Counter32,
        vRtrIfIcmp6InRedirects               Counter32,
        vRtrIfIcmp6InGrpMembQueries          Counter32,
        vRtrIfIcmp6InGrpMembResponses        Counter32,
        vRtrIfIcmp6InGrpMembReductions       Counter32,
        vRtrIfIcmp6OutMsgs                   Counter32,
        vRtrIfIcmp6OutErrors                 Counter32,
        vRtrIfIcmp6OutDestUnreachs           Counter32,
        vRtrIfIcmp6OutAdminProhibs           Counter32,
        vRtrIfIcmp6OutTimeExcds              Counter32,
        vRtrIfIcmp6OutParmProblems           Counter32,
        vRtrIfIcmp6OutPktTooBigs             Counter32,
        vRtrIfIcmp6OutEchos                  Counter32,
        vRtrIfIcmp6OutEchoReplies            Counter32,
        vRtrIfIcmp6OutRtrSolicits            Counter32,
        vRtrIfIcmp6OutRtrSolicitsTime        TimeStamp,
        vRtrIfIcmp6OutRtrAdvertisements      Counter32,
        vRtrIfIcmp6OutRtrAdvTime             TimeStamp,
        vRtrIfIcmp6OutNbrSolicits            Counter32,
        vRtrIfIcmp6OutNbrSolicitsTime        TimeStamp,
        vRtrIfIcmp6OutNbrAdvertisements      Counter32,
        vRtrIfIcmp6OutNbrAdvTime             TimeStamp,
        vRtrIfIcmp6OutRedirects              Counter32,
        vRtrIfIcmp6OutGrpMembQueries         Counter32,
        vRtrIfIcmp6OutGrpMembResponses       Counter32,
        vRtrIfIcmp6OutGrpMembReductions      Counter32
        }

vRtrIfIcmp6InMsgs OBJECT-TYPE
    SYNTAX     Counter32
    MAX-ACCESS read-only
    STATUS     current
    DESCRIPTION
        "The value of vRtrIfIcmp6InMsgs indicates the total number
         of ICMP messages received by this interface which includes
         all those counted by vRtrIfIcmp6InErrors. Note that this
         interface is the interface to which the ICMP messages were
         addressed which may not be necessarily the input interface
         for the messages."
    ::= { vRtrIfIcmp6Entry 1 }

vRtrIfIcmp6InErrors OBJECT-TYPE
    SYNTAX     Counter32
    MAX-ACCESS read-only
    STATUS     current
    DESCRIPTION
        "The value of vRtrIfIcmp6InErrors indicates the number of
         ICMP messages which this interface received but determined
         as having ICMP-specific errors (bad ICMP checksums, bad length
         , etc.)."
    ::= { vRtrIfIcmp6Entry 2 }

vRtrIfIcmp6InDestUnreachs OBJECT-TYPE
    SYNTAX     Counter32
    MAX-ACCESS read-only
    STATUS     current
    DESCRIPTION
        "The value of vRtrIfIcmp6InDestUnreachs indicates the number of
         ICMP Destination Unreachable messages received by this interface."
    ::= { vRtrIfIcmp6Entry 3 }

vRtrIfIcmp6InAdminProhibs OBJECT-TYPE
    SYNTAX     Counter32
    MAX-ACCESS read-only
    STATUS     current
    DESCRIPTION
        "The value of vRtrIfIcmp6InAdminProhibs indicates the number of
         ICMP destination unreachable/communication administratively
         prohibited messages received by this interface."
    ::= { vRtrIfIcmp6Entry 4 }

vRtrIfIcmp6InTimeExcds OBJECT-TYPE
    SYNTAX     Counter32
    MAX-ACCESS read-only
    STATUS     current
    DESCRIPTION
         "The value of vRtrIfIcmp6InTimeExcds indicates the number of
          ICMP Time Exceeded messages received by this interface."
    ::= { vRtrIfIcmp6Entry 5 }

vRtrIfIcmp6InParmProblems OBJECT-TYPE
    SYNTAX     Counter32
    MAX-ACCESS read-only
    STATUS     current
    DESCRIPTION
        "The value of vRtrIfIcmp6InParmProblems indicates the number of
         ICMP Parameter Problem messages received by this interface."
    ::= { vRtrIfIcmp6Entry 6 }

vRtrIfIcmp6InPktTooBigs OBJECT-TYPE
    SYNTAX     Counter32
    MAX-ACCESS read-only
    STATUS     current
    DESCRIPTION
        "The value of vRtrIfIcmp6InPktTooBigs indicates the number of
         ICMP Packet Too Big messages received by this interface."
    ::= { vRtrIfIcmp6Entry 7 }

vRtrIfIcmp6InEchos OBJECT-TYPE
    SYNTAX     Counter32
    MAX-ACCESS read-only
    STATUS     current
    DESCRIPTION
        "The value of vRtrIfIcmp6InEchos indicates the number of ICMP
         Echo (request) messages received by this interface."
    ::= { vRtrIfIcmp6Entry 8 }

vRtrIfIcmp6InEchoReplies OBJECT-TYPE
    SYNTAX     Counter32
    MAX-ACCESS read-only
    STATUS     current
    DESCRIPTION
        "The value of vRtrIfIcmp6InEchoReplies indicates the number of ICMP
         Echo Reply messages received by this interface."
    ::= { vRtrIfIcmp6Entry 9 }

vRtrIfIcmp6InRtrSolicits OBJECT-TYPE
    SYNTAX     Counter32
    MAX-ACCESS read-only
    STATUS     current
    DESCRIPTION
        "The value of vRtrIfIcmp6InRtrSolicits indicates the number of ICMP
         Router Solicit messages received by this interface."
    ::= { vRtrIfIcmp6Entry 10 }

vRtrIfIcmp6InRtrAdvertisements OBJECT-TYPE
    SYNTAX     Counter32
    MAX-ACCESS read-only
    STATUS     current
    DESCRIPTION
        "The value of vRtrIfIcmp6InRtrAdvertisements indicates the number of
         ICMP Router Advertisement messages received by this interface."
    ::= { vRtrIfIcmp6Entry 11 }

vRtrIfIcmp6InNbrSolicits OBJECT-TYPE
    SYNTAX     Counter32
    MAX-ACCESS read-only
    STATUS     current
    DESCRIPTION
        "The value of vRtrIfIcmp6InNbrSolicits indicates the number of ICMP
         Neighbor Solicit messages received by this interface."
    ::= { vRtrIfIcmp6Entry 12 }

vRtrIfIcmp6InNbrAdvertisements OBJECT-TYPE
    SYNTAX     Counter32
    MAX-ACCESS read-only
    STATUS     current
    DESCRIPTION
        "The value of vRtrIfIcmp6InNbrAdvertisements indicates the number
         of ICMP Neighbor Advertisement messages received by this interface."
    ::= { vRtrIfIcmp6Entry 13 }

vRtrIfIcmp6InRedirects OBJECT-TYPE
    SYNTAX     Counter32
    MAX-ACCESS read-only
    STATUS     current
    DESCRIPTION
        "The value of vRtrIfIcmp6InRedirects indicates number of ICMP
         Redirect messages received by this interface."
    ::= { vRtrIfIcmp6Entry 14 }

vRtrIfIcmp6InGrpMembQueries OBJECT-TYPE
    SYNTAX     Counter32
    MAX-ACCESS read-only
    STATUS     current
    DESCRIPTION
        "The value of vRtrIfIcmp6InGrpMembQueries indicates the number of
         ICMP Group Membership Query messages received by this interface."
    ::= { vRtrIfIcmp6Entry 15 }

vRtrIfIcmp6InGrpMembResponses OBJECT-TYPE
    SYNTAX     Counter32
    MAX-ACCESS read-only
    STATUS     current
    DESCRIPTION
        "The value of vRtrIfIcmp6InGrpMembResponses indicates the number of
         ICMP Group Membership Response messages received by this interface."
    ::= { vRtrIfIcmp6Entry 16 }

vRtrIfIcmp6InGrpMembReductions OBJECT-TYPE
    SYNTAX     Counter32
    MAX-ACCESS read-only
    STATUS     current
    DESCRIPTION
        "The value of vRtrIfIcmp6InGrpMembReductions indicates the number of
         ICMP Group Membership Reduction messages received by this interface."
    ::= { vRtrIfIcmp6Entry 17 }

vRtrIfIcmp6OutMsgs OBJECT-TYPE
    SYNTAX     Counter32
    MAX-ACCESS read-only
    STATUS     current
    DESCRIPTION
        "The value of vRtrIfIcmp6OutMsgs indicates the total number of ICMP
         messages which this interface attempted to send.  Note that this
         counter includes all those counted by icmpOutErrors."
    ::= { vRtrIfIcmp6Entry 18 }

vRtrIfIcmp6OutErrors OBJECT-TYPE
    SYNTAX     Counter32
    MAX-ACCESS read-only
    STATUS     current
    DESCRIPTION
        "The value of vRtrIfIcmp6OutErrors indicates the number of ICMP
         messages which this interface did not send due to problems discovered
         within ICMP such as a lack of buffers.  This value should not include
         errors discovered outside the ICMP layer such as the inability of
         VRtrIpv6 to route the resultant datagram.  In some implementations
         there may be no types of error which contribute to this counter's
         value."
    ::= { vRtrIfIcmp6Entry 19 }

vRtrIfIcmp6OutDestUnreachs OBJECT-TYPE
    SYNTAX     Counter32
    MAX-ACCESS read-only
    STATUS     current
    DESCRIPTION
        "The value of vRtrIfIcmp6OutDestUnreachs indicates the number of ICMP
         Destination Unreachable messages sent by this interface."
    ::= { vRtrIfIcmp6Entry 20 }

vRtrIfIcmp6OutAdminProhibs OBJECT-TYPE
    SYNTAX     Counter32
    MAX-ACCESS read-only
    STATUS     current
    DESCRIPTION
        "The value of vRtrIfIcmp6OutAdminProhibs indicates the number of ICMP
         destination unreachable/communication administratively prohibited
         messages sent by this interface."
    ::= { vRtrIfIcmp6Entry 21 }

vRtrIfIcmp6OutTimeExcds OBJECT-TYPE
    SYNTAX     Counter32
    MAX-ACCESS read-only
    STATUS     current
    DESCRIPTION
        "The value of vRtrIfIcmp6OutTimeExcds indicates the number of ICMP
         Time Exceeded messages sent by this interface."
    ::= { vRtrIfIcmp6Entry 22 }

vRtrIfIcmp6OutParmProblems OBJECT-TYPE
    SYNTAX     Counter32
    MAX-ACCESS read-only
    STATUS     current
    DESCRIPTION
        "The value of vRtrIfIcmp6OutParmProblems indicates the number of ICMP
         Parameter Problem messages sent by this interface."
    ::= { vRtrIfIcmp6Entry 23 }

vRtrIfIcmp6OutPktTooBigs OBJECT-TYPE
    SYNTAX     Counter32
    MAX-ACCESS read-only
    STATUS     current
    DESCRIPTION
        "The value of vRtrIfIcmp6OutPktTooBigs indicates the number of ICMP
         Packet Too Big messages sent by this interface."
    ::= { vRtrIfIcmp6Entry 24 }

vRtrIfIcmp6OutEchos OBJECT-TYPE
    SYNTAX     Counter32
    MAX-ACCESS read-only
    STATUS     current
    DESCRIPTION
        "The value of vRtrIfIcmp6OutEchos indicates the number of ICMP
         Echo Request messages sent by this interface."
    ::= { vRtrIfIcmp6Entry 25 }

vRtrIfIcmp6OutEchoReplies OBJECT-TYPE
    SYNTAX     Counter32
    MAX-ACCESS read-only
    STATUS     current
    DESCRIPTION
        "The value of vRtrIfIcmp6OutEchoReplies indicates the number
         of ICMP Echo Reply messages sent by this interface."
    ::= { vRtrIfIcmp6Entry 26 }

vRtrIfIcmp6OutRtrSolicits OBJECT-TYPE
    SYNTAX     Counter32
    MAX-ACCESS read-only
    STATUS     current
    DESCRIPTION
        "The value of vRtrIfIcmp6OutRtrSolicits indicates the number
         of ICMP Router Solicitation messages sent by this interface."
    ::= { vRtrIfIcmp6Entry 27 }

vRtrIfIcmp6OutRtrSolicitsTime   OBJECT-TYPE
    SYNTAX      TimeStamp
    MAX-ACCESS  read-only
    STATUS      current
    DESCRIPTION
        "The value of vRtrIfIcmp6OutRtrSolicitsTime indicates the system
         time when the last router solicitation message was sent by this
         interface."
    ::= { vRtrIfIcmp6Entry 28 }

vRtrIfIcmp6OutRtrAdvertisements OBJECT-TYPE
    SYNTAX     Counter32
    MAX-ACCESS read-only
    STATUS     current
    DESCRIPTION
        "The value of vRtrIfIcmp6OutRtrAdvertisements indicates the
         number of ICMP Router Advertisement messages
         sent by this interface."
    ::= { vRtrIfIcmp6Entry 29 }

vRtrIfIcmp6OutRtrAdvTime        OBJECT-TYPE
    SYNTAX      TimeStamp
    MAX-ACCESS  read-only
    STATUS      current
    DESCRIPTION
        "The value of vRtrIfIcmp6OutRtrAdvTime indicates the system
         time when the last router advertisement message was sent by
         this interface."
    ::= { vRtrIfIcmp6Entry 30 }

vRtrIfIcmp6OutNbrSolicits OBJECT-TYPE
    SYNTAX     Counter32
    MAX-ACCESS read-only
    STATUS     current
    DESCRIPTION
        "The value of vRtrIfIcmp6OutNbrSolicits indicates the number
         of ICMP Neighbor Solicitation messages sent by this interface."
    ::= { vRtrIfIcmp6Entry 31 }

vRtrIfIcmp6OutNbrSolicitsTime OBJECT-TYPE
    SYNTAX      TimeStamp
    MAX-ACCESS  read-only
    STATUS      current
    DESCRIPTION
        "The value of vRtrIfIcmp6OutNbrSolicitsTime indicates the system
         time when the last neighbor solicitation message was sent by this
         interface."
    ::= { vRtrIfIcmp6Entry 32 }

vRtrIfIcmp6OutNbrAdvertisements OBJECT-TYPE
    SYNTAX     Counter32
    MAX-ACCESS read-only
    STATUS     current
    DESCRIPTION
        "The value of vRtrIfIcmp6OutNbrAdvertisements indicates the number
         of ICMP Neighbor Advertisement messages sent by this interface."
    ::= { vRtrIfIcmp6Entry 33 }

vRtrIfIcmp6OutNbrAdvTime        OBJECT-TYPE
    SYNTAX      TimeStamp
    MAX-ACCESS  read-only
    STATUS      current
    DESCRIPTION
        "The value of vRtrIfIcmp6OutNbrAdvTime indicates the system
         time when the last neighbor advertisement message was sent by
         this interface."
    ::= { vRtrIfIcmp6Entry 34 }

vRtrIfIcmp6OutRedirects OBJECT-TYPE
    SYNTAX     Counter32
    MAX-ACCESS read-only
    STATUS     current
    DESCRIPTION
        "The value of vRtrIfIcmp6OutRedirects indicates the number of
         ICMP Redirect messages sent by this interface."
    ::= { vRtrIfIcmp6Entry 35 }

vRtrIfIcmp6OutGrpMembQueries OBJECT-TYPE
    SYNTAX     Counter32
    MAX-ACCESS read-only
    STATUS     current
    DESCRIPTION
        "The value of vRtrIfIcmp6OutGrpMembQueries indicates the number of
         ICMP Group Membership Query messages sent by this interface."
    ::= { vRtrIfIcmp6Entry 36 }

vRtrIfIcmp6OutGrpMembResponses OBJECT-TYPE
    SYNTAX     Counter32
    MAX-ACCESS read-only
    STATUS     current
    DESCRIPTION
        "The value of vRtrIfIcmp6OutGrpMembResponses indicates the number of
         ICMP Group Membership Response messages sent by this interface."
    ::= { vRtrIfIcmp6Entry 37 }

vRtrIfIcmp6OutGrpMembReductions OBJECT-TYPE
    SYNTAX     Counter32
    MAX-ACCESS read-only
    STATUS     current
    DESCRIPTION
        "The value of vRtrIfIcmp6OutGrpMembReductions indicates the number of
         ICMP Group Membership Reduction messages sent by this interface."
    ::= { vRtrIfIcmp6Entry 38 }

--
--  Virtual Router Interface Bi-directional Forwarding Detection table
--

vRtrIfBfdTable OBJECT-TYPE
    SYNTAX     SEQUENCE OF VRtrIfBfdEntry
    MAX-ACCESS not-accessible
    STATUS     current
    DESCRIPTION
        "The vRtrIfBfdTable table contains the configuration for
         Bi-directional Forwarding Detection (BFD) on the vRtrIfEntry
         with the same indices."
    ::= { tmnxVRtrObjs 33 }

vRtrIfBfdEntry OBJECT-TYPE
    SYNTAX     VRtrIfBfdEntry
    MAX-ACCESS not-accessible
    STATUS     current
    DESCRIPTION
        "Each row entry represents the BFD configuration for an
         interface. Entries are created and deleted when entries
         in the vRtrIfTable are created and deleted."
    AUGMENTS { vRtrIfEntry }
    ::= { vRtrIfBfdTable 1 }

VRtrIfBfdEntry ::=
    SEQUENCE {
        vRtrIfBfdAdminState             TmnxAdminState,
        vRtrIfBfdTransmitInterval       Unsigned32,
        vRtrIfBfdReceiveInterval        Unsigned32,
        vRtrIfBfdMultiplier             Unsigned32,
        vRtrIfBfdEchoInterval           Unsigned32
    }

vRtrIfBfdAdminState     OBJECT-TYPE
    SYNTAX      TmnxAdminState
    MAX-ACCESS  read-write
    STATUS      current
    DESCRIPTION
        "The value of vRtrIfBfdAdminState specifies the admin state of
         BFD on this interface. When it is 'inService', BFD sessions can be
         established on this interface. When it is 'outOfService', they
         cannot."
    ::= { vRtrIfBfdEntry 1 }

vRtrIfBfdTransmitInterval       OBJECT-TYPE
    SYNTAX      Unsigned32 (100..100000) --100..100k
    UNITS       "milliseconds"
    MAX-ACCESS  read-write
    STATUS      current
    DESCRIPTION
        "The value of vRtrIfBfdTransmitInterval specifies the BFD transmit
         interval over this interface."
    DEFVAL { 100 }
    ::= { vRtrIfBfdEntry 2 }

vRtrIfBfdReceiveInterval        OBJECT-TYPE
    SYNTAX      Unsigned32 (100..100000) --100..100k
    UNITS       "milliseconds"
    MAX-ACCESS  read-write
    STATUS      current
    DESCRIPTION
        "The value of vRtrIfBfdReceiveInterval specifies the BFD receive
         interval over this interface."
    DEFVAL { 100 }
    ::= { vRtrIfBfdEntry 3 }

vRtrIfBfdMultiplier     OBJECT-TYPE
    SYNTAX      Unsigned32 (3..20)
    MAX-ACCESS  read-write
    STATUS      current
    DESCRIPTION
        "The value of vRtrIfBfdMultiplier specifies the the number of
         consecutive BFD messages that must be missed from the peer before
         the BFD session state is changed to down and the upper level
         protocols (OSPF, IS-IS or PIM) are notified of the fault."
    DEFVAL { 3 }
    ::= { vRtrIfBfdEntry 4 }

vRtrIfBfdEchoInterval    OBJECT-TYPE
    SYNTAX      Unsigned32 (0|100..100000) --100..100k
    UNITS       "milliseconds"
    MAX-ACCESS  read-write
    STATUS      current
    DESCRIPTION
        "The value of vRtrIfBfdEchoInterval specifies the BFD echo
         interval over this interface."
    DEFVAL { 0 }
    ::= { vRtrIfBfdEntry 5 }

--
--  Virtual Router BFD session table
--

vRtrIfBfdSessionTable OBJECT-TYPE
    SYNTAX     SEQUENCE OF VRtrIfBfdSessionEntry
    MAX-ACCESS not-accessible
    STATUS     current
    DESCRIPTION
        "The vRtrIfBfdSessionTable table contains per BFD session statistics
         and operational settings."
    ::= { tmnxVRtrObjs 34 }

vRtrIfBfdSessionEntry OBJECT-TYPE
    SYNTAX     VRtrIfBfdSessionEntry
    MAX-ACCESS not-accessible
    STATUS     current
    DESCRIPTION
        "Each row entry represents a BFD session. Entries are created
         automatically by the system, or when a static-route is
         configured to use BFD."
    INDEX {
        vRtrID,
        vRtrIfIndex,
        vRtrIfBfdSessionLclAddrType,
        vRtrIfBfdSessionLclAddr,
        vRtrIfBfdSessionRemAddrType,
        vRtrIfBfdSessionRemAddr
        }
    ::= { vRtrIfBfdSessionTable 1 }

VRtrIfBfdSessionEntry ::=
    SEQUENCE {
        vRtrIfBfdSessionLclAddrType     InetAddressType,
        vRtrIfBfdSessionLclAddr         InetAddress,
        vRtrIfBfdSessionRemAddrType     InetAddressType,
        vRtrIfBfdSessionRemAddr         InetAddress,
        vRtrIfBfdSessionOperState       TmnxOperState,
        vRtrIfBfdSessionState           INTEGER,
        vRtrIfBfdSessionOperFlags       BITS,
        vRtrIfBfdSessionMesgRecv        Counter32,
        vRtrIfBfdSessionMesgSent        Counter32,
        vRtrIfBfdSessionLastDownTime    TimeStamp,
        vRtrIfBfdSessionLastUpTime      TimeStamp,
        vRtrIfBfdSessionUpCount         Counter32,
        vRtrIfBfdSessionDownCount       Counter32,
        vRtrIfBfdSessionLclDisc         Unsigned32,
        vRtrIfBfdSessionRemDisc         Unsigned32,
        vRtrIfBfdSessionProtocols       BITS,
        vRtrIfBfdSessionTxInterval      Unsigned32,
        vRtrIfBfdSessionRxInterval      Unsigned32,
        vRtrIfBfdSessionType            INTEGER
    }

vRtrIfBfdSessionLclAddrType     OBJECT-TYPE
    SYNTAX      InetAddressType
    MAX-ACCESS  not-accessible
    STATUS      current
    DESCRIPTION
        "The value of vRtrIfBfdSessionLclAddrType indicates the address
         type in vRtrIfBfdSessionLclAddr."
    ::= { vRtrIfBfdSessionEntry 1 }

vRtrIfBfdSessionLclAddr         OBJECT-TYPE
    SYNTAX      InetAddress (SIZE(0|4))
    MAX-ACCESS  not-accessible
    STATUS      current
    DESCRIPTION
        "The value of vRtrIfBfdSessionLclAddr indicates the address of the
         local endpoint of this BFD session. Its type is specified by
         vRtrIfBfdSessionLclAddrType."
    ::= { vRtrIfBfdSessionEntry 2 }

vRtrIfBfdSessionRemAddrType     OBJECT-TYPE
    SYNTAX      InetAddressType
    MAX-ACCESS  not-accessible
    STATUS      current
    DESCRIPTION
        "The value of vRtrIfBfdSessionRemAddrType indicates the address
         type in vRtrIfBfdSessionRemAddr."
    ::= { vRtrIfBfdSessionEntry 3 }

vRtrIfBfdSessionRemAddr         OBJECT-TYPE
    SYNTAX      InetAddress (SIZE(0|4))
    MAX-ACCESS  not-accessible
    STATUS      current
    DESCRIPTION
        "The value of vRtrIfBfdSessionRemAddr indicates the address of the
         local endpoint of this BFD session. Its type is specified by
         vRtrIfBfdSessionRemAddrType."
    ::= { vRtrIfBfdSessionEntry 4 }

vRtrIfBfdSessionOperState       OBJECT-TYPE
    SYNTAX      TmnxOperState
    MAX-ACCESS  read-only
    STATUS      current
    DESCRIPTION
        "The value of vRtrIfBfdSessionOperState indicates the operational state
         of BFD on this interface."
    ::= { vRtrIfBfdSessionEntry 5 }

vRtrIfBfdSessionState   OBJECT-TYPE
    SYNTAX      INTEGER {
                   adminDown (0),  --Session is administratively down
                   down      (1),  --Session is down
                   init      (2),  --Session is initializing
                   up        (3)   --Session is up
                }
    MAX-ACCESS  read-only
    STATUS      current
    DESCRIPTION
        "The value of vRtrIfBfdSessionState indicates the state of the BFD
         protocl on this interface."
    ::= { vRtrIfBfdSessionEntry 6 }

vRtrIfBfdSessionOperFlags       OBJECT-TYPE
    SYNTAX      BITS {
                    noProtocols    (0),
                    noHeartBeat    (1),
                    echoFailed     (2),
                    nbrSignalDown  (3),
                    fwdPlaneReset  (4),
                    pathDown       (5),
                    nbrAdminDown   (6),
                    adminClear     (7)
                }
    MAX-ACCESS  read-only
    STATUS      current
    DESCRIPTION
        "The value of vRtrIfBfdSessionOperFlags indicates the reasons why a BFD
         session is not up."
    ::= { vRtrIfBfdSessionEntry 7 }

vRtrIfBfdSessionMesgRecv        OBJECT-TYPE
    SYNTAX      Counter32
    MAX-ACCESS  read-only
    STATUS      current
    DESCRIPTION
        "The value of vRtrIfBfdSessionMesgRecv indicates the number of messages
         received in this session."
    ::= { vRtrIfBfdSessionEntry 8 }

vRtrIfBfdSessionMesgSent        OBJECT-TYPE
    SYNTAX      Counter32
    MAX-ACCESS  read-only
    STATUS      current
    DESCRIPTION
        "The value of vRtrIfBfdSessionMesgSent indicates the number of messages
         sent in this session."
    ::= { vRtrIfBfdSessionEntry 9 }


vRtrIfBfdSessionLastDownTime        OBJECT-TYPE
    SYNTAX      TimeStamp
    MAX-ACCESS  read-only
    STATUS      current
    DESCRIPTION
        "The value of vRtrIfBfdSessionLastDownTime indicates the system time
         when this session last went down."
    ::= { vRtrIfBfdSessionEntry 10 }

vRtrIfBfdSessionLastUpTime        OBJECT-TYPE
    SYNTAX      TimeStamp
    MAX-ACCESS  read-only
    STATUS      current
    DESCRIPTION
        "The value of vRtrIfBfdSessionLastUpTime indicates the system time
         when this session last came up."
    ::= { vRtrIfBfdSessionEntry 11 }

vRtrIfBfdSessionUpCount         OBJECT-TYPE
    SYNTAX      Counter32
    MAX-ACCESS  read-only
    STATUS      current
    DESCRIPTION
        "The value of vRtrIfBfdSessionUpCount indicates the number of times
         vRtrIfBfdSessionOperState changed from 'outOfService' to 'inService'."
    ::= { vRtrIfBfdSessionEntry 12 }

vRtrIfBfdSessionDownCount         OBJECT-TYPE
    SYNTAX      Counter32
    MAX-ACCESS  read-only
    STATUS      current
    DESCRIPTION
        "The value of vRtrIfBfdSessionDownCount indicates the number of times
         vRtrIfBfdSessionOperState changed from 'inService' to 'outOfService'."
    ::= { vRtrIfBfdSessionEntry 13 }

vRtrIfBfdSessionLclDisc         OBJECT-TYPE
    SYNTAX      Unsigned32
    MAX-ACCESS  read-only
    STATUS      current
    DESCRIPTION
        "The value of vRtrIfBfdSessionLclDisc indicates the unique local
         discriminator for this session."
    ::= { vRtrIfBfdSessionEntry 14 }

vRtrIfBfdSessionRemDisc         OBJECT-TYPE
    SYNTAX      Unsigned32
    MAX-ACCESS  read-only
    STATUS      current
    DESCRIPTION
        "The value of vRtrIfBfdSessionRemDisc indicates the remote
         discriminator for this session."
    ::= { vRtrIfBfdSessionEntry 15 }

vRtrIfBfdSessionProtocols       OBJECT-TYPE
    SYNTAX      BITS {
                    ospfv2 (0),
                    pim (1),
                    isis (2),
                    staticRoute (3),
                    mcRing (4),
                    rsvp (5),
                    bgp (6)
                }
    MAX-ACCESS  read-only
    STATUS      current
    DESCRIPTION
        "The value of vRtrIfBfdSessionProtocols indicates which protocols
         are using this BFD session."
    ::= { vRtrIfBfdSessionEntry 16 }

vRtrIfBfdSessionTxInterval      OBJECT-TYPE
    SYNTAX      Unsigned32
    UNITS       "milliseconds"
    MAX-ACCESS  read-only
    STATUS      current
    DESCRIPTION
        "The value of vRtrIfBfdSessionTxInterval indicates the negotiated
         transmit interval. This value is the minimum of the local node's
         'vRtrIfBfdTransmitInterval' and the remote node's receive interval."
    ::= { vRtrIfBfdSessionEntry 17 }

vRtrIfBfdSessionRxInterval      OBJECT-TYPE
    SYNTAX      Unsigned32
    UNITS       "milliseconds"
    MAX-ACCESS  read-only
    STATUS      current
    DESCRIPTION
        "The value of vRtrIfBfdSessionRxInterval indicates the negotiated
         receive interval. This value is the minimum of the local node's
         'vRtrIfBfdReceiveInterval' and the remote node's transmit interval."
    ::= { vRtrIfBfdSessionEntry 18 }

vRtrIfBfdSessionType      OBJECT-TYPE
    SYNTAX     INTEGER {    
                  iom (1), --Session is running on IOM
                  cpm (2)  --Session is running on CPM
               } 
    MAX-ACCESS  read-only
    STATUS      current
    DESCRIPTION
        "The value of vRtrIfBfdSessionType indicates if the bfd session is 
         running on IOM or CPM."
    ::= { vRtrIfBfdSessionEntry 19 }

--
--  Alcatel 7x50 SR series Virtual Router Interface Proxy ARP Table
--
--  Augmentation of the vRtrIfTable.
--  Use of AUGMENTS clause implies a one-to-one dependent relationship
--  between the base table, vRtrIfTable, and the augmenting table,
--  vRtrIfProxyArpTable. This in effect extends the vRtrIfTable with
--  additional columns. Creation (or deletion) of a row in the
--  vRtrIfTable results in the same fate for the row in the
--  vRtrIfProxyArpTable.
--

vRtrIfProxyArpTable  OBJECT-TYPE
    SYNTAX      SEQUENCE OF VRtrIfProxyArpEntry
    MAX-ACCESS  not-accessible
    STATUS      current
    DESCRIPTION
        "The vRtrIfProxyArpTable provides an extension to the vRtrIfTable.
         It has an entry for each virtual router interface configured in
         the system."
    ::= { tmnxVRtrObjs 18 }

vRtrIfProxyArpEntry  OBJECT-TYPE
    SYNTAX      VRtrIfProxyArpEntry
    MAX-ACCESS  not-accessible
    STATUS      current
    DESCRIPTION
        "Each row entry represents information related to Proxy ARP for a
         virtual router interface in the system.

         Entries cannot be created and deleted via SNMP SET operations."
    AUGMENTS { vRtrIfEntry }
    ::= { vRtrIfProxyArpTable 1 }

VRtrIfProxyArpEntry ::=
    SEQUENCE {
        vRtrIfProxyArp              TruthValue,
        vRtrIfProxyArpLocal         TruthValue,
        vRtrIfProxyArpPolicy1       TPolicyStatementNameOrEmpty,
        vRtrIfProxyArpPolicy2       TPolicyStatementNameOrEmpty,
        vRtrIfProxyArpPolicy3       TPolicyStatementNameOrEmpty,
        vRtrIfProxyArpPolicy4       TPolicyStatementNameOrEmpty,
        vRtrIfProxyArpPolicy5       TPolicyStatementNameOrEmpty
        }

vRtrIfProxyArp  OBJECT-TYPE
    SYNTAX      TruthValue
    MAX-ACCESS  read-create
    STATUS      current
    DESCRIPTION
        "If the value of vRtrIfProxyArp is set to 'true', proxy ARP is
         enabled on this interface. If this value is 'false', proxy ARP
         is disabled on the interface."
    DEFVAL { false }
    ::= { vRtrIfProxyArpEntry 1 }

vRtrIfProxyArpLocal  OBJECT-TYPE
    SYNTAX      TruthValue
    MAX-ACCESS  read-create
    STATUS      current
    DESCRIPTION
        "If the value of vRtrIfProxyArpLocal is set to 'true', local proxy
         ARP is enabled, that is, the interface will reply to ARP requests
         even if both the hosts are on the same subnet. In this case ICMP
         redirects will be disabled. If the value of vRtrIfProxyArpLocal
         is set to 'false', the interface will not reply to ARP requests
         if both the hosts are on the same subnet."
     DEFVAL { false }
    ::= { vRtrIfProxyArpEntry 2 }

vRtrIfProxyArpPolicy1  OBJECT-TYPE
    SYNTAX      TPolicyStatementNameOrEmpty
    MAX-ACCESS  read-create
    STATUS      current
    DESCRIPTION
        "The value of vRtrIfProxyArpPolicy1 is used to specify the first
         proxy ARP policy for this interface. This policy determines
         networks and sources for which proxy ARP will be attempted. If
         this value is set to an empty string, ''H, the interface does
         not have a proxy ARP policy associated with it.

         The value of vRtrIfProxyArpPolicy1 has no effect if vRtrIfProxyArp
         is set to 'false'."
    DEFVAL { ''H }      -- the empty string
    ::= { vRtrIfProxyArpEntry 3 }

vRtrIfProxyArpPolicy2  OBJECT-TYPE
    SYNTAX      TPolicyStatementNameOrEmpty
    MAX-ACCESS  read-create
    STATUS      current
    DESCRIPTION
        "The value of vRtrIfProxyArpPolicy2 is used to specify the second
         proxy ARP policy for this interface. This policy determines
         networks and sources for which proxy ARP will be attempted. If
         this value is set to an empty string, ''H, the interface does
         not have a proxy ARP policy associated with it.

         The value of vRtrIfProxyArpPolicy2 has no effect if vRtrIfProxyArp
         is set to 'false'."
    DEFVAL { ''H }      -- the empty string
    ::= { vRtrIfProxyArpEntry 4 }

vRtrIfProxyArpPolicy3  OBJECT-TYPE
    SYNTAX      TPolicyStatementNameOrEmpty
    MAX-ACCESS  read-create
    STATUS      current
    DESCRIPTION
        "The value of vRtrIfProxyArpPolicy3 is used to specify the third
         proxy ARP policy for this interface. This policy determines
         networks and sources for which proxy ARP will be attempted. If
         this value is set to an empty string, ''H, the interface does
         not have a proxy ARP policy associated with it.

         The value of vRtrIfProxyArpPolicy3 has no effect if vRtrIfProxyArp
         is set to 'false'."
    DEFVAL { ''H }      -- the empty string
    ::= { vRtrIfProxyArpEntry 5 }

vRtrIfProxyArpPolicy4  OBJECT-TYPE
    SYNTAX      TPolicyStatementNameOrEmpty
    MAX-ACCESS  read-create
    STATUS      current
    DESCRIPTION
        "The value of vRtrIfProxyArpPolicy4 is used to specify the fourth
         proxy ARP policy for this interface. This policy determines
         networks and sources for which proxy ARP will be attempted. If
         this value is set to an empty string, ''H, the interface does
         not have a proxy ARP policy associated with it.

         The value of vRtrIfProxyArpPolicy4 has no effect if vRtrIfProxyArp
         is set to 'false'."
    DEFVAL { ''H }      -- the empty string
    ::= { vRtrIfProxyArpEntry 6 }

vRtrIfProxyArpPolicy5  OBJECT-TYPE
    SYNTAX      TPolicyStatementNameOrEmpty
    MAX-ACCESS  read-create
    STATUS      current
    DESCRIPTION
        "The value of vRtrIfProxyArpPolicy5 is used to specify the fifth
         proxy ARP policy for this interface. This policy determines
         networks and sources for which proxy ARP will be attempted. If
         this value is set to an empty string, ''H, the interface does
         not have a proxy ARP policy associated with it.

         The value of vRtrIfProxyArpPolicy5 has no effect if vRtrIfProxyArp
         is set to 'false'."
    DEFVAL { ''H }      -- the empty string
    ::= { vRtrIfProxyArpEntry 7 }


--
--  Alcatel 7x50 SR series Virtual Router Interface DHCP Relay Table
--
--  Augmentation of the vRtrIfTable.
--  Use of AUGMENTS clause implies a one-to-one dependent relationship
--  between the base table, vRtrIfTable, and the augmenting table,
--  vRtrIfDHCPTable. This in effect extends the vRtrIfTable with
--  additional columns. Creation (or deletion) of a row in the
--  vRtrIfTable results in the same fate for the row in the
--  vRtrIfDHCPTable.
--

vRtrIfDHCPTable  OBJECT-TYPE
    SYNTAX      SEQUENCE OF VRtrIfDHCPEntry
    MAX-ACCESS  not-accessible
    STATUS      current
    DESCRIPTION
        "The vRtrIfDHCPTable is used to configure the interface
         parameters for the DHCP Relay agent."
    ::= { tmnxVRtrObjs 19 }

vRtrIfDHCPEntry  OBJECT-TYPE
    SYNTAX      VRtrIfDHCPEntry
    MAX-ACCESS  not-accessible
    STATUS      current
    DESCRIPTION
        "Each row entry represents information related to DHCP Relay for a
         virtual router interface in the system.

         Entries cannot be created and deleted via SNMP SET operations."
    AUGMENTS { vRtrIfEntry }
    ::= { vRtrIfDHCPTable 1 }

VRtrIfDHCPEntry ::=
    SEQUENCE {
        vRtrIfDHCPRelayInfoOption       TruthValue,
        vRtrIfDHCPRelayInfoAction       INTEGER,
        vRtrIfDHCPRelayCircuitId        INTEGER,
        vRtrIfDHCPRelayRemoteId         INTEGER,
        vRtrIfDHCPAutoFilter            Unsigned32,
        vRtrIfDHCPRelayServer1          IpAddress,
        vRtrIfDHCPRelayServer2          IpAddress,
        vRtrIfDHCPRelayServer3          IpAddress,
        vRtrIfDHCPRelayServer4          IpAddress,
        vRtrIfDHCPRelayServer5          IpAddress,
        vRtrIfDHCPRelayServer6          IpAddress,
        vRtrIfDHCPRelayServer7          IpAddress,
        vRtrIfDHCPRelayServer8          IpAddress,
        vRtrIfDHCPRelayTrusted          TruthValue,
        vRtrIfDHCPAdminState            TmnxAdminState,
        vRtrIfDHCPSnooping              INTEGER,
        vRtrIfDHCPDescription           TItemDescription,
        vRtrIfDHCPAutoFilterId          TFilterID,
        vRtrIfDHCPOperAutoFilter        Unsigned32,
        vRtrIfDHCPAuthPolicy            TPolicyStatementNameOrEmpty,
        vRtrIfDHCPLeasePopulate         Unsigned32,
        vRtrIfDHCPOperLeasePopulate     Unsigned32,
        vRtrIfDHCPGiAddressType         InetAddressType,
        vRtrIfDHCPGiAddress             InetAddress,
        vRtrIfDHCPGiAddressAsSrc        TruthValue,
        vRtrIfDHCPMatchOption82         TruthValue,
        vRtrIfDHCPRelayRemoteIdStr      DisplayString,
        vRtrIfDHCPProxyAdminState       TmnxAdminState,
        vRtrIfDHCPProxyServerAddr       IpAddress,
        vRtrIfDHCPProxyLeaseTime        Unsigned32,
        vRtrIfDHCPProxyLTRadiusOverride TruthValue,
        vRtrIfDHCPVendorIncludeOptions  BITS,
        vRtrIfDHCPVendorOptionString    DisplayString,
        vRtrIfDHCPLayer2Header          TruthValue,
        vRtrIfDHCPAntiSpoofMacAddr      MacAddress,
        vRtrIfDHCPClientApplications    BITS
        }

vRtrIfDHCPRelayInfoOption  OBJECT-TYPE
    SYNTAX      TruthValue
    MAX-ACCESS  read-create
    STATUS      obsolete
    DESCRIPTION
        "vRtrIfDHCPRelayInfoOption is used to enable/disable DHCP
         Option 82. If the value of this object is set to 'false', DHCP
         Relay is disabled."
    DEFVAL { false }
    ::= { vRtrIfDHCPEntry 1 }

vRtrIfDHCPRelayInfoAction  OBJECT-TYPE
    SYNTAX      INTEGER {
                    replace (1),
                    drop    (2),
                    keep    (3)
                }
    MAX-ACCESS  read-create
    STATUS      current
    DESCRIPTION
        "vRtrIfDHCPRelayInfoAction is used to configure the DHCP Relay
         reforwarding policy.

         replace(1) - replace existing information with
                      DHCP relay information
         drop(2)    - discard messages with existing relay information if
                      the option-82 information is also present.
         keep(3)    - retain the existing relay information."
    DEFVAL { keep }
    ::= { vRtrIfDHCPEntry 2 }

vRtrIfDHCPRelayCircuitId  OBJECT-TYPE
    SYNTAX      INTEGER {
                    none           (0),
                    ifIndex        (1),
                    asciiTuple     (2),
                    sapId          (3),
                    vlanAsciiTuple (4)
                }
    MAX-ACCESS  read-create
    STATUS      current
    DESCRIPTION
        "The value of the object vRtrIfDHCPRelayCircuitId specifies whether or
         not the circuit-id suboption is present, and if it is present what
         information goes in it.
         If the value of this object is set to 'none', the circuit-id suboption
         will not be part of the information option (option 82).
         If the value of this object is set to 'ifIndex', the value of the
         interface index is used.
         If the value of this object is set to 'asciiTuple', the ASCII-encoded
         concatenated tuple consisting of the
         - access-node-identifier
         - service-id
         - interface-name
         - SAP-id (only if the value of vRtrIfType is 'serviceIesGroup')
         is used.
         If the value of this object is set to 'sapId', the ASCII-encoded
         SAP-id is used.
         If the value of this object is set to 'vlan-ascii-tuple' - the format
         will include VLAN-id and dot1p bits in addition to what is included in
         ascii-tuple already.  The format is supported on dot1q and qinq
         encapsulated ports only.  Thus, when the option 82 bits are
         stripped, dot1p bits will be copied to the Ethernet header of an
         outgoing packet."
    DEFVAL { asciiTuple }
    ::= { vRtrIfDHCPEntry 3 }

vRtrIfDHCPRelayRemoteId  OBJECT-TYPE
    SYNTAX      INTEGER {
                    mac       (1),
                    none      (2),
                    remote-id (3)
                }
    MAX-ACCESS  read-create
    STATUS      current
    DESCRIPTION
        "The value of vRtrIfDHCPRelayRemoteId specifies what information goes
         into the remote-id suboption in the DHCP Relay packet.  If the
         value of this object is set to 'none', the remote-id suboption is
         left blank. If the value of this object is set to 'mac',
         the MAC address of the remote end is encoded in the suboption.  If the
         value of the object is set to 'remote-id', vRtrIfDHCPRelayRemoteIdStr
         will be the remote-id."
    DEFVAL { none }
    ::= { vRtrIfDHCPEntry 4 }

vRtrIfDHCPAutoFilter  OBJECT-TYPE
    SYNTAX      Unsigned32 (0..2000)
    MAX-ACCESS  read-create
    STATUS      obsolete
    DESCRIPTION
        "vRtrIfDHCPAutoFilter allows the router to automatically build
         anti-spoofing filter lists. When this object is set to a non-zero
         value, auto-filtering is enabled and a filter allowing only
         PPPoE or DHCP traffic is established on the interface. The non-zero
         value indicates the maximum number of entries that the auto-filter
         can have. These entries are created by the agent upon snooping a
         valid DHCP Reply packet and are used to allow traffic sourced by
         the given DHCP-assigned IP address."
    DEFVAL { 0 }
    ::= { vRtrIfDHCPEntry 5 }

vRtrIfDHCPRelayServer1  OBJECT-TYPE
    SYNTAX      IpAddress
    MAX-ACCESS  read-create
    STATUS      current
    DESCRIPTION
        "vRtrIfDHCPRelayServer1 is used to configure the first DHCP server
         where the requests will be forwarded."
    DEFVAL { '00000000'H } -- 0.0.0.0
    ::= { vRtrIfDHCPEntry 6 }

vRtrIfDHCPRelayServer2  OBJECT-TYPE
    SYNTAX      IpAddress
    MAX-ACCESS  read-create
    STATUS      current
    DESCRIPTION
        "vRtrIfDHCPRelayServer2 is used to configure the second DHCP server
         where the requests will be forwarded."
    DEFVAL { '00000000'H }
    ::= { vRtrIfDHCPEntry 7 }

vRtrIfDHCPRelayServer3  OBJECT-TYPE
    SYNTAX      IpAddress
    MAX-ACCESS  read-create
    STATUS      current
    DESCRIPTION
        "vRtrIfDHCPRelayServer3 is used to configure the third DHCP server
         where the requests will be forwarded."
    DEFVAL { '00000000'H }
    ::= { vRtrIfDHCPEntry 8 }

vRtrIfDHCPRelayServer4  OBJECT-TYPE
    SYNTAX      IpAddress
    MAX-ACCESS  read-create
    STATUS      current
    DESCRIPTION
        "vRtrIfDHCPRelayServer4 is used to configure the fourth DHCP server
         where the requests will be forwarded."
    DEFVAL { '00000000'H }
    ::= { vRtrIfDHCPEntry 9 }

vRtrIfDHCPRelayServer5  OBJECT-TYPE
    SYNTAX      IpAddress
    MAX-ACCESS  read-create
    STATUS      current
    DESCRIPTION
        "vRtrIfDHCPRelayServer5 is used to configure the fifth DHCP server
         where the requests will be forwarded."
    DEFVAL { '00000000'H }
    ::= { vRtrIfDHCPEntry 10 }

vRtrIfDHCPRelayServer6  OBJECT-TYPE
    SYNTAX      IpAddress
    MAX-ACCESS  read-create
    STATUS      current
    DESCRIPTION
        "vRtrIfDHCPRelayServer6 is used to configure the sixth DHCP server
         where the requests will be forwarded."
    DEFVAL { '00000000'H }
    ::= { vRtrIfDHCPEntry 11 }

vRtrIfDHCPRelayServer7  OBJECT-TYPE
    SYNTAX      IpAddress
    MAX-ACCESS  read-create
    STATUS      current
    DESCRIPTION
        "vRtrIfDHCPRelayServer7 is used to configure the seventh DHCP server
         where the requests will be forwarded."
    DEFVAL { '00000000'H }
    ::= { vRtrIfDHCPEntry 12 }

vRtrIfDHCPRelayServer8  OBJECT-TYPE
    SYNTAX      IpAddress
    MAX-ACCESS  read-create
    STATUS      current
    DESCRIPTION
        "vRtrIfDHCPRelayServer8 is used to configure the eighth DHCP server
         where the requests will be forwarded."
    DEFVAL { '00000000'H }
    ::= { vRtrIfDHCPEntry 13 }

vRtrIfDHCPRelayTrusted  OBJECT-TYPE
    SYNTAX          TruthValue
    MAX-ACCESS      read-create
    STATUS          current
    DESCRIPTION
        "When the value of vRtrIfDHCPRelayTrusted is set to 'true(1)', the
         router will relay requests where the DHCP giaddr is zero."
    DEFVAL { false }
    ::= { vRtrIfDHCPEntry 14 }

vRtrIfDHCPAdminState  OBJECT-TYPE
    SYNTAX      TmnxAdminState
    MAX-ACCESS  read-create
    STATUS      current
    DESCRIPTION
        "vRtrIfDHCPAdminState is used to configure the desired
         administrative state of DHCP on this interface.
         If the value of vRtrIfType is network this object can only be set
         to 'outOfService'."
    DEFVAL { outOfService }
    ::= { vRtrIfDHCPEntry 15 }

vRtrIfDHCPSnooping  OBJECT-TYPE
    SYNTAX          INTEGER {
                        enabled(1),
                        disabled(2)
                    }
    MAX-ACCESS      read-create
    STATUS          obsolete
    DESCRIPTION
        "vRtrIfDHCPSnooping is used to enable/disable snooping of DHCP
         packets received on interface."
    DEFVAL { disabled }
    ::= { vRtrIfDHCPEntry 16 }

vRtrIfDHCPDescription  OBJECT-TYPE
    SYNTAX      TItemDescription
    MAX-ACCESS  read-create
    STATUS      current
    DESCRIPTION
        "The value of vRtrIfDHCPDescription is a user provided description
         string for DHCP on this virtual router interface.  It can consist of
         any printable, seven-bit ASCII characters up to 80 characters in
         length."
    DEFVAL { ''H }      -- the empty string
    ::= { vRtrIfDHCPEntry 17 }

vRtrIfDHCPAutoFilterId  OBJECT-TYPE
    SYNTAX      TFilterID
    MAX-ACCESS  read-only
    STATUS      obsolete
    DESCRIPTION
        "vRtrIfDHCPAutoFilterId maintains the auto-filter identifier being
         used for this interface."
    ::= { vRtrIfDHCPEntry 18 }

vRtrIfDHCPOperAutoFilter  OBJECT-TYPE
    SYNTAX      Unsigned32 (0..2000)
    MAX-ACCESS  read-only
    STATUS      obsolete
    DESCRIPTION
        "The value of vRtrIfDHCPOperAutoFilter indicates the number of active
         auto-filter entries per interface. These entries are created in the
         TIMETRA-FILTER-MIB::tIPFilterTable by the agent by snooping
         valid 'DHCP ACK' messages."
    DEFVAL { 0 }
    ::= { vRtrIfDHCPEntry 19 }

vRtrIfDHCPAuthPolicy  OBJECT-TYPE
    SYNTAX      TPolicyStatementNameOrEmpty
    MAX-ACCESS  read-create
    STATUS      current
    DESCRIPTION
        "Defines which subscriber authentication policy must be applied when a
         subscriber message (e.g. DHCP, PPPoE, ...) is received on the
         interface.
         The authentication policy must be defined in tmnxSubAuthPlcyTable."
    DEFVAL { ''H }
    ::= { vRtrIfDHCPEntry 20 }

vRtrIfDHCPLeasePopulate  OBJECT-TYPE
    SYNTAX      Unsigned32 (0..8000)
    MAX-ACCESS  read-create
    STATUS      current
    DESCRIPTION
        "The value of the object vRtrIfDHCPLeasePopulate specifies the
         maximum number of DHCP lease states allowed on this interface."
    DEFVAL { 0 }
    ::= { vRtrIfDHCPEntry 21 }

vRtrIfDHCPOperLeasePopulate  OBJECT-TYPE
    SYNTAX      Unsigned32 (0..8000)
    MAX-ACCESS  read-only
    STATUS      current
    DESCRIPTION
        "The value of the object vRtrIfDHCPOperLeasePopulate indicates the
         maximum number of DHCP lease states allocated on this interface."
    ::= { vRtrIfDHCPEntry 22 }

vRtrIfDHCPGiAddressType OBJECT-TYPE
    SYNTAX      InetAddressType
    MAX-ACCESS  read-create
    STATUS      current
    DESCRIPTION
        "The value of vRtrIfDHCPGiAddressType specifies the type of
         vRtrIfDHCPGiAddress, the gateway interface address."
    DEFVAL { unknown }
    ::= { vRtrIfDHCPEntry 23 }

vRtrIfDHCPGiAddress  OBJECT-TYPE
    SYNTAX      InetAddress (SIZE(0|4))
    MAX-ACCESS  read-create
    STATUS      current
    DESCRIPTION
        "The value of vRtrIfDHCPGiAddress specifies the gateway interface
         address. The type of this address is specified by the value of
         vRtrIfDHCPGiAddressType."
    DEFVAL { ''H }
    ::= { vRtrIfDHCPEntry 24 }

vRtrIfDHCPGiAddressAsSrc  OBJECT-TYPE
    SYNTAX      TruthValue
    MAX-ACCESS  read-create
    STATUS      current
    DESCRIPTION
        "The value of vRtrIfDHCPGiAddressAsSrc specifies whether the DHCP
         relay should use the gateway interface address as the source IP
         address when communicating with the DHCP server. When it is set
         to 'true(1)', the source IP address used to communicate with the DHCP
         server is the gateway interface address. When it is 'false', the
         source IP is the IP of the egress interface the IP packet goes
         out on."
    DEFVAL { false }
    ::= { vRtrIfDHCPEntry 25 }

vRtrIfDHCPMatchOption82  OBJECT-TYPE
    SYNTAX      TruthValue
    MAX-ACCESS  read-create
    STATUS      current
    DESCRIPTION
        "The value of vRtrIfDHCPMatchOption82 specifies whether the
         DHCP relay should use the circuit ID in the option 82 field
         in DHCP packets to match DHCP messages. When it is set to 'true(1)',
         the option 82 circuit ID is used in addition to the MAC address and
         transaction ID. When it is set to 'false', only the MAC address and
         transaction ID are used."
    DEFVAL { false }
    ::= { vRtrIfDHCPEntry 26 }

vRtrIfDHCPRelayRemoteIdStr  OBJECT-TYPE
    SYNTAX      DisplayString (SIZE (0..32))
    MAX-ACCESS  read-create
    STATUS      current
    DESCRIPTION
        "The value of vRtrIfDHCPRelayRemoteIdStr specifies the remote-id
         in the DHCP Relay packet if value of vRtrIfDHCPRelayRemoteId is set
         to 'remote-id'."
    DEFVAL { "" }
    ::= { vRtrIfDHCPEntry 27 }

vRtrIfDHCPProxyAdminState  OBJECT-TYPE
    SYNTAX      TmnxAdminState
    MAX-ACCESS  read-create
    STATUS      current
    DESCRIPTION
        "The value of vRtrIfDHCPProxyAdminState specifies the desired
         administrative state of the proxy server on this interface.

         When it is set to 'inService', the proxy server is enabled only if
         vRtrIfDHCPAdminState is also set to 'inService'."
    DEFVAL { outOfService }
    ::= { vRtrIfDHCPEntry 28 }

vRtrIfDHCPProxyServerAddr  OBJECT-TYPE
    SYNTAX      IpAddress
    MAX-ACCESS  read-create
    STATUS      current
    DESCRIPTION
        "The value of vRtrIfDHCPProxyServerAddr specifies the IP address
         which will be used as the source address of the emulated DHCP server.

         If this IP address is not configured, the value of vRiaIpAddress
         will be used as the source address of the emulated DHCP server."
    DEFVAL { '00000000'H }  -- 0.0.0.0 means not-set
    ::= { vRtrIfDHCPEntry 29 }

vRtrIfDHCPProxyLeaseTime  OBJECT-TYPE
    SYNTAX      Unsigned32 (0|300..315446399)
    UNITS       "seconds"
    MAX-ACCESS  read-create
    STATUS      current
    DESCRIPTION
        "The value of vRtrIfDHCPProxyLeaseTime specifies in seconds how long a
         DHCP client is allowed to use the offered IP address.

         Value 0 means the lease time provided by a RADIUS or an upstream DHCP
         server will not be overridden. A lease time of 7 days is used when
         RADIUS does not provide a lease time."
    DEFVAL { 0 }
    ::= { vRtrIfDHCPEntry 30 }

vRtrIfDHCPProxyLTRadiusOverride  OBJECT-TYPE
    SYNTAX      TruthValue
    MAX-ACCESS  read-create
    STATUS      current
    DESCRIPTION
        "The value of vRtrIfDHCPProxyLTRadiusOverride specifies whether or not
         the lease time provided by the RADIUS server is presented to the DHCP
         client.

         By default the proxy-server will always make use of
         vRtrIfDHCPProxyLeaseTime, regardless of what lease time information is
         provided from the RADIUS server.
         When vRtrIfDHCPProxyLTRadiusOverride is set to 'true(1)', the
         proxy-server will use the lease time information provided by the
         RADIUS server, regardless of the configured one."
    DEFVAL { false }
    ::= { vRtrIfDHCPEntry 31 }

vRtrIfDHCPVendorIncludeOptions OBJECT-TYPE
    SYNTAX      BITS {
                    systemId  (0),
                    clientMac (1),
                    serviceId (2),
                    sapId     (3)
                }
    MAX-ACCESS  read-create
    STATUS      current
    DESCRIPTION
        "The value of vRtrIfDHCPVendorIncludeOptions specifies what is
         encoded in the Alcatel vendor specific sub-option of option 82.

         The value of this object is only used when vRtrIfDHCPRelayInfoAction
         is 'replace(1)'."
    DEFVAL { '0'H }
    ::= { vRtrIfDHCPEntry 32 }

vRtrIfDHCPVendorOptionString  OBJECT-TYPE
    SYNTAX      DisplayString (SIZE (0..32))
    MAX-ACCESS  read-create
    STATUS      current
    DESCRIPTION
        "The value of vRtrIfDHCPVendorOptionString specifies the string that
         goes into the Alcatel vendor specific sub-option of option 82.

         This string is only used when vRtrIfDHCPRelayInfoAction is set to
         'replace(1)'."
    DEFVAL { "" }
    ::= { vRtrIfDHCPEntry 33 }

vRtrIfDHCPLayer2Header OBJECT-TYPE
    SYNTAX      TruthValue
    MAX-ACCESS  read-create
    STATUS      current
    DESCRIPTION
        "The value of vRtrIfDHCPLayer2Header specificies,
         together with the value of object vRtrIfDHCPAntiSpoofMacAddr,
         the MAC address that is used in anti-spoof entries for the lease
         states on this interface.
         
         When it is set to 'false (2)', the client hardware address from the
         DHCP payload, stored in TIMETRA-SERV-MIB::svcDhcpLseStateChAddr,
         is used.

         When it is set to 'true (1)', the behavior depends on the value of
         vRtrIfDHCPAntiSpoofMacAddr. If vRtrIfDHCPAntiSpoofMacAddr is set to
         all zeros, the source MAC address in the L2 header of the DHCP packet
         is used. If vRtrIfDHCPAntiSpoofMacAddr is configured, then its value
         is used."
    DEFVAL { false }
    ::= { vRtrIfDHCPEntry 34 }

vRtrIfDHCPAntiSpoofMacAddr OBJECT-TYPE
    SYNTAX      MacAddress
    MAX-ACCESS  read-create
    STATUS      current
    DESCRIPTION
        "The value of vRtrIfDHCPAntiSpoofMacAddr specifies,
         together with the value of object vRtrIfDHCPLayer2Header,
         the MAC address that is used in anti-spoof entries for the lease
         states on this interface.

         When vRtrIfDHCPLayer2Header is 'false (2)', the client hardware
         address from the DHCP payload, stored in
         TIMETRA-SERV-MIB::svcDhcpLseStateChAddr, is used.

         When vRtrIfDHCPLayer2Header is 'true (1)' and the value of this object
         is all zeros, the source MAC address in the L2 header of the DHCP
         packet is used.
         
         When vRtrIfDHCPLayer2Header is 'true (1)' and the value of this object
         is not all zeros, then this value is used.

         This object can only be configured if the value of object
         vRtrIfDHCPLayer2Header is set to 'true (1)'."
    DEFVAL { '000000000000'H }
    ::= { vRtrIfDHCPEntry 35 }

vRtrIfDHCPClientApplications OBJECT-TYPE
    SYNTAX      BITS {
                    dhcp  (0),
                    pppoe (1)
                }
    MAX-ACCESS  read-create
    STATUS      current
    DESCRIPTION
        "The value of vRtrIfDHCPClientApplications specifies the set of
         client applications that can make use of the DHCP relay functionality
         on this interface."
    DEFVAL { { dhcp } }
    ::= { vRtrIfDHCPEntry 36 }

--
-- DHCP Relay Statistics Table
--

vRtrIfDHCPRelayStatsTable  OBJECT-TYPE
    SYNTAX      SEQUENCE OF VRtrIfDHCPRelayStatsEntry
    MAX-ACCESS  not-accessible
    STATUS      current
    DESCRIPTION
        "The vRtrIfDHCPRelayStatsTable contains the statistics for the
         DHCP Relay agent."
    ::= { tmnxVRtrObjs 20 }

vRtrIfDHCPRelayStatsEntry      OBJECT-TYPE
    SYNTAX      VRtrIfDHCPRelayStatsEntry
    MAX-ACCESS  not-accessible
    STATUS      current
    DESCRIPTION
        "Each row entry represents information related to DHCP Relay statistics
         for a virtual router interface in the system.

         Entries cannot be created and deleted via SNMP SET operations."
    AUGMENTS { vRtrIfEntry }
    ::= { vRtrIfDHCPRelayStatsTable 1 }

VRtrIfDHCPRelayStatsEntry ::=
    SEQUENCE {
        vRtrIfDHCPRelayRxPkts              Counter32,
        vRtrIfDHCPRelayTxPkts              Counter32,
        vRtrIfDHCPRelayRxMalformedPkts     Counter32,
        vRtrIfDHCPRelayRxUntrustedPkts     Counter32,
        vRtrIfDHCPRelayClientPktsDiscarded Counter32,
        vRtrIfDHCPRelayClientPktsRelayed   Counter32,
        vRtrIfDHCPRelayServerPktsDiscarded Counter32,
        vRtrIfDHCPRelayServerPktsRelayed   Counter32,
        vRtrIfDHCPRelayAuthPktsDiscarded   Counter32,
        vRtrIfDHCPRelayAuthPktsSuccess     Counter32,
        vRtrIfDHCPRelayClientPktsSnooped   Counter32,
        vRtrIfDHCPRelayServerPktsSnooped   Counter32,
        vRtrIfDHCPRelayClientPktsProxRad   Counter32,
        vRtrIfDHCPRelayClientPktsProxLS    Counter32,
        vRtrIfDHCPRelayPktsGenRelease      Counter32,
        vRtrIfDHCPRelayPktsGenForceRenew   Counter32
        }

vRtrIfDHCPRelayRxPkts  OBJECT-TYPE
    SYNTAX      Counter32
    MAX-ACCESS  read-only
    STATUS      current
    DESCRIPTION
        "vRtrIfDHCPRelayRxPkts indicates the total number of packets received
         by the DHCP relay agent."
    ::= { vRtrIfDHCPRelayStatsEntry 1 }

vRtrIfDHCPRelayTxPkts  OBJECT-TYPE
    SYNTAX      Counter32
    MAX-ACCESS  read-only
    STATUS      current
    DESCRIPTION
        "vRtrIfDHCPRelayTxPkts indicates the total number of packets transmitted
         by the DHCP relay agent."
    ::= { vRtrIfDHCPRelayStatsEntry 2 }

vRtrIfDHCPRelayRxMalformedPkts  OBJECT-TYPE
    SYNTAX      Counter32
    MAX-ACCESS  read-only
    STATUS      current
    DESCRIPTION
        "vRtrIfDHCPRelayRxMalformedPkts indicates the total number of
         malformed packets received by the DHCP relay agent."
    ::= { vRtrIfDHCPRelayStatsEntry 3 }

vRtrIfDHCPRelayRxUntrustedPkts  OBJECT-TYPE
    SYNTAX      Counter32
    MAX-ACCESS  read-only
    STATUS      current
    DESCRIPTION
        "vRtrIfDHCPRelayRxUntrustedPkts indicates the total number of
         untrusted packets received by the DHCP relay agent."
    ::= { vRtrIfDHCPRelayStatsEntry 4 }

vRtrIfDHCPRelayClientPktsDiscarded  OBJECT-TYPE
    SYNTAX      Counter32
    MAX-ACCESS  read-only
    STATUS      current
    DESCRIPTION
        "vRtrIfDHCPRelayClientPktsDiscarded indicates the total number of
         client packets dicarded by the DHCP relay agent."
    ::= { vRtrIfDHCPRelayStatsEntry 5 }

vRtrIfDHCPRelayClientPktsRelayed  OBJECT-TYPE
    SYNTAX      Counter32
    MAX-ACCESS  read-only
    STATUS      current
    DESCRIPTION
        "vRtrIfDHCPRelayClientPktsRelayed indicates the total number of
         client packets relayed by the DHCP relay agent."
    ::= { vRtrIfDHCPRelayStatsEntry 6 }

vRtrIfDHCPRelayServerPktsDiscarded  OBJECT-TYPE
    SYNTAX      Counter32
    MAX-ACCESS  read-only
    STATUS      current
    DESCRIPTION
        "vRtrIfDHCPRelayServerPktsDiscarded indicates the total number of
         server packets discarded by the DHCP relay agent."
    ::= { vRtrIfDHCPRelayStatsEntry 7 }

vRtrIfDHCPRelayServerPktsRelayed  OBJECT-TYPE
    SYNTAX      Counter32
    MAX-ACCESS  read-only
    STATUS      current
    DESCRIPTION
        "vRtrIfDHCPRelayServerPktsRelayed indicates the total number of
         server packets relayed by the DHCP relay agent."
    ::= { vRtrIfDHCPRelayStatsEntry 8 }

vRtrIfDHCPRelayAuthPktsDiscarded  OBJECT-TYPE
    SYNTAX      Counter32
    MAX-ACCESS  read-only
    STATUS      current
    DESCRIPTION
        "vRtrIfDHCPRelayAuthPktsDiscarded indicates the total number of
         packets discarded because authentication was not successful."
    ::= { vRtrIfDHCPRelayStatsEntry 9 }

vRtrIfDHCPRelayAuthPktsSuccess  OBJECT-TYPE
    SYNTAX      Counter32
    MAX-ACCESS  read-only
    STATUS      current
    DESCRIPTION
        "vRtrIfDHCPRelayAuthPktsSuccess indicates the total number of
         packets for which authentication was successful."
    ::= { vRtrIfDHCPRelayStatsEntry 10 }

vRtrIfDHCPRelayClientPktsSnooped  OBJECT-TYPE
    SYNTAX      Counter32
    MAX-ACCESS  read-only
    STATUS      current
    DESCRIPTION
        "vRtrIfDHCPRelayClientPktsSnooped indicates the total number of
         client packets snooped by the DHCP relay agent."
    ::= { vRtrIfDHCPRelayStatsEntry 11 }

vRtrIfDHCPRelayServerPktsSnooped  OBJECT-TYPE
    SYNTAX      Counter32
    MAX-ACCESS  read-only
    STATUS      current
    DESCRIPTION
        "vRtrIfDHCPRelayServerPktsSnooped indicates the total number of
         server packets snooped by the DHCP relay agent."
    ::= { vRtrIfDHCPRelayStatsEntry 12 }

vRtrIfDHCPRelayClientPktsProxRad  OBJECT-TYPE
    SYNTAX      Counter32
    MAX-ACCESS  read-only
    STATUS      current
    DESCRIPTION
        "vRtrIfDHCPRelayClientPktsProxRad indicates the total number of
         client packets proxied by the DHCP relay agent based on data received
         from a RADIUS server."
    ::= { vRtrIfDHCPRelayStatsEntry 13 }

vRtrIfDHCPRelayClientPktsProxLS  OBJECT-TYPE
    SYNTAX      Counter32
    MAX-ACCESS  read-only
    STATUS      current
    DESCRIPTION
        "vRtrIfDHCPRelayClientPktsProxLS indicates the total number of
         client packets proxied by the DHCP relay agent based on a lease
         state. The lease itself can have been obtained from a DHCP or RADIUS
         server. This is the so called lease split functionality."
    ::= { vRtrIfDHCPRelayStatsEntry 14 }

vRtrIfDHCPRelayPktsGenRelease  OBJECT-TYPE
    SYNTAX      Counter32
    MAX-ACCESS  read-only
    STATUS      current
    DESCRIPTION
        "vRtrIfDHCPRelayPktsGenRelease indicates the total number of DHCP
         RELEASE messages spoofed by the DHCP relay agent to the DHCP server."
    ::= { vRtrIfDHCPRelayStatsEntry 15 }

vRtrIfDHCPRelayPktsGenForceRenew  OBJECT-TYPE
    SYNTAX      Counter32
    MAX-ACCESS  read-only
    STATUS      current
    DESCRIPTION
        "vRtrIfDHCPRelayPktsGenForceRenew indicates the total number of DHCP
         FORCERENEW messages spoofed by the DHCP relay agent to the DHCP
         clients."
    ::= { vRtrIfDHCPRelayStatsEntry 16 }

--
--  Virtual Router Interface DHCP Lease State Table
--

vRtrIfDHCPLeaseStateTable  OBJECT-TYPE
    SYNTAX      SEQUENCE OF VRtrIfDHCPLeaseStateEntry
    MAX-ACCESS  not-accessible
    STATUS      obsolete
    DESCRIPTION
        "vRtrIfDHCPLeaseStateTable contains DHCP lease state info for a
         virtual router interface in the system.
         The content of this table is moved to the
         TIMETRA-SERV-MIB::svcDhcpLeaseStateTable."
    ::= { tmnxVRtrObjs 22 }

vRtrIfDHCPLeaseStateEntry  OBJECT-TYPE
    SYNTAX      VRtrIfDHCPLeaseStateEntry
    MAX-ACCESS  not-accessible
    STATUS      obsolete
    DESCRIPTION
        "DHCP lease state information for a virtual router interface."
    INDEX { vRtrID,
            vRtrIfIndex,
            vRtrIfDHCPLseStateCiAddr
          }
    ::= { vRtrIfDHCPLeaseStateTable 1 }

VRtrIfDHCPLeaseStateEntry ::=
    SEQUENCE {
        vRtrIfDHCPLseStateCiAddr        IpAddress,
        vRtrIfDHCPLseStateChAddr        MacAddress,
        vRtrIfDHCPLseStateRemainLseTime Unsigned32,
        vRtrIfDHCPLseStateOption82      OCTET STRING,
        vRtrIfDHCPLseStatePersistKey    Unsigned32
    }

vRtrIfDHCPLseStateCiAddr  OBJECT-TYPE
    SYNTAX      IpAddress
    MAX-ACCESS  not-accessible
    STATUS      obsolete
    DESCRIPTION
        "The value of the object vRtrIfDHCPLseStateCiAddr indicates the IP
         address of the DHCP lease state."
    ::= { vRtrIfDHCPLeaseStateEntry 1 }

vRtrIfDHCPLseStateChAddr  OBJECT-TYPE
    SYNTAX      MacAddress
    MAX-ACCESS  read-only
    STATUS      obsolete
    DESCRIPTION
        "The value of the object vRtrIfDHCPLseStateChAddr indicates the MAC
         address of the DHCP lease state."
    ::= { vRtrIfDHCPLeaseStateEntry 2 }

vRtrIfDHCPLseStateRemainLseTime  OBJECT-TYPE
    SYNTAX      Unsigned32
    MAX-ACCESS  read-only
    STATUS      obsolete
    DESCRIPTION
        "The value of the object vRtrIfDHCPLseStateRemainLseTime indicates the
         remaining lease time of the IP address of the DHCP lease state."
    ::= { vRtrIfDHCPLeaseStateEntry 3 }

vRtrIfDHCPLseStateOption82  OBJECT-TYPE
    SYNTAX      OCTET STRING
    MAX-ACCESS  read-only
    STATUS      obsolete
    DESCRIPTION "vRtrIfDHCPLseStateOption82 indicates the content of the
                 Option82 for this DHCP lease state."
    ::= { vRtrIfDHCPLeaseStateEntry 4 }

vRtrIfDHCPLseStatePersistKey  OBJECT-TYPE
    SYNTAX      Unsigned32
    MAX-ACCESS  read-only
    STATUS      obsolete
    DESCRIPTION
        "The value of the object vRtrIfDHCPLseStatePersistKey indicates a
         key value that can be used to track this lease state in the
         persistence file."
    ::= { vRtrIfDHCPLeaseStateEntry 5 }

--
--  Alcatel 7x50 SR series Virtual Router Interface IPv6 DHCP Relay Table
--
--  Augmentation of the vRtrIfTable.
--  Use of AUGMENTS clause implies a one-to-one dependent relationship
--  between the base table, vRtrIfTable, and the augmenting table,
--  vRtrIfDHCP6RelayTable. This in effect extends the vRtrIfTable with
--  additional columns. Creation (or deletion) of a row in the
--  vRtrIfTable results in the same fate for the row in the
--  vRtrIfDHCP6RelayTable.
--
vRtrIfDHCP6TableLastChanged  OBJECT-TYPE
    SYNTAX      TimeStamp
    MAX-ACCESS  read-only
    STATUS      current
    DESCRIPTION
        "The value of the object vRtrIfDHCP6TableLastChanged indicates
         the time of the last change to any row of vRtrIfDHCP6Table"
    ::= { tmnxVRtrObjs 35 }

vRtrIfDHCP6Table  OBJECT-TYPE
    SYNTAX      SEQUENCE OF VRtrIfDHCP6Entry
    MAX-ACCESS  not-accessible
    STATUS      current
    DESCRIPTION
        "The vRtrIfDHCP6Table is used to configure the interface parameters
         for the DHCP6 Relay agent."
    ::= { tmnxVRtrObjs 36 }

vRtrIfDHCP6Entry  OBJECT-TYPE
    SYNTAX      VRtrIfDHCP6Entry
    MAX-ACCESS  not-accessible
    STATUS      current
    DESCRIPTION
        "Each row entry represents information related to DHCP6 Relay for a
         virtual router interface in the system.

         Entries cannot be created and deleted via SNMP SET operations."
    AUGMENTS { vRtrIfEntry }
    ::= { vRtrIfDHCP6Table 1 }

VRtrIfDHCP6Entry ::=
    SEQUENCE {
        vRtrIfDHCP6LastChanged           TimeStamp,
        vRtrIfDHCP6AdminState            TmnxAdminState,
        vRtrIfDHCP6OperState             INTEGER,
        vRtrIfDHCP6Description           TItemDescription,
        vRtrIfDHCP6RelayServer1          InetAddressIPv6z,
        vRtrIfDHCP6RelayServer2          InetAddressIPv6z,
        vRtrIfDHCP6RelayServer3          InetAddressIPv6z,
        vRtrIfDHCP6RelayServer4          InetAddressIPv6z,
        vRtrIfDHCP6RelayServer5          InetAddressIPv6z,
        vRtrIfDHCP6RelayServer6          InetAddressIPv6z,
        vRtrIfDHCP6RelayServer7          InetAddressIPv6z,
        vRtrIfDHCP6RelayServer8          InetAddressIPv6z,
        vRtrIfDHCP6RelayItfIdOption      INTEGER,
        vRtrIfDHCP6LeasePopulate         Unsigned32,
        vRtrIfDHCP6CurrLeasePopulate     Unsigned32,
        vRtrIfDHCP6SourceAddress         InetAddressIPv6,
        vRtrIfDHCP6EnableNgbrResolution  TruthValue,
        vRtrIfDHCP6RemoteIdOption        TruthValue,
        vRtrIfDHCP6PfxdAdminState        INTEGER,
        vRtrIfDHCP6ServerMaxLeaseStates  Unsigned32,
        vRtrIfDHCP6CurrServerLeaseStates Unsigned32,
        vRtrIfDHCP6ItfIdString           DisplayString
        }

vRtrIfDHCP6LastChanged  OBJECT-TYPE
    SYNTAX      TimeStamp
    MAX-ACCESS  read-only
    STATUS      current
    DESCRIPTION
        "The value of the object vRtrIfDHCP6LastChanged indicates the time of
         the last change to this row of VRtrIfDHCP6Entry."
    ::= { vRtrIfDHCP6Entry 1 }

vRtrIfDHCP6AdminState  OBJECT-TYPE
    SYNTAX      TmnxAdminState
    MAX-ACCESS  read-create
    STATUS      current
    DESCRIPTION
        "The value of the object vRtrIfDHCP6AdminState specifies the desired
         administrative status of the DHCP6 relay agent on this interface.

         The value can only be set to inService if the value of vRtrIfType
         is serviceIesGroup.
         The value noop(3) is never allowed."
    DEFVAL { outOfService }
    ::= { vRtrIfDHCP6Entry 2 }

vRtrIfDHCP6OperState  OBJECT-TYPE
    SYNTAX      INTEGER {
                    up                 (1),
                    down               (2),
                    noIPv6Pfx          (3),
                    noServerConfigured (4),
                    noValidSourceAddr  (5)
                }
    MAX-ACCESS  read-only
    STATUS      current
    DESCRIPTION
        "The value of the object vRtrIfDHCP6OperState indicates the current
         operational state of the DHCP6 relay agent on this interface.
         Following value are possible:
         up (1)           - the DHCP6 relay agent is running.

         down (2),        - the DHCP6 relay agent is administratively disabled.

         noIPv6Pfx (3),   - the DHCP6 relay agent cannot be operational as
                            no ipv6 prefix is assigned to this link.

         noServerConfigured(4) - the DHCP6 relay agent cannot be operational
                                 as no DHCP6 servers are configured.
         noValidSourceAddr(5)  - the DHCP6 relay agent cannot be operational
                                 because a source address has been configured
                                 and the address is not local to this node."
    ::= { vRtrIfDHCP6Entry 3 }

vRtrIfDHCP6Description  OBJECT-TYPE
    SYNTAX      TItemDescription
    MAX-ACCESS  read-create
    STATUS      current
    DESCRIPTION
        "The value of the object vRtrIfDHCP6Description specifies a user
         provided description string for DHCP6 relay agent on this virtual
         router interface.
         It can consist of any printable, seven-bit ASCII characters up to
         80 characters in length."
    DEFVAL { ''H }      -- the empty string
    ::= { vRtrIfDHCP6Entry 4 }

vRtrIfDHCP6RelayServer1  OBJECT-TYPE
    SYNTAX      InetAddressIPv6z
    MAX-ACCESS  read-create
    STATUS      current
    DESCRIPTION
        "The value of the object vRtrIfDHCP6RelayServer1 specifies the first
         DHCP6 server where the DHCP6 requests will be forwarded to."
    DEFVAL { '0000000000000000000000000000000000000000'H }
    ::= { vRtrIfDHCP6Entry 5 }

vRtrIfDHCP6RelayServer2  OBJECT-TYPE
    SYNTAX      InetAddressIPv6z
    MAX-ACCESS  read-create
    STATUS      current
    DESCRIPTION
        "The value of the object vRtrIfDHCP6RelayServer2 specifies the 2nd
         DHCP6 server where the DHCP6 requests will be forwarded to."
    DEFVAL { '0000000000000000000000000000000000000000'H }
    ::= { vRtrIfDHCP6Entry 6 }

vRtrIfDHCP6RelayServer3  OBJECT-TYPE
    SYNTAX      InetAddressIPv6z
    MAX-ACCESS  read-create
    STATUS      current
    DESCRIPTION
        "The value of the object vRtrIfDHCP6RelayServer3 specifies the 3rd
         DHCP6 server where the DHCP6 requests will be forwarded to."
    DEFVAL { '0000000000000000000000000000000000000000'H }
    ::= { vRtrIfDHCP6Entry 7 }

vRtrIfDHCP6RelayServer4  OBJECT-TYPE
    SYNTAX      InetAddressIPv6z
    MAX-ACCESS  read-create
    STATUS      current
    DESCRIPTION
        "The value of the object vRtrIfDHCP6RelayServer4 specifies the 4rd
         DHCP6 server where the DHCP6 requests will be forwarded to."
    DEFVAL { '0000000000000000000000000000000000000000'H }
    ::= { vRtrIfDHCP6Entry 8 }

vRtrIfDHCP6RelayServer5  OBJECT-TYPE
    SYNTAX      InetAddressIPv6z
    MAX-ACCESS  read-create
    STATUS      current
    DESCRIPTION
        "The value of the object vRtrIfDHCP6RelayServer5 specifies the 5th
         DHCP6 server where the DHCP6 requests will be forwarded to."
    DEFVAL { '0000000000000000000000000000000000000000'H }
    ::= { vRtrIfDHCP6Entry 9 }

vRtrIfDHCP6RelayServer6  OBJECT-TYPE
    SYNTAX      InetAddressIPv6z
    MAX-ACCESS  read-create
    STATUS      current
    DESCRIPTION
        "The value of the object vRtrIfDHCP6RelayServer6 specifies the 6th
         DHCP6 server where the DHCP6 requests will be forwarded to."
    DEFVAL { '0000000000000000000000000000000000000000'H }
    ::= { vRtrIfDHCP6Entry 10 }

vRtrIfDHCP6RelayServer7  OBJECT-TYPE
    SYNTAX      InetAddressIPv6z
    MAX-ACCESS  read-create
    STATUS      current
    DESCRIPTION
        "The value of the object vRtrIfDHCP6RelayServer7 specifies the 7th
         DHCP6 server where the DHCP6 requests will be forwarded to."
    DEFVAL { '0000000000000000000000000000000000000000'H }
    ::= { vRtrIfDHCP6Entry 11 }

vRtrIfDHCP6RelayServer8  OBJECT-TYPE
    SYNTAX      InetAddressIPv6z
    MAX-ACCESS  read-create
    STATUS      current
    DESCRIPTION
        "The value of the object vRtrIfDHCP6RelayServer8 specifies the 8th
         DHCP6 server where the DHCP6 requests will be forwarded to."
    DEFVAL { '0000000000000000000000000000000000000000'H }
    ::= { vRtrIfDHCP6Entry 12 }

vRtrIfDHCP6RelayItfIdOption  OBJECT-TYPE
    SYNTAX      INTEGER {
                    none       (0),
                    ifIndex    (1),
                    asciiTuple (2),
                    sapId      (3),
                    string     (4)
                }
    MAX-ACCESS  read-create
    STATUS      current
    DESCRIPTION
        "The value of the object vRtrIfDHCP6RelayItfIdOption specifies whether
         or not the interface-id option is added by the DHCP6 relay agent,
         and, if it is present, what information goes in it.
         If the value of this object is set to 'none', the option is not added
         by the relay agent. In all other cases the option is added to the relay
         message. The content of the option is defined as follows:
         - 'ifIndex'    - the value of the interface index is used.
         - 'asciiTuple' - the ASCII-encoded concatenated tuple consisting of the
             - access-node-identifier
             - service-id
             - interface-name
             - SAP-id (only if the value of vRtrIfType is 'serviceIesGroup')
         - 'sapId'      - the ASCII-encoded SAP-id is used.
         - 'string'     - the value of the object vRtrIfDHCP6ItfIdString
                          is used.
        "
    DEFVAL { none }
    ::= { vRtrIfDHCP6Entry 13 }

vRtrIfDHCP6LeasePopulate  OBJECT-TYPE
    SYNTAX      Unsigned32 (0..8000)
    MAX-ACCESS  read-create
    STATUS      current
    DESCRIPTION
        "The value of the object vRtrIfDHCP6LeasePopulate specifies the
         maximum number of lease states allocated by the DHCP6 relay function,
         allowed on this interface."
    DEFVAL { 0 }
    ::= { vRtrIfDHCP6Entry 14 }

vRtrIfDHCP6CurrLeasePopulate  OBJECT-TYPE
    SYNTAX      Unsigned32 (0..8000)
    MAX-ACCESS  read-only
    STATUS      current
    DESCRIPTION
        "The value of the object vRtrIfDHCP6CurrLeasePopulate indicates the
         number of lease states currently allocated on this interface by
         the DHCP6 relay function."
    ::= { vRtrIfDHCP6Entry 15 }

vRtrIfDHCP6SourceAddress OBJECT-TYPE
    SYNTAX      InetAddressIPv6
    MAX-ACCESS  read-create
    STATUS      current
    DESCRIPTION
        "The value of the object vRtrIfDHCP6SourceAddress specifies the ipv6
         address that will be used by the DHCP6 relay agent as source IP
         address in all messages sent to the DHCP6 servers.
         If set to ::, the system will use the IPv6 address assigned on the
         link on which the relay message is sent out, if such an address is
         defined. As a last resort the system Ipv6 address is taken."
    DEFVAL { '00000000000000000000000000000000'H }
    ::= { vRtrIfDHCP6Entry 16 }

vRtrIfDHCP6EnableNgbrResolution  OBJECT-TYPE
    SYNTAX      TruthValue
    MAX-ACCESS  read-create
    STATUS      current
    DESCRIPTION
        "The value of the object vRtrIfDHCP6EnableNgbrResolution specifies
         whether or not neighbor resolution via DHCP6 Relay must be enabled
         on this interface.
         This feature is similar to the arp-populate feature in ipv4."
    DEFVAL { false }
    ::= { vRtrIfDHCP6Entry 17 }

vRtrIfDHCP6RemoteIdOption  OBJECT-TYPE
    SYNTAX      TruthValue
    MAX-ACCESS  read-create
    STATUS      current
    DESCRIPTION
        "The value of the object vRtrIfDHCP6RemoteIdOption specifies
         whether or not the remote Id option is sent to the DHCP6 server.
         The client DUID is used as remoteId."
    DEFVAL { false }
    ::= { vRtrIfDHCP6Entry 18 }

vRtrIfDHCP6PfxdAdminState  OBJECT-TYPE
    SYNTAX      INTEGER {
                    enabled (1),
                    disabled(2)
                }
    MAX-ACCESS  read-create
    STATUS      current
    DESCRIPTION
        "The value of the object vRtrIfDHCP6PfxdAdminState specifies the
         administrative state of the row. If set to enabled, this
         IPv6 prefix will be delegated by the system."
    DEFVAL { disabled }
    ::= { vRtrIfDHCP6Entry 19 }

vRtrIfDHCP6ServerMaxLeaseStates  OBJECT-TYPE
    SYNTAX      Unsigned32 (0..8000)
    MAX-ACCESS  read-create
    STATUS      current
    DESCRIPTION
        "The value of the object vRtrIfDHCP6ServerMaxLeaseStates specifies
         the maximum number of lease states installed by the DHCP6 server
         function allowed on this interface."
    DEFVAL { 8000 }
    ::= { vRtrIfDHCP6Entry 20 }

vRtrIfDHCP6CurrServerLeaseStates OBJECT-TYPE
    SYNTAX      Unsigned32 (0..8000)
    MAX-ACCESS  read-only
    STATUS      current
    DESCRIPTION
        "The value of the object vRtrIfDHCP6CurrServerLeaseStates indicates the
         number of lease states currently allocated on this interface
         by the DHCP6 server function."
    ::= { vRtrIfDHCP6Entry 21 }

vRtrIfDHCP6ItfIdString  OBJECT-TYPE
    SYNTAX      DisplayString (SIZE(0..80))
    MAX-ACCESS  read-create
    STATUS      current
    DESCRIPTION
        "The value of the object vRtrIfDHCP6ItfIdString specifies the string
         that will be put in the interface-id option added by the relay agent.
         This value is only meaningful if the object vRtrIfDHCP6RelayItfIdOption
         is set to string(4)."
    ::= { vRtrIfDHCP6Entry 22 }

--
-- Alcatel 7x50 SR series Virtual Router Interface Name to vRtrIfIndex Mapping
-- Table
--

vRtrIfNameTable OBJECT-TYPE
    SYNTAX      SEQUENCE OF VRtrIfNameEntry
    MAX-ACCESS  not-accessible
    STATUS      current
    DESCRIPTION
        "This is a read-only table, each row of which represents a one to
         one equivalence between a router interface name (vRtrIfName)
         and its corresponding index in the vRtrIfTable (vRtrIfIndex)."
    ::= { tmnxVRtrObjs 5}

vRtrIfNameEntry OBJECT-TYPE
    SYNTAX      VRtrIfNameEntry
    MAX-ACCESS  not-accessible
    STATUS      current
    DESCRIPTION
        "Each row entry in the vRtrIfNameTable corresponds to a row
         in the vRtrIfTable. When an entry is created or deleted in the
         vRtrIfTable, a corresponding entry is created or deleted in this
         table."
    INDEX { vRtrID, IMPLIED vRtrIfName }
    ::= { vRtrIfNameTable 1 }

VRtrIfNameEntry ::=
    SEQUENCE {
        vRtrIfNameIndex                 InterfaceIndex
             }

vRtrIfNameIndex  OBJECT-TYPE
    SYNTAX      InterfaceIndex
    MAX-ACCESS  read-only
    STATUS      current
    DESCRIPTION
        "The value of vRtrIfNameIndex gives the value of vRtrIfIndex
         for a row in the vRtrIfTable. This row corresponds to the
         virtual router interface which has interface name as vRtrIfName.
         Every vRtrIfName is unique within a specific instance of vRtrID."
    ::= { vRtrIfNameEntry 1 }


--
-- Virtual Router IP Address Table
--

vRtrIpAddrTable OBJECT-TYPE
    SYNTAX      SEQUENCE OF VRtrIpAddrEntry
    MAX-ACCESS  not-accessible
    STATUS      current
    DESCRIPTION
        "The vRtrIpAddrTable has an entry for each IP address configured
         for a virtual router in the system.  An interface on the
         virtual router may have more than one IP address assigned to
         it."
    ::= { tmnxVRtrObjs 6 }

vRtrIpAddrEntry  OBJECT-TYPE
    SYNTAX      VRtrIpAddrEntry
    MAX-ACCESS  not-accessible
    STATUS      current
    DESCRIPTION
        "Each row entry represents an IP address assigned a virtual
         router interface.  Entries can be created and deleted via
         SNMP SET operations.  Setting RowStatus to 'active' requires
         a values for all column variables to have been assigned."
    INDEX { vRtrID, vRtrIfIndex, vRiaIndex }
    ::= { vRtrIpAddrTable 1 }

VRtrIpAddrEntry ::=
    SEQUENCE {
        vRiaIndex                  INTEGER,
        vRiaRowStatus              RowStatus,
        vRiaIpAddress              IpAddress,
        vRiaNetMask                IpAddress,
        vRiaBcastAddrFormat        INTEGER,
        vRiaReasmMaxSize           INTEGER,
        vRiaIgpInhibit             TruthValue,
        vRiaInetAddressType        InetAddressType,
        vRiaInetAddress            InetAddress,
        vRiaInetPrefixLen          InetAddressPrefixLength,
        vRiaInetAddrState          TmnxInetAddrState,
        vRiaInetEui64              TruthValue,
        vRiaInetOperAddress        InetAddress,
        vRiaInetGwAddressType      InetAddressType,
        vRiaInetGwAddress          InetAddress,
        vRiaInetRemoteIpType       InetAddressType,
        vRiaInetRemoteIp           InetAddress
        }

vRiaIndex OBJECT-TYPE
    SYNTAX      INTEGER (1..16)
    MAX-ACCESS  not-accessible
    STATUS      current
    DESCRIPTION
        "The unique value which identifies this IP address entry for
         this interface of this virtual router in the Tmnx system.
         Those row entries with vRiaIndex = 1 represent the primary
         IP address for the interface identified by the vRtrID and
         vRtrIfIndex pair.  Row entries with other values for vRiaIndex
         are secondary IP addresses.  There must always be a primary
         IP address assigned an interface.  This implies that if the
         primary address row is deleted, the secondary rows are also
         deleted."
    ::= { vRtrIpAddrEntry 1 }

vRiaRowStatus  OBJECT-TYPE
    SYNTAX      RowStatus
    MAX-ACCESS  read-create
    STATUS      current
    DESCRIPTION
        "The row status used for creation, deletion, or control
         of vRtrIpAddrTable entries.  All the other row variables
         must have been assigned values before the row can be
         place into the 'active' state."
    ::= { vRtrIpAddrEntry 2 }

vRiaIpAddress  OBJECT-TYPE
    SYNTAX      IpAddress
    MAX-ACCESS  read-create
    STATUS      current
    DESCRIPTION
        "The IP address assigned to a router's interface."
    ::= { vRtrIpAddrEntry 3 }

vRiaNetMask  OBJECT-TYPE
    SYNTAX      IpAddress
    MAX-ACCESS  read-create
    STATUS      current
    DESCRIPTION
        "The subnet mask associated with the IP address of this
         entry.  The value of the mask is an IP address with all
         the network bits set to 1 and all the host bits set to
         0."
    DEFVAL  { 'FFFFFF00'H } -- 255.255.255.0
    ::= { vRtrIpAddrEntry 4 }

vRiaBcastAddrFormat  OBJECT-TYPE
    SYNTAX      INTEGER {
                    allOnes (1),
                    hostOnes (2)
                }
    MAX-ACCESS  read-create
    STATUS      current
    DESCRIPTION
        "When vRiaBcastAddrFormat is set to 'allOnes', the
         255.255.255.255 address is used for local broadcast.
         When vRiaBcastAddrFormat is set to 'hostOnes', the
         <prefix>-1 address is used for the local broadcast.
         For example for subnet 10.10.16.0/20 the <prefix>-1
         address is 10.10.31.255."
    DEFVAL { hostOnes }
    ::= { vRtrIpAddrEntry 5 }

vRiaReasmMaxSize  OBJECT-TYPE
    SYNTAX      INTEGER (0..65535)
    MAX-ACCESS  read-create
    STATUS      current
    DESCRIPTION
        "The size of the largest IP datagram which this entry
         can reassemble from incoming IP fragmented datagrams
         received on this interface."
    ::= { vRtrIpAddrEntry 6 }

vRiaIgpInhibit  OBJECT-TYPE
    SYNTAX      TruthValue
    MAX-ACCESS  read-create
    STATUS      current
    DESCRIPTION
        "This variable should only be associated with secondary
         ip addresses, i.e., when the value of vRiaIndex is other
         than 1. When vRiaIgpInhibit has a value of 'true',
         it indicates that the given secondary IP address should
         not be recognized as a local interface by the running IGP.
         For OSPF and IS-IS, this means that the given secondary
         IP addresses will not be injected as passive interfaces
         and will not be advertised as internal IP interfaces into
         the IGP's link state database.  For RIP this means these
         secondary IP interfaces will not source RIP updates."
    ::= { vRtrIpAddrEntry 7 }

vRiaInetAddressType  OBJECT-TYPE
    SYNTAX      InetAddressType
    MAX-ACCESS  read-create
    STATUS      current
    DESCRIPTION
        "vRiaInetAddressType specifies the type of the
         vRiaInetAddress address assigned to a router's interface."
    ::= { vRtrIpAddrEntry 8 }

vRiaInetAddress  OBJECT-TYPE
    SYNTAX      InetAddress (SIZE(0|4|16))
    MAX-ACCESS  read-create
    STATUS      current
    DESCRIPTION
        "The type of this address is determined by the value of
         the vRiaInetAddressType object.

         vRiaInetAddress indicates the IPv4/IPv6 address assigned
         to a router's interface."
    ::= { vRtrIpAddrEntry 9 }

vRiaInetPrefixLen  OBJECT-TYPE
    SYNTAX      InetAddressPrefixLength
    MAX-ACCESS  read-create
    STATUS      current
    DESCRIPTION
        "The value of vRiaInetPrefixLen specifies the length of
         the IP netmask for this interface address."
    ::= { vRtrIpAddrEntry 10 }

vRiaInetAddrState  OBJECT-TYPE
    SYNTAX      TmnxInetAddrState
    MAX-ACCESS  read-only
    STATUS      current
    DESCRIPTION
        "The value of vRiaInetAddrState indicates the address
         state of the IPv6 address of the interface."
    ::= { vRtrIpAddrEntry 11 }

vRiaInetEui64   OBJECT-TYPE
    SYNTAX      TruthValue
    MAX-ACCESS  read-create
    STATUS      current
    DESCRIPTION
        "The value of vRiaInetEui64 specifies whether the
         vRiaInetOperAddress is an eui64 address.  This object
         can only be set at creation time.

         When vRiaInetEui64 is 'true', then the vRiaInetOperAddress
         is derived from the vRiaInetAddress and the physical address
         of the interface this address is attached to.  vRiaInetAddress
         has to have all zeros the least significant 8 bytes. Also,
         vRiaInetPrefixLen cannot be longer than 64.

         When vRiaInetEui64 is 'false', then the vRiaInetOperAddress
         is a copy of vRiaInetAddress.  The value is always 'false' when
         vRiaInetAddressType is not 'ipv6'."
    DEFVAL { false }
    ::= { vRtrIpAddrEntry 12 }

vRiaInetOperAddress     OBJECT-TYPE
    SYNTAX      InetAddress
    MAX-ACCESS  read-only
    STATUS      current
    DESCRIPTION
        "The value of vRiaInetOperAddress indicates the operational
         address of this entry.  The type of this address is determined
         by the value of the vRiaInetAddressType object."
    ::= { vRtrIpAddrEntry 13 }

vRiaInetGwAddressType   OBJECT-TYPE
    SYNTAX      InetAddressType
    MAX-ACCESS  read-create
    STATUS      current
    DESCRIPTION
        "The value of vRiaInetGwAddressType specifies the address type
         of vRiaInetGwAddress."
    DEFVAL { unknown }
    ::= { vRtrIpAddrEntry 14 }

vRiaInetGwAddress       OBJECT-TYPE
    SYNTAX      InetAddress (SIZE(0|4|16))
    MAX-ACCESS  read-create
    STATUS      current
    DESCRIPTION
        "The value of vRiaInetGwAddress specifies the gateway address
         for the subnet specified by vRiaInetAddress and vRiaInetPrefixLen.
         The address type is defined by vRiaInetGwAddressType. This field
         is only valid when the address is configured on a subscriber
         interface."
    DEFVAL { ''H }
    ::= { vRtrIpAddrEntry 15 }

vRiaInetRemoteIpType    OBJECT-TYPE
    SYNTAX      InetAddressType
    MAX-ACCESS  read-create
    STATUS      current
    DESCRIPTION
        "The value of vRiaInetRemoteIpType specifies the address type
         of vRiaInetRemoteIp."
    DEFVAL { unknown }
    ::= { vRtrIpAddrEntry 16 }

vRiaInetRemoteIp        OBJECT-TYPE
    SYNTAX      InetAddress (SIZE(0|4|16))
    MAX-ACCESS  read-create
    STATUS      current
    DESCRIPTION
        "The value of vRiaInetRemoteIp specifies the IP address of the remote
         redundant interface. This field is only valid when the address is
         configured on a redundant interface."
    DEFVAL { ''H }
    ::= { vRtrIpAddrEntry 17 }

--
--  Augmentation of the IP-FORWARD-MIB ipCidrRouteTable.
--  Use of AUGMENTS clause implies a one-to-one dependent relationship between
--  the base table, ipCidrRouteTable, and the augmenting table,
--  vRtrIpCidrRouteTable.  This in effect extends the ipCidrRouteTable with
--  additional columns.  Creation (or deletion) of a row in the
--  ipCidrRouteTable results in the same fate for the row in the
--  vRtrIpCidrRouteTable.
--

vRtrIpCidrRouteTable  OBJECT-TYPE
    SYNTAX      SEQUENCE OF VRtrIpCidrRouteEntry
    MAX-ACCESS  not-accessible
    STATUS      current
    DESCRIPTION
        "The vRtrIpCidrRouteTable provides an extension of the ipCidrRouteTable
         in the IP-FORWARD-MIB."
    ::= { tmnxVRtrObjs 7 }

vRtrIpCidrRouteEntry  OBJECT-TYPE
    SYNTAX      VRtrIpCidrRouteEntry
    MAX-ACCESS  not-accessible
    STATUS      current
    DESCRIPTION
        "Each row entry in the vRtrIpCidrRouteTable represents additional
         columns for attributes specific to the Alcatel 7x50 SR series
         implementation for the IP route table."
   AUGMENTS { ipCidrRouteEntry }
   ::= { vRtrIpCidrRouteTable 1 }

VRtrIpCidrRouteEntry ::=
    SEQUENCE {
        vRtrIpCidrRouteLastEnabledTime   TimeStamp,
        vRtrIpCidrRoutePreference        Unsigned32,
        vRtrIpCidrRouteMetric            Unsigned32
        }

vRtrIpCidrRouteLastEnabledTime  OBJECT-TYPE
    SYNTAX      TimeStamp
    MAX-ACCESS  read-only
    STATUS      current
    DESCRIPTION
        "The vRtrIpCidrRouteLastEnabledTime variable contains the sysUpTime
         value when ipCidrRouteStatus was last set to active (1) to
         allow IP forwarding on this route entry."
    ::= { vRtrIpCidrRouteEntry 1 }


vRtrIpCidrRoutePreference  OBJECT-TYPE
    SYNTAX      Unsigned32 (0..255)
    MAX-ACCESS  read-create
    STATUS      current
    DESCRIPTION
        "When ipCidrRouteProto has a value of 'netmgmt' to indicate that
         this entry is a static route, the value of
         vRtrIpCidrRoutePreference determines the priority of this
         static route versus the routes from different sources such as
         BGP or OSPF etc.

         Different protocols should not be configured with the same
         preference, if this occurs the tiebreaker is determined per the
         default preference value as defined in the table below.

         If multiple routes are learned with an identical preference
         using the same protocol, the lowest cost is used. If multiple
         routes are learned with an identical preference using the same
         protocol and the costs (metrics) are equal, then the decision
         as to what route to use is determined by the configuration of
         the ecmp command.

         Default preferences:

         Route Type             Preference      Configurable
         ----------             ----------      ------------
         Direct attached                 0                no
         Static-route                    5               yes
         MPLS (post FCS)                 7
         OSPF Internal routes           10                no
         OSPF External                 150               yes
         BGP                           170               yes
         "
    DEFVAL { 5 }
    ::= { vRtrIpCidrRouteEntry 2 }

vRtrIpCidrRouteMetric  OBJECT-TYPE
    SYNTAX      Unsigned32
    MAX-ACCESS  read-only
    STATUS      current
    DESCRIPTION
        "The primary routing metric  for this route. The semantics
         of this metric are determined by the routing-protocol specified
         in the route's ipCidrRouteProto value."
    ::= { vRtrIpCidrRouteEntry 3 }


--  Virtual router Static Route Table

--  The Virtual router Static Route Table maintains both active and inactive
--  static routes that have been configured by the network manager.
--  It adds knowledge of the autonomous system of the next hop, multiple
--  next hops, and policy routing, and Classless Inter-Domain Routing.
--  Active entries are also represented in the IP-FORWARD-MIB ipCidrTable.

vRtrStaticRouteNumber  OBJECT-TYPE
    SYNTAX      Unsigned32
    MAX-ACCESS  read-only
    STATUS      current
    DESCRIPTION
       "The number of current vRtrStaticRouteTable entries that are 'active'."
    ::= { tmnxVRtrObjs 8 }

vRtrStaticRouteTable  OBJECT-TYPE
    SYNTAX      SEQUENCE OF VRtrStaticRouteEntry
    MAX-ACCESS  not-accessible
    STATUS      current
    DESCRIPTION
       "This entity's Static Routing table."
    ::= { tmnxVRtrObjs 9 }

vRtrStaticRouteEntry OBJECT-TYPE
    SYNTAX      VRtrStaticRouteEntry
    MAX-ACCESS  not-accessible
    STATUS      current
    DESCRIPTION
       "A particular route to  a  particular  destination, through a
        particular next hop."
    INDEX {
        vRtrID,
        vRtrStaticRouteDest,
        vRtrStaticRouteMask,
        vRtrStaticRouteIndex
        }
    ::= { vRtrStaticRouteTable 1 }

VRtrStaticRouteEntry ::=
    SEQUENCE {
        vRtrStaticRouteDest                     IpAddress,
        vRtrStaticRouteMask                     IpAddress,
        vRtrStaticRouteIndex                    INTEGER,
        vRtrStaticRouteRowStatus                RowStatus,
        vRtrStaticRouteLastEnabledTime          TimeStamp,
        vRtrStaticRouteStatus                   INTEGER,
        vRtrStaticRouteStaticType               INTEGER,
        vRtrStaticRoutePreference               Unsigned32,
        vRtrStaticRouteMetric                   Unsigned32,
        vRtrStaticRouteEgressIfIndex            InterfaceIndexOrZero,
        vRtrStaticRouteNextHop                  IpAddress,
        vRtrStaticRouteNextHopUnnumberedIf      DisplayString,
        vRtrStaticRouteAdminState               TmnxAdminState,
        vRtrStaticRouteIgpShortcut              BITS,
        vRtrStaticRouteDisallowIgp              TruthValue,
        vRtrStaticRouteTag                      Unsigned32
    }

vRtrStaticRouteDest  OBJECT-TYPE
    SYNTAX      IpAddress
    MAX-ACCESS  read-only
    STATUS      current
    DESCRIPTION
       "The destination IP address of this route.
        This object may not take a Multicast (Class  D) address value.

        Any assignment (implicit or  otherwise) of an instance of this object to
        a value x must be rejected if the bitwise logical-AND of x with the
        value of the corresponding instance of the vRtrStaticRouteMask object
        is not equal to x."
    ::= { vRtrStaticRouteEntry 1 }

vRtrStaticRouteMask  OBJECT-TYPE
    SYNTAX      IpAddress
    MAX-ACCESS  read-only
    STATUS      current
    DESCRIPTION
       "Indicate the mask to be logical-ANDed  with  the  destination  address
        before  being compared to the value  in  the  vRtrStaticRouteDest field.
        For those  systems  that  do  not support arbitrary subnet masks, an
        agent constructs the value  of the  vRtrStaticRouteMask  by  reference
        to the IP Address Class.

        Any assignment (implicit or  otherwise)  of  an instance of this object
        to a value x must be rejected if the bitwise logical-AND of x with the
        value of the corresponding instance of the vRtrStaticRouteDest object is
        not equal to vRtrStaticRouteDest."
    ::= { vRtrStaticRouteEntry 2 }

vRtrStaticRouteIndex  OBJECT-TYPE
    SYNTAX      INTEGER (1..2147483647)
    MAX-ACCESS  read-only
    STATUS      current
    DESCRIPTION
       "The quaternary index for the vRtrStaticRouteTable."
    ::= { vRtrStaticRouteEntry 3 }

vRtrStaticRouteRowStatus  OBJECT-TYPE
    SYNTAX      RowStatus
    MAX-ACCESS  read-create
    STATUS      current
    DESCRIPTION
       "The row status variable, used according to
        row installation and removal conventions."
    ::= { vRtrStaticRouteEntry 4 }

vRtrStaticRouteLastEnabledTime  OBJECT-TYPE
    SYNTAX      TimeStamp
    MAX-ACCESS  read-only
    STATUS      current
    DESCRIPTION
        "The vRtrStaticRouteLastEnabledTime variable contains the sysUpTime
         value when vRtrStaticRouteStatus was last set to active (1) to
         allow IP forwarding on this static route entry."
    ::= { vRtrStaticRouteEntry 5 }

vRtrStaticRouteStatus  OBJECT-TYPE
    SYNTAX      INTEGER {
                    active   (1),
                    inactive (2)
                }
    MAX-ACCESS  read-only
    STATUS      current
    DESCRIPTION
        "The value of vRtrStaticRouteStatus indicates whether or not this
         route entry is active in the system.  When an interface
         transitions to the down state, any associated route entries
         are marked as 'inactive' and are usually not displayed in a
         standard route table listing.  When the interface transitions
         to the up state, the agent marks the associated routes as
         'active'"
    ::= { vRtrStaticRouteEntry 6 }

vRtrStaticRouteStaticType  OBJECT-TYPE
    SYNTAX      INTEGER {
                    unknown (0),
                    nextHop (1),
                    indirect (2),
                    blackHole (3)
                }
    MAX-ACCESS  read-create
    STATUS      current
    DESCRIPTION
        "The value of vRtrStaticRouteStaticType indicates the
         type of static route represented by this row entry."
    DEFVAL { unknown }
    ::= { vRtrStaticRouteEntry 7 }

vRtrStaticRoutePreference  OBJECT-TYPE
    SYNTAX      Unsigned32 (1..256)
    MAX-ACCESS  read-create
    STATUS      current
    DESCRIPTION
        "The value of vRtrStaticRoutePreference determines the priority
         of this static route versus the routes from different sources
         such as BGP or OSPF etc.

         Different protocols should not be configured with the same
         preference, if this occurs the tiebreaker is determined per the
         default preference value as defined in the table below.

         If multiple routes are learned with an identical preference
         using the same protocol, the lowest cost is used. If multiple
         routes are learned with an identical preference using the same
         protocol and the costs (metrics) are equal, then the decision
         as to what route to use is determined by the configuration of
         the ecmp command.

         Default preferences.


         Route Type             Preference      Configurable
         ----------             ----------      ------------
         Direct attached                 0                no
         Static-route                    5               yes
         MPLS (post FCS)                 7
         OSPF Internal routes           10                no
         OSPF External                 150               yes
         BGP                           170               yes
         "
    DEFVAL { 5 }
    ::= { vRtrStaticRouteEntry 8 }

vRtrStaticRouteMetric  OBJECT-TYPE
    SYNTAX      Unsigned32 (0..65535)
    MAX-ACCESS  read-create
    STATUS      current
    DESCRIPTION
        "When ipCidrRouteProto has a value of 'netmgmt' to indicate that
         this entry is a static route, the value of vRtrStaticRouteMetric
         associates a metric value with the route. This value is used
         when importing this static route into other protocols such as
         OSPF.  When the metric is configured as zero then the metric
         configured in OSPF, default-import-metric, applies.  This value
         is also used to determine which static route to install in the
         forwarding table:

         If there are multiple static routes with the same preference
         but unequal metric then the lower cost (metric) route will be
         installed.

         If there are multiple static routes with equal preference and
         metrics then ecmp rules apply.

         If there are multiple routes with unequal preference then the
         lower preference route will be installed.
         "
    DEFVAL { 1 }
    ::= { vRtrStaticRouteEntry 9 }

vRtrStaticRouteEgressIfIndex  OBJECT-TYPE
    SYNTAX      InterfaceIndexOrZero
    MAX-ACCESS  read-only
    STATUS      current
    DESCRIPTION
        "The outgoing ifIndex for this route as computed by the
         static-route module. This variable will have a value of 0
         if vRtrStaticRouteStatus is 'inactive' or if this static
         route is configured as a black hole."
    ::= { vRtrStaticRouteEntry 11 }

vRtrStaticRouteNextHop  OBJECT-TYPE
    SYNTAX      IpAddress
    MAX-ACCESS  read-create
    STATUS      current
    DESCRIPTION
        "In case of remote routes, the address of the next system en route.
         This member is complemented by vRtrStaticRouteNextHopUnnumberedIf.
         Atmost only one of them can be non-null. If vRtrStaticRouteNextHop
         is '0.0.0.0' and vRtrStaticRouteNextHopUnnumberedIf is a null
         string then this static route is configured as a black hole."
    ::= { vRtrStaticRouteEntry 12 }

vRtrStaticRouteNextHopUnnumberedIf  OBJECT-TYPE
    SYNTAX      DisplayString (SIZE(0..32))
    MAX-ACCESS  read-create
    STATUS      current
    DESCRIPTION
            "The name of the unnumbered Interface which will be the nexthop for
             this route. This member is complemented by vRtrStaticRouteNextHop.

             Atmost only one of them can be non-null. If vRtrStaticRouteNextHop
             is '0.0.0.0' and vRtrStaticRouteNextHopUnnumberedIf is a null
             string then this static route is configured as a black hole."
    ::= { vRtrStaticRouteEntry 13 }

vRtrStaticRouteAdminState  OBJECT-TYPE
    SYNTAX      TmnxAdminState
    MAX-ACCESS  read-create
    STATUS      current
    DESCRIPTION
        "The desired administrative state for this virtual router static route"
    DEFVAL { inService }
    ::= { vRtrStaticRouteEntry 14 }

vRtrStaticRouteIgpShortcut  OBJECT-TYPE
    SYNTAX      BITS {
                    te(0),
                    ldp(1),
                    ip(2)
                }
    MAX-ACCESS  read-create
    STATUS      current
    DESCRIPTION
        "The value of vRtrStaticRouteIgpShortcut is valid only for indirect
         static routes (i.e. vRtrStaticRouteStaticType is 'indirect'). The
         bits of vRtrStaticRouteIgpShortcut identify Layer 2 tunneling
         mechanisms used for IGP shortcuts. If a bit is set, IGP shortcuts
         associated with that tunneling mechanism will be used to resolve
         next-hop for the static-route. If no bits are set, IGP shortcuts
         will not be used to resolve next-hop for the static routes.

         The tunneling mechanisms represented by each bit are:
           te(0)  - RSVP Traffic Engineering
           ldp(1) - LDP /32 Route Forwarding Equivalence Class (FEC)
           ip(2)  - IP (IP-in-IP or GRE)

         Evaluation of tunnel preference is based on the following order, in
         descending priority:
           1. Traffic Engineered Shortcut (RSVP-TE)
           2. LDP /32 Route FEC Shortcut
           3. IP Shortcut (IP-in-IP or GRE)
           4. Actual IGP Next-Hop."
    DEFVAL { { } }
    ::= { vRtrStaticRouteEntry 15 }

vRtrStaticRouteDisallowIgp  OBJECT-TYPE
    SYNTAX      TruthValue
    MAX-ACCESS  read-create
    STATUS      current
    DESCRIPTION
        "The value of vRtrStaticRouteDisallowIgp is valid only for indirect
         static routes (i.e. vRtrStaticRouteStaticType is 'indirect'). If
         the value of vRtrStaticRouteDisallowIgp is set to 'true', and if
         none of the defined tunneling mechanisms (RSVP-TE, LDP or IP)
         qualify as a next-hop, the normal IGP next-hop to the indirect
         next-hop address will not be used. If the value is set to 'false',
         IGP next-hop to the indirect next-hop address can be used as the
         next-hop of the last resort."
    DEFVAL { false }
    ::= { vRtrStaticRouteEntry 16 }

vRtrStaticRouteTag  OBJECT-TYPE
    SYNTAX      Unsigned32 (0..4294967295)
    MAX-ACCESS  read-create
    STATUS      current
    DESCRIPTION
        "The value of vRtrStaticRouteTag is used to add a 32-bit integer tag
         to the static route. This tag could then be used in route policies
         to control distribution of the route into other protocols. A value
         of 0 indicates that the tag has not been set."
    DEFVAL { 0 }
    ::= { vRtrStaticRouteEntry 17 }

--
--  Virtual Router Service Interface IP Address Range table
--
vRtrSvcIpRangeTable  OBJECT-TYPE
    SYNTAX      SEQUENCE OF VRtrSvcIpRangeEntry
    MAX-ACCESS  not-accessible
    STATUS      current
    DESCRIPTION
        "The vRtrSvcIpRangeTable has an entry for each IP address
         range configured for a virtual interface in a virtual router
         in the system.  An interface on the virtual router may have
         more than one Service IP address ranges assigned to it."
    ::= { tmnxVRtrObjs 10 }

vRtrSvcIpRangeEntry  OBJECT-TYPE
    SYNTAX      VRtrSvcIpRangeEntry
    MAX-ACCESS  not-accessible
    STATUS      current
    DESCRIPTION
        "Each row entry represents an IP address range assigned a
         virtual router service interface.  Entries can be created
         and deleted via SNMP SET operations.  Setting RowStatus to
         'active' requires values for all column variables to have
         been assigned."
    INDEX { vRtrID, vRtrSvcIpRangeAddress, vRtrSvcIpRangeMask }
    ::= { vRtrSvcIpRangeTable 1 }

VRtrSvcIpRangeEntry ::=
    SEQUENCE {
        vRtrSvcIpRangeAddress    IpAddress,
        vRtrSvcIpRangeMask       Unsigned32,
        vRtrSvcIpRangeRowStatus  RowStatus,
        vRtrSvcIpRangeExclusive  TruthValue
    }

vRtrSvcIpRangeAddress  OBJECT-TYPE
    SYNTAX      IpAddress
    MAX-ACCESS  read-create
    STATUS      current
    DESCRIPTION
        "The IP address prefix range assigned to a router's service
         interface."
    ::= { vRtrSvcIpRangeEntry 1 }

vRtrSvcIpRangeMask  OBJECT-TYPE
    SYNTAX      Unsigned32 (0..32)
    MAX-ACCESS  read-create
    STATUS      current
    DESCRIPTION
        "The subnet mask associated with the Service IP address of this
         entry.  The value of the mask is an 32-bit integer with all
         the network bits set to 1 and all the host bits set to 0."
    ::= { vRtrSvcIpRangeEntry 2 }

vRtrSvcIpRangeRowStatus  OBJECT-TYPE
    SYNTAX      RowStatus
    MAX-ACCESS  read-create
    STATUS      current
    DESCRIPTION
        "The row status used for creation, deletion, or control
         of vRtrSvcIpRangeTable entries."
    ::= { vRtrSvcIpRangeEntry 3 }

vRtrSvcIpRangeExclusive  OBJECT-TYPE
    SYNTAX      TruthValue
    MAX-ACCESS  read-create
    STATUS      current
    DESCRIPTION
        "When vRtrSvcIpRangeExclusive has a value of 'true', this
         set of addresses is reserved for services only and cannot be
         assigned to network ports.  When it has a value of 'false',
         it could be used for services as well as network ports."
    DEFVAL { false }
    ::= { vRtrSvcIpRangeEntry 4 }

--
--  Augmentation of the IP-MIB ipNetToMediaTable.
--  Use of AUGMENTS clause implies a one-to-one dependent relationship between
--  the base table, ipNetToMediaTable, and the augmenting table,
--  vRtrIpNetToMediaTable.  This in effect extends the ipNetToMediaTable with
--  additional columns.  Creation (or deletion) of a row in the
--  ipNetToMediaTable results in the same fate for the row in the
--  vRtrIpNetToMediaTable.
--

vRtrIpNetToMediaTable  OBJECT-TYPE
    SYNTAX      SEQUENCE OF VRtrIpNetToMediaEntry
    MAX-ACCESS  not-accessible
    STATUS      current
    DESCRIPTION
        "The vRtrIpNetToMediaTable provides an extension of the
         ipNetToMediaTable in the IP-MIB."
    ::= { tmnxVRtrObjs 11 }

vRtrIpNetToMediaEntry  OBJECT-TYPE
    SYNTAX      VRtrIpNetToMediaEntry
    MAX-ACCESS  not-accessible
    STATUS      current
    DESCRIPTION
        "Each row entry in the vRtrIpNetToMediaTable represents additional
         columns for attributes specific to the Alcatel 7x50 SR series
         implementation for the vRtrIpNetToMediaTable."
   AUGMENTS { ipNetToMediaEntry }
   ::= { vRtrIpNetToMediaTable 1 }

VRtrIpNetToMediaEntry ::=
    SEQUENCE {
        vRtrIpNetToMediaTimer        Unsigned32,
        vRtrIpNetToMediaOperState    TmnxOperState
        }

vRtrIpNetToMediaTimer  OBJECT-TYPE
    SYNTAX      Unsigned32 (0..65535)
    UNITS       "seconds"
    MAX-ACCESS  read-only
    STATUS      current
    DESCRIPTION
         "The value of vRtrIpNetToMediaTimer determines how much longer an ARP
          entry associated with an vRtrIpNetToMediaTable entry remains in the ARP
          cache. It is initially set to vRtrIfArpTimeout. When
          vRtrIpNetToMediaTimer has a value of zero, '0', the entry is cleared
          from the cache."
     ::= { vRtrIpNetToMediaEntry 1 }

vRtrIpNetToMediaOperState  OBJECT-TYPE
    SYNTAX      TmnxOperState
    MAX-ACCESS  read-only
    STATUS      current
    DESCRIPTION
         "The value of vRtrIpNetToMediaOperState specifies if the ARP entry is
          being used actively in the ARP Table. When ipNetToMediaType has a
          value 'dynamic', vRtrIpNetToMediaOperState will never have a value of
          'outOfService'."
     ::= { vRtrIpNetToMediaEntry 2 }

--
-- VRtr instance aggregation objects
--

vRtrInstanceAggregationTableLastChanged OBJECT-TYPE
    SYNTAX      TimeStamp
    MAX-ACCESS  read-only
    STATUS      current
    DESCRIPTION
        "Timestamp of the last change to the vRtrInstanceAggregationTable
         either from adding a row or removing a row."
    ::= { tmnxVRtrObjs 12 }

vRtrInstanceAggregationTable  OBJECT-TYPE
    SYNTAX      SEQUENCE OF VRtrInstanceAggregationEntry
    MAX-ACCESS  not-accessible
    STATUS      current
    DESCRIPTION
        "The vRtrInstanceAggregationTable is the list of configured
         VRtr aggregations and their operational status information.

         Specifies the route aggregates that should be generated
         into the virtual router if at least one contributing route
         (more specific) is learned.

         A route could match multiple aggregate statements.
         For instance, with the following entries:
         aggregate 10.0.0.0/8
         aggregate 10.1.0.0/16

         If the route 10.1.1.0/24 is learned, both aggregates would be
         generated."
    ::= { tmnxVRtrObjs 13 }

vRtrInstanceAggregationEntry  OBJECT-TYPE
    SYNTAX      VRtrInstanceAggregationEntry
    MAX-ACCESS  not-accessible
    STATUS      current
    DESCRIPTION
        "An entry (conceptual row) in the vRtrInstanceAggregationTable.
         Entries are created by user. Entries are destroyed by user."
    INDEX { vRtrID, vRtrAggregationIpPrefix, vRtrAggregationIpPrefixMask }
    ::= { vRtrInstanceAggregationTable 1 }

VRtrInstanceAggregationEntry ::= SEQUENCE {
    vRtrAggregationIpPrefix         IpAddress,
    vRtrAggregationIpPrefixMask     IpAddressPrefixLength,
    vRtrAggregationRowStatus        RowStatus,
    vRtrAggregationLastChanged      TimeStamp,
    vRtrAggregationSummaryOnly      TruthValue,
    vRtrAggregationASSet            TruthValue,
    vRtrAggregationAggregatorAS     TmnxBgpAutonomousSystem,
    vRtrAggregationAggregatorIPAddr IpAddress,
    vRtrAggregationOperState        TmnxOperState
    }

vRtrAggregationIpPrefix  OBJECT-TYPE
    SYNTAX      IpAddress
    MAX-ACCESS  not-accessible
    STATUS      current
    DESCRIPTION
        "IP address prefix to match for the aggregation."
    ::= { vRtrInstanceAggregationEntry 1 }


vRtrAggregationIpPrefixMask  OBJECT-TYPE
    SYNTAX      IpAddressPrefixLength
    MAX-ACCESS  not-accessible
    STATUS      current
    DESCRIPTION
        "Mask length for vRtrAggregationIpPrefix, to match for the
         aggregation."
    ::= { vRtrInstanceAggregationEntry 2 }

vRtrAggregationRowStatus  OBJECT-TYPE
    SYNTAX      RowStatus
    MAX-ACCESS  read-create
    STATUS      current
    DESCRIPTION
        "Row status for this entry."
    ::= { vRtrInstanceAggregationEntry 3 }

vRtrAggregationLastChanged  OBJECT-TYPE
    SYNTAX      TimeStamp
    MAX-ACCESS  read-create
    STATUS      current
    DESCRIPTION
        "Time stamp of last change of any object for this entry."
    ::= { vRtrInstanceAggregationEntry 4 }

vRtrAggregationSummaryOnly  OBJECT-TYPE
    SYNTAX      TruthValue
    MAX-ACCESS  read-create
    STATUS      current
    DESCRIPTION
        "When true(1), only the aggregate is advertised, the more
         specfic routes that make up the aggregate are not.

         When false(2), both the aggregate and more specific
         components are advertised."
    DEFVAL { false }
    ::= { vRtrInstanceAggregationEntry 5 }

vRtrAggregationASSet  OBJECT-TYPE
    SYNTAX      TruthValue
    MAX-ACCESS  read-create
    STATUS      current
    DESCRIPTION
        "When true(1), the AS-Path of the resulting aggregate will contain
         an AS-SET containing all AS numbers from the contributing routes.

         When false(2), the AS-Path will contain no AS-SET and will be
         originated by the ESR."
    DEFVAL { false }
    ::= { vRtrInstanceAggregationEntry 6 }

vRtrAggregationAggregatorAS  OBJECT-TYPE
    SYNTAX      TmnxBgpAutonomousSystem
    MAX-ACCESS  read-create
    STATUS      current
    DESCRIPTION
        "When vRtrAggregationAggregatorAS is set to non zero, and
         vRtrAggregationAggregatorIPAddr is set to non-zero,
         the supplied ASN and IP address will be used for the aggregator path
         attributes.

         When omitted, automatically uses its own ASN & Router-ID."
    DEFVAL { 0 }
    ::= { vRtrInstanceAggregationEntry 7 }

vRtrAggregationAggregatorIPAddr  OBJECT-TYPE
    SYNTAX      IpAddress
    MAX-ACCESS  read-create
    STATUS      current
    DESCRIPTION
        "When vRtrAggregationAggregatorAS is set to non zero, and
         vRtrAggregationAggregatorIPAddr is set to non-zero,
         the supplied ASN and IP address will be used for the aggregator path
         attributes.

         When omitted, automatically uses its own ASN & Router-ID."
    DEFVAL { '00000000'H }  -- 0.0.0.0 means not-set
    ::= { vRtrInstanceAggregationEntry 8 }

 vRtrAggregationOperState  OBJECT-TYPE
    SYNTAX      TmnxOperState
    MAX-ACCESS  read-only
    STATUS      current
    DESCRIPTION
        "vRtrAggregationOperState specifies the current operational status
         of the aggregation entry."
    ::= { vRtrInstanceAggregationEntry 9 }

--
-- Static Route Index Table
--

-- A read-only table which suggests the available index - vRtrStaticRouteIndex
-- for a given set of vRtrID, vRtrStaticRouteDest & vRtrStaticRouteMask.
-- vRtrStaticRouteIndex will be the fourth index while configuring an entry
-- into the vRtrStaticRouteTable.

vRtrStaticRouteIndexTable  OBJECT-TYPE
    SYNTAX      SEQUENCE OF VRtrStaticRouteIndexEntry
    MAX-ACCESS  not-accessible
    STATUS      current
    DESCRIPTION
        "This entity's Static Route Index Table."
    ::= { tmnxVRtrObjs 14 }

vRtrStaticRouteIndexEntry  OBJECT-TYPE
    SYNTAX      VRtrStaticRouteIndexEntry
    MAX-ACCESS  not-accessible
    STATUS      current
    DESCRIPTION
        "The available index for the vRtrStaticRouteTable for every
        destination per virtual router."
    INDEX {
        vRtrID,
        vRtrStaticRouteIndexDest,
        vRtrStaticRouteIndexMask
        }
    ::= { vRtrStaticRouteIndexTable 1 }

VRtrStaticRouteIndexEntry ::=
    SEQUENCE {
        vRtrStaticRouteIndexDest                     IpAddress,
        vRtrStaticRouteIndexMask                     IpAddress,
        vRtrStaticRouteAvailableIndex                TestAndIncr
        }

vRtrStaticRouteIndexDest  OBJECT-TYPE
    SYNTAX      IpAddress
    MAX-ACCESS  read-only
    STATUS      current
    DESCRIPTION
        "The destination IP address of this index entry.
         This object may not take a Multicast (Class  D) address value.

         Any  assignment  (implicit  or  otherwise)  of an instance of this
         object to a value x must be rejected if the bitwise logical-AND of
         x   with   the   value   of  the  corresponding  instance  of  the
         vRtrStaticRouteMask object is not equal to x."
    ::= { vRtrStaticRouteIndexEntry 1 }

vRtrStaticRouteIndexMask  OBJECT-TYPE
    SYNTAX      IpAddress
    MAX-ACCESS  read-only
    STATUS      current
    DESCRIPTION
        "Indicate the mask to be logical-ANDed with the destination address
         before  being  compared  to  the  value in the vRtrStaticRouteDest
         field.  For  those  systems  that  do not support arbitrary subnet
         masks, an agent constructs the value of the vRtrStaticRouteMask by
         reference  to  the  IP  Address Class. Any assignment (implicit or
         otherwise)  of  an  instance  of  this object to a value x must be
         rejected  if  the  bitwise  logical-AND of x with the value of the
         corresponding  instance  of  the vRtrStaticRouteDest object is not
         equal to vRtrStaticRouteDest."
    ::= { vRtrStaticRouteIndexEntry 2 }

vRtrStaticRouteAvailableIndex  OBJECT-TYPE
    SYNTAX      TestAndIncr (1..2147483647)
    MAX-ACCESS  read-only
    STATUS      current
    DESCRIPTION
        "The available quaternary index for the vRtrStaticRouteTable."
    ::= { vRtrStaticRouteIndexEntry 3 }

--
--  Tunnel Table
--

vRtrTunnelTable  OBJECT-TYPE
    SYNTAX      SEQUENCE OF VRtrTunnelEntry
    MAX-ACCESS  not-accessible
    STATUS      current
    DESCRIPTION
       "vRtrTunnelTable maintains a list of tunnels for the specific router
        instance."
    ::= { tmnxVRtrObjs 17 }

vRtrTunnelEntry  OBJECT-TYPE
    SYNTAX      VRtrTunnelEntry
    MAX-ACCESS  not-accessible
    STATUS      current
    DESCRIPTION
       "vRtrTunnelEntry defines a tunnel to a particular destination in a
        specific router context. A tunnel to a specific destination could
        established using GRE, LDP, RSVP or could be a static LSP."
    INDEX {
        vRtrID,
        vRtrTunnelDest,
        vRtrTunnelMask,
        vRtrTunnelPreference,
        vRtrTunnelType,
        vRtrTunnelID,
        vRtrTunnelNexthop
        }
    ::= { vRtrTunnelTable 1 }

VRtrTunnelEntry ::=
    SEQUENCE {
        vRtrTunnelDest              IpAddress,
        vRtrTunnelMask              IpAddress,
        vRtrTunnelPreference        Unsigned32,
        vRtrTunnelNexthop           IpAddress,
        vRtrTunnelType              TmnxTunnelType,
        vRtrTunnelID                TmnxTunnelID,
        vRtrTunnelMetric            Unsigned32,
        vRtrTunnelAge               Integer32
    }

vRtrTunnelDest  OBJECT-TYPE
    SYNTAX      IpAddress
    MAX-ACCESS  not-accessible
    STATUS      current
    DESCRIPTION
       "vRtrTunnelDest maintains the destination IP address of this tunnel.
        This object may not take a Multicast (Class  D) address value.

        Any assignment (implicit or otherwise) of an instance of this object
        to a value x must be rejected if the bitwise logical-AND of x with the
        value of the corresponding instance of the vRtrTunnelMask object is not
        equal to x."
    ::= { vRtrTunnelEntry 1 }

vRtrTunnelMask  OBJECT-TYPE
    SYNTAX      IpAddress
    MAX-ACCESS  not-accessible
    STATUS     current
    DESCRIPTION
       "vRtrTunnelMask indicates the mask to be logical-ANDed with the
        destination address before being compared to the value in the
        vRtrTunnelDest field. For those systems that do not support arbitrary
        subnet masks, an agent constructs the value of the vRtrTunnelMask
        by reference to the IP Address Class.

        Any assignment (implicit or otherwise) of an instance of this object
        to a value x must be rejected if the bitwise logical-AND of x with
        the value of the corresponding instance of the ipCidrRouteDest object
        is not equal to ipCidrRouteDest."
    ::= { vRtrTunnelEntry 2 }

vRtrTunnelPreference  OBJECT-TYPE
    SYNTAX      Unsigned32 (1..255)
    MAX-ACCESS  not-accessible
    STATUS      current
    DESCRIPTION
        "The value of vRtrTunnelPreference determines the priority of this
         tunnel versus the other tunnels from different sources such as LDP,
         RSVP, GRE etc. This is an absolute number used internally by the
         system to specify preferences for the tunnel.

         Lowest number signifies the most preferred entry in the table."
    ::= { vRtrTunnelEntry 3 }

vRtrTunnelType  OBJECT-TYPE
    SYNTAX      TmnxTunnelType
    MAX-ACCESS  not-accessible
    STATUS      current
    DESCRIPTION
       "The type of this tunnel entity."
    ::= { vRtrTunnelEntry 4 }

vRtrTunnelID  OBJECT-TYPE
    SYNTAX      TmnxTunnelID
    MAX-ACCESS  not-accessible
    STATUS      current
    DESCRIPTION
       "Additional index provided to distinguish between multiple tunnels to
        same destination having same characteristics.

        There could be multiple tunnels for the type 'sdp'. In such cases the
        vRtrTunnelID will hold the SDP Id.

        There could be multiple tunnels for the type 'ldp'. In such cases the
        vRtrTunnelID will hold the LSPId of the LSP in use.

        For other vRtrTunnelType values this field will always be 0 as only a
        single tunnel is established using other tunnel types."
    ::= { vRtrTunnelEntry 5 }

vRtrTunnelNexthop  OBJECT-TYPE
    SYNTAX      IpAddress
    MAX-ACCESS  not-accessible
    STATUS      current
    DESCRIPTION
       "The address of the next system en route; Otherwise, 0.0.0.0."
    ::= { vRtrTunnelEntry 6 }

vRtrTunnelMetric  OBJECT-TYPE
    SYNTAX      Unsigned32
    MAX-ACCESS  read-only
    STATUS     current
    DESCRIPTION
       "vRtrTunnelMetric maintains the metric of the tunnel. This is used
        in addition to the preference for this tunnel."
    ::= { vRtrTunnelEntry 7 }

vRtrTunnelAge OBJECT-TYPE
    SYNTAX      Integer32
    MAX-ACCESS  read-only
    STATUS      current
    DESCRIPTION
       "The number of seconds  since this tunnel entry was last
        updated or otherwise determined to be correct. No semantics
        of  `too  old' can  be implied except through knowledge of
        owner of the tunnel."
    ::= { vRtrTunnelEntry 8 }

--
--  Router-Advertisement Prefix Table
--

vRtrAdvPrefixTable OBJECT-TYPE
    SYNTAX     SEQUENCE OF VRtrAdvPrefixEntry
    MAX-ACCESS not-accessible
    STATUS     current
    DESCRIPTION
           "This table allows the user to configure IPv6 prefixes for
            router advertisements on an interface"
    ::= { tmnxVRtrObjs 23 }

vRtrAdvPrefixEntry OBJECT-TYPE
    SYNTAX     VRtrAdvPrefixEntry
    MAX-ACCESS not-accessible
    STATUS     current
    DESCRIPTION
           "An entry in the vRtrAdvPrefixTable."
    INDEX    { vRtrID, vRtrAdvPrefixIfIndex, vRtrAdvPrefixPrefix, vRtrAdvPrefixLength }
    ::= { vRtrAdvPrefixTable 1 }

VRtrAdvPrefixEntry ::= SEQUENCE {
        vRtrAdvPrefixIfIndex                InterfaceIndex,
        vRtrAdvPrefixPrefix                 InetAddress,
        vRtrAdvPrefixLength                 InetAddressPrefixLength,
        vRtrAdvPrefixRowStatus              RowStatus,
        vRtrAdvPrefixOnLinkFlag             TruthValue,
        vRtrAdvPrefixAutonomousFlag         TruthValue,
        vRtrAdvPrefixPreferredLifetime      Unsigned32,
        vRtrAdvPrefixValidLifetime          Unsigned32
    }

vRtrAdvPrefixIfIndex OBJECT-TYPE
    SYNTAX     InterfaceIndex
    MAX-ACCESS not-accessible
    STATUS     current
    DESCRIPTION
           "The index value which uniquely identifies the interface on
            which this prefix is configured.  The interface identified
            by a particular value of this index is the same interface as
            identified by the same value of the IF-MIB's ifIndex."
    ::= { vRtrAdvPrefixEntry 1 }

vRtrAdvPrefixPrefix OBJECT-TYPE
    SYNTAX     InetAddress (SIZE (16))
    MAX-ACCESS not-accessible
    STATUS     current
    DESCRIPTION
           "The ipv6 address prefix. The length of this object
            is the standard length (16 bytes ) for IPv6 prefixes."
    ::= { vRtrAdvPrefixEntry 2 }

vRtrAdvPrefixLength OBJECT-TYPE
    SYNTAX     InetAddressPrefixLength (4..127)
    MAX-ACCESS not-accessible
    STATUS     current
    DESCRIPTION
           "The prefix length associated with this prefix.
            The value 0 has no special meaning for this object."
    ::= { vRtrAdvPrefixEntry 3 }

vRtrAdvPrefixRowStatus OBJECT-TYPE
    SYNTAX     RowStatus
    MAX-ACCESS read-create
    STATUS     current
    DESCRIPTION
           "The row status used for creation and deletion of router
            advertisement prefix entries."
    ::= { vRtrAdvPrefixEntry 4 }

vRtrAdvPrefixOnLinkFlag OBJECT-TYPE
    SYNTAX     TruthValue
    MAX-ACCESS read-create
    STATUS     current
    DESCRIPTION
           "This object has the value 'true(1)', if this prefix can be
            used  for on-link determination and the value 'false(2)'
            otherwise."
    REFERENCE "For IPv6 RFC2461, especially sections 2 and 4.6.2 and
    RFC2462"
    DEFVAL { true }
    ::= { vRtrAdvPrefixEntry 5 }

vRtrAdvPrefixAutonomousFlag OBJECT-TYPE
    SYNTAX     TruthValue
    MAX-ACCESS read-create
    STATUS     current
    DESCRIPTION
           "Autonomous address configuration flag. When true(1),
            indicates that this prefix can be used for autonomous
            address configuration (i.e. can be used to form a local
            interface address).  If false(2), it is not used to auto-
            configure a local interface address."
    REFERENCE "For IPv6 RFC2461, especially sections 2 and 4.6.2 and
    RFC2462"
    DEFVAL { true }
    ::= { vRtrAdvPrefixEntry 6 }

vRtrAdvPrefixPreferredLifetime OBJECT-TYPE
    SYNTAX     Unsigned32
    UNITS       "seconds"
    MAX-ACCESS read-create
    STATUS     current
    DESCRIPTION
           "The remaining length of time in seconds that this prefix
            will continue to be preferred, i.e. time until deprecation.
            A value of 4,294,967,295 represents infinity.

            The address generated from a deprecated prefix should no
            longer be used as a source address in new communications,
            but packets received on such an interface are processed as
            expected."
    REFERENCE "For IPv6 RFC2461, especially sections 2 and 4.6.2 and
    RFC2462"
    DEFVAL { 604800 }
    ::= { vRtrAdvPrefixEntry 7 }

vRtrAdvPrefixValidLifetime OBJECT-TYPE
    SYNTAX     Unsigned32
    UNITS       "seconds"
    MAX-ACCESS read-create
    STATUS     current
    DESCRIPTION
           "The remaining length of time, in seconds, that this prefix
            will continue to be valid, i.e. time until invalidation.  A
            value of 4,294,967,295 represents infinity.

            The address generated from an invalidated prefix should not
            appear as the destination or source address of a packet."
    REFERENCE "For IPv6 RFC2461, especially sections 2 and 4.6.2 and
    RFC2462"
    DEFVAL { 2592000 }
    ::= { vRtrAdvPrefixEntry 8 }

--
--  Virtual router Static Route Table
--

-- vRtrInetStaticRouteTable replaces the vRtrStaticRouteTable
-- that supports configuration of static routes using only the
-- IPv4 address style. The vRtrInetStaticRouteTable is IP version
-- neutral and allows configuration of static routes using IPv4 or
-- IPv6 InetAddress style.

vRtrInetStaticRouteTable  OBJECT-TYPE
    SYNTAX      SEQUENCE OF VRtrInetStaticRouteEntry
    MAX-ACCESS  not-accessible
    STATUS      current
    DESCRIPTION
       "The table of addressing information relevant
        to this entity's Static Routing table."
    ::= { tmnxVRtrObjs 24 }

vRtrInetStaticRouteEntry OBJECT-TYPE
    SYNTAX      VRtrInetStaticRouteEntry
    MAX-ACCESS  not-accessible
    STATUS      current
    DESCRIPTION
       "A particular route to a particular destination,
        through a particular next hop."
    INDEX {
        vRtrID,
        vRtrInetStaticRouteDestType,
        vRtrInetStaticRouteDest,
        vRtrInetStaticRouteDestPfxLen,
        vRtrInetStaticRouteIndex
        }
    ::= { vRtrInetStaticRouteTable 1 }

VRtrInetStaticRouteEntry ::=
    SEQUENCE {
        vRtrInetStaticRouteDestType                 InetAddressType,
        vRtrInetStaticRouteDest                     InetAddress,
        vRtrInetStaticRouteDestPfxLen               InetAddressPrefixLength,
        vRtrInetStaticRouteIndex                    INTEGER,
        vRtrInetStaticRouteRowStatus                RowStatus,
        vRtrInetStaticRouteLastEnabledTime          TimeStamp,
        vRtrInetStaticRouteStatus                   INTEGER,
        vRtrInetStaticRouteStaticType               INTEGER,
        vRtrInetStaticRoutePreference               Unsigned32,
        vRtrInetStaticRouteMetric                   Unsigned32,
        vRtrInetStaticRouteEgressIfIndex            InterfaceIndexOrZero,
        vRtrInetStaticRouteNextHopType              InetAddressType,
        vRtrInetStaticRouteNextHop                  InetAddress,
        vRtrInetStaticRouteNextHopIf                DisplayString,
        vRtrInetStaticRouteAdminState               TmnxAdminState,
        vRtrInetStaticRouteIgpShortcut              BITS,
        vRtrInetStaticRouteDisallowIgp              TruthValue,
        vRtrInetStaticRouteTag                      Unsigned32,
        vRtrInetStaticRouteEnableBfd                TruthValue,
        vRtrInetStaticRouteCpeAddrType              InetAddressType,
        vRtrInetStaticRouteCpeAddr                  InetAddress,
        vRtrInetStaticRouteCpeInterval              Unsigned32,
        vRtrInetStaticRouteCpeDropCnt               Unsigned32,
        vRtrInetStaticRouteCpeEnableLog             TruthValue
    }

vRtrInetStaticRouteDestType  OBJECT-TYPE
    SYNTAX      InetAddressType
    MAX-ACCESS  not-accessible
    STATUS      current
    DESCRIPTION
       "The value of vRtrInetStaticRouteDestType indicates
        the address type of vRtrInetStaticRouteDest address."
    ::= { vRtrInetStaticRouteEntry 1 }

vRtrInetStaticRouteDest  OBJECT-TYPE
    SYNTAX      InetAddress
    MAX-ACCESS  not-accessible
    STATUS      current
    DESCRIPTION
       "The value of vRtrInetStaticRouteDest indicates the
        destination IP address of this static route."
    ::= { vRtrInetStaticRouteEntry 2 }

vRtrInetStaticRouteDestPfxLen  OBJECT-TYPE
    SYNTAX      InetAddressPrefixLength
    MAX-ACCESS  not-accessible
    STATUS      current
    DESCRIPTION
       "The value of vRtrInetStaticRouteDestPfxLen indicates
        the prefix length associated with the
        vRtrInetStaticRouteDest address."
    ::= { vRtrInetStaticRouteEntry 3 }

vRtrInetStaticRouteIndex  OBJECT-TYPE
    SYNTAX      INTEGER (1..2147483647)
    MAX-ACCESS  not-accessible
    STATUS      current
    DESCRIPTION
       "The value of vRtrInetStaticRouteIndex indicates the fifth
        index for the vRtrInetStaticRouteTable.

        The fifth index to vRtrInetStaticRouteTable identifies a
        specific next-hop route to distinguish it from other
        routes that share the same destination address."
    ::= { vRtrInetStaticRouteEntry 4 }

vRtrInetStaticRouteRowStatus  OBJECT-TYPE
    SYNTAX      RowStatus
    MAX-ACCESS  read-create
    STATUS      current
    DESCRIPTION
       "vRtrInetStaticRouteRowStatus controls the creation
        and deletion of rows in the table."
    ::= { vRtrInetStaticRouteEntry 5 }

vRtrInetStaticRouteLastEnabledTime  OBJECT-TYPE
    SYNTAX      TimeStamp
    MAX-ACCESS  read-only
    STATUS      current
    DESCRIPTION
        "The value of vRtrInetStaticRouteLastEnabledTime
         indicates the sysUpTime value when
         vRtrInetStaticRouteStatus was last set to active (1) to
         allow IP forwarding on this static route entry."
    ::= { vRtrInetStaticRouteEntry 6 }

vRtrInetStaticRouteStatus  OBJECT-TYPE
    SYNTAX      INTEGER {
                    active   (1),
                    inactive (2)
                }
    MAX-ACCESS  read-only
    STATUS      current
    DESCRIPTION
        "The value of vRtrInetStaticRouteStatus indicates
         whether or not this route entry is active in the system.
         When an interface transitions to the down state, any
         associated route entries are marked as 'inactive'
         and are usually not displayed in a standard route
         table listing.  When the interface transitions
         to the up state, the agent marks the associated routes as
         'active'"
    ::= { vRtrInetStaticRouteEntry 7 }

vRtrInetStaticRouteStaticType  OBJECT-TYPE
    SYNTAX      INTEGER {
                    unknown (0),
                    nextHop (1),
                    indirect (2),
                    blackHole (3)
                }
    MAX-ACCESS  read-create
    STATUS      current
    DESCRIPTION
        "The value of vRtrInetStaticRouteStaticType specifies the
         type of static route represented by this row entry."
    DEFVAL { unknown }
    ::= { vRtrInetStaticRouteEntry 8 }

vRtrInetStaticRoutePreference  OBJECT-TYPE
    SYNTAX      Unsigned32 (1..256)
    MAX-ACCESS  read-create
    STATUS      current
    DESCRIPTION
        "The value of vRtrInetStaticRoutePreference specifies the priority
         of this static route versus the routes from different sources
         such as BGP or OSPF etc.

         Different protocols should not be configured with the same
         preference, if this occurs the tiebreaker is determined per the
         default preference value as defined in the table below.

         If multiple routes are learned with an identical preference
         using the same protocol, the lowest cost is used. If multiple
         routes are learned with an identical preference using the same
         protocol and the costs (metrics) are equal, then the decision
         as to what route to use is determined by the configuration of
         the ecmp command.

         Default preferences.


         Route Type             Preference      Configurable
         ----------             ----------      ------------
         Direct attached                 0                no
         Static-route                    5               yes
         MPLS (post FCS)                 7
         OSPF Internal routes           10                no
         OSPF External                 150               yes
         BGP                           170               yes
         "
    DEFVAL { 5 }
    ::= { vRtrInetStaticRouteEntry 9 }

vRtrInetStaticRouteMetric  OBJECT-TYPE
    SYNTAX      Unsigned32 (0..65535)
    MAX-ACCESS  read-create
    STATUS      current
    DESCRIPTION
        "The value of vRtrInetStaticRouteMetric specifies
         the metric for the static route.

         When ipCidrRouteProto has a value of 'netmgmt' to specify that
         this entry is a static route, the value of vRtrInetStaticRouteMetric
         associates a metric value with the route. This value is used
         when importing this static route into other protocols such as
         OSPF.  When the metric is configured as zero then the metric
         configured in OSPF, default-import-metric, applies.  This value
         is also used to determine which static route to install in the
         forwarding table:

         If there are multiple static routes with the same preference
         but unequal metric then the lower cost (metric) route will be
         installed.

         If there are multiple static routes with equal preference and
         metrics then ecmp rules apply.

         If there are multiple routes with unequal preference then the
         lower preference route will be installed.
         "
    DEFVAL { 1 }
    ::= { vRtrInetStaticRouteEntry 10 }

vRtrInetStaticRouteEgressIfIndex  OBJECT-TYPE
    SYNTAX      InterfaceIndexOrZero
    MAX-ACCESS  read-only
    STATUS      current
    DESCRIPTION
        "The value of vRtrInetStaticRouteEgressIfIndex indicates
         the outgoing ifIndex for this route as computed by the
         static-route module. This variable will have a value of 0
         if vRtrInetStaticRouteStatus is 'inactive' or if this static
         route is configured as a black hole."
    ::= { vRtrInetStaticRouteEntry 11 }

vRtrInetStaticRouteNextHopType  OBJECT-TYPE
    SYNTAX      InetAddressType
    MAX-ACCESS  read-create
    STATUS      current
    DESCRIPTION
        "The value of vRtrInetStaticRouteNextHopType specifies
         the address type of vRtrInetStaticRouteNextHop address."
    DEFVAL { unknown }
    ::= { vRtrInetStaticRouteEntry 12 }

vRtrInetStaticRouteNextHop  OBJECT-TYPE
    SYNTAX      InetAddress (SIZE (0|4|16|20))
    MAX-ACCESS  read-create
    STATUS      current
    DESCRIPTION
        "The value of vRtrInetStaticRouteNextHop specifies
         the address of the next hop for the static route.

         In case of remote routes, the address of the
         next system en route. This member is
         complemented by vRtrInetStaticRouteNextHopIf.

         At most only one of the two objects:
         vRtrInetStaticRouteNextHop, vRtrInetStaticRouteNextHopIf
         and can be non-null. If vRtrInetStaticRouteNextHopType
         is 'unknown' and vRtrInetStaticRouteNextHopIf is a
         null string then this static route is configured as
         a black hole."
    ::= { vRtrInetStaticRouteEntry 13 }

vRtrInetStaticRouteNextHopIf  OBJECT-TYPE
    SYNTAX      DisplayString (SIZE(0..32))
    MAX-ACCESS  read-create
    STATUS      current
    DESCRIPTION
       "The value of vRtrInetStaticRouteNextHopIf specifies
         the interface of the next hop for the static route.

         The name of the Interface which will be the nexthop for
         this route. This member is complemented by
         vRtrInetStaticRouteNextHop.

         At most only one of the two objects:
         vRtrInetStaticRouteNextHop, vRtrInetStaticRouteNextHopIf
         and can be non-null. If vRtrInetStaticRouteNextHopType
         is 'unknown' and vRtrInetStaticRouteNextHopIf is a
         null string then this static route is configured as
         a black hole."
    ::= { vRtrInetStaticRouteEntry 14 }

vRtrInetStaticRouteAdminState  OBJECT-TYPE
    SYNTAX      TmnxAdminState
    MAX-ACCESS  read-create
    STATUS      current
    DESCRIPTION
        "The value of vRtrInetStaticRouteAdminState specifies
          the desired administrative state for this
         virtual router static route"
    DEFVAL { inService }
    ::= { vRtrInetStaticRouteEntry 15 }

vRtrInetStaticRouteIgpShortcut  OBJECT-TYPE
    SYNTAX      BITS {
                    te(0),
                    ldp(1),
                    ip(2)
                }
    MAX-ACCESS  read-create
    STATUS      current
    DESCRIPTION
        "The value of vRtrInetStaticRouteIgpShortcut specifies the
         Layer 2 tunneling mechanism used for IGP shortcuts.

         The value of vRtrInetStaticRouteIgpShortcut is valid only for indirect
         static routes (i.e. vRtrInetStaticRouteStaticType is 'indirect'). The
         bits of vRtrInetStaticRouteIgpShortcut identify Layer 2 tunneling
         mechanisms used for IGP shortcuts. If a bit is set, IGP shortcuts
         associated with that tunneling mechanism will be used to resolve
         next-hop for the static-route. If no bits are set, IGP shortcuts
         will not be used to resolve next-hop for the static routes.

         The tunneling mechanisms represented by each bit are:
           te(0)  - RSVP Traffic Engineering
           ldp(1) - LDP /32 Route Forwarding Equivalence Class (FEC)
           ip(2)  - IP (IP-in-IP or GRE)

         Evaluation of tunnel preference is based on the following order, in
         descending priority:
           1. Traffic Engineered Shortcut (RSVP-TE)
           2. LDP /32 Route FEC Shortcut
           3. IP Shortcut (IP-in-IP or GRE)
           4. Actual IGP Next-Hop."
    DEFVAL { { } }
    ::= { vRtrInetStaticRouteEntry 16 }

vRtrInetStaticRouteDisallowIgp  OBJECT-TYPE
    SYNTAX      TruthValue
    MAX-ACCESS  read-create
    STATUS      current
    DESCRIPTION
        "The value of vRtrInetStaticRouteDisallowIgp specifies if
         IGP shortcuts are to be used or not.

         The value of vRtrInetStaticRouteDisallowIgp is valid only for indirect
         static routes (i.e. vRtrInetStaticRouteStaticType is 'indirect'). If
         the value of vRtrInetStaticRouteDisallowIgp is set to 'true', and if
         none of the defined tunneling mechanisms (RSVP-TE, LDP or IP)
         qualify as a next-hop, the normal IGP next-hop to the indirect
         next-hop address will not be used. If the value is set to 'false',
         IGP next-hop to the indirect next-hop address can be used as the
         next-hop of the last resort."
    DEFVAL { false }
    ::= { vRtrInetStaticRouteEntry 17 }

vRtrInetStaticRouteTag  OBJECT-TYPE
    SYNTAX      Unsigned32 (0..4294967295)
    MAX-ACCESS  read-create
    STATUS      current
    DESCRIPTION
        "The value of vRtrInetStaticRouteTag specifies a 32-bit integer tag
         that is used to add to the static route. This tag could then be used
         in route policies to control distribution of the route into other
         protocols. A value of 0 indicates that the tag has not been set."
    DEFVAL { 0 }
    ::= { vRtrInetStaticRouteEntry 18 }

vRtrInetStaticRouteEnableBfd    OBJECT-TYPE
    SYNTAX      TruthValue
    MAX-ACCESS  read-create
    STATUS      current
    DESCRIPTION
        "The value of vRtrInetStaticRouteEnableBfd specifies whether or not
         Bi-directional Forwarding Detection is enabled on this static route.

         When the value is 'true', this static-route can establish BFD sessions
         and use BFD as a signalling mechanism.
         When it is 'false', it cannot use BFD."
    DEFVAL { false }
    ::= { vRtrInetStaticRouteEntry 19 }

vRtrInetStaticRouteCpeAddrType OBJECT-TYPE
    SYNTAX      InetAddressType
    MAX-ACCESS  read-create
    STATUS      current
    DESCRIPTION
        "The value of vRtrInetStaticRouteCpeAddrType specifies the address
         type of vRtrInetStaticRouteCpeAddr address.

         When the value of vRtrInetStaticRouteCpeAddrType is not 'unknown',
         statitistics for the Customer-Provided Equipment (CPE) host checks
         for this static route entry will be found in the sparsely dependent
         table extension, vRtrInetStatRteCpeChkStatsTable."
    DEFVAL { unknown }
    ::= { vRtrInetStaticRouteEntry 20 }

vRtrInetStaticRouteCpeAddr OBJECT-TYPE
    SYNTAX      InetAddress (SIZE(0|4|16))
    MAX-ACCESS  read-create
    STATUS      current
    DESCRIPTION
        "The value of vRtrInetStaticRouteCpeAddr specifies the IP address 
         of the target CPE device. When this object is configured, ICMP pings 
         will be sent to this target IP address to determine CPE connectivity
         and whether this static route should be active.

         When the value of vRtrInetStaticRouteCpeAddr is non-empty,
         statitistics for the CPE host checks for this static route entry
         will be found in the sparsely dependent table extension,
         vRtrInetStatRteCpeChkStatsTable."
    DEFVAL { ''H }
    ::= { vRtrInetStaticRouteEntry 21 }

vRtrInetStaticRouteCpeInterval OBJECT-TYPE
    SYNTAX      Unsigned32 (1..255)
    UNITS       "seconds"
    MAX-ACCESS  read-create
    STATUS      current
    DESCRIPTION
        "The value of vRtrInetStaticRouteCpeInterval specifies the interval,
         in seconds, between ICMP pings to the target CPE IP address,
         vRtrInetStaticRouteCpeAddr."
    DEFVAL { 1 }
    ::= { vRtrInetStaticRouteEntry 22 }

vRtrInetStaticRouteCpeDropCnt OBJECT-TYPE
    SYNTAX      Unsigned32 (1..255)
    MAX-ACCESS  read-create
    STATUS      current
    DESCRIPTION
        "The value of vRtrInetStaticRouteCpeDropCnt specifies the number of
         consecutive ping-replies that must be missed before concluding the 
         CPE is down. If the CPE is determined to be down, the associated 
         static route will be deactivated."
    DEFVAL { 3 }
    ::= { vRtrInetStaticRouteEntry 23 }

vRtrInetStaticRouteCpeEnableLog OBJECT-TYPE
    SYNTAX      TruthValue
    MAX-ACCESS  read-create
    STATUS      current
    DESCRIPTION
        "The value of vRtrInetStaticRouteCpeEnableLog specifies whether to enable
         the logging of transitions between active and in-active based on the CPE
         connectivity check.

         A value of 'true (1)' indicates that logging should be enabled."
    DEFVAL { false }
    ::= { vRtrInetStaticRouteEntry 24 }


--
-- Inet Static Route Index Table
--

-- A read-only table which suggests the available
-- index - vRtrInetStaticRouteIndex
-- for a given set of vRtrID, vRtrInetStaticRouteDestType,
-- vRtrInetStaticRouteDest & vRtrInetStaticRouteDestPfxLen.
-- vRtrInetStaticRouteIndex will be the fifth index while
-- configuring an entry into the vRtrInetStaticRouteTable.

-- vRtrInetStaticRouteIndexTable table replaces vRtrStaticRouteIndexTable

vRtrInetStaticRouteIndexTable  OBJECT-TYPE
    SYNTAX      SEQUENCE OF VRtrInetStaticRouteIndexEntry
    MAX-ACCESS  not-accessible
    STATUS      current
    DESCRIPTION
        "This entity's Static Route Index Table."
    ::= { tmnxVRtrObjs 25 }

vRtrInetStaticRouteIndexEntry  OBJECT-TYPE
    SYNTAX      VRtrInetStaticRouteIndexEntry
    MAX-ACCESS  not-accessible
    STATUS      current
    DESCRIPTION
        "The available index for the vRtrInetStaticRouteTable for every
        destination per virtual router."
    INDEX {
        vRtrID,
        vRtrInetStaticRouteDestType,
        vRtrInetStaticRouteDest,
        vRtrInetStaticRouteDestPfxLen
        }
    ::= { vRtrInetStaticRouteIndexTable 1 }

VRtrInetStaticRouteIndexEntry ::=
    SEQUENCE {
        vRtrInetStaticRouteAvailIndex       TestAndIncr
        }

vRtrInetStaticRouteAvailIndex  OBJECT-TYPE
    SYNTAX      TestAndIncr (1..2147483647)
    MAX-ACCESS  read-only
    STATUS      current
    DESCRIPTION
        "The value of vRtrInetStaticRouteAvailIndex indicates
         the available fifth index for the vRtrInetStaticRouteTable.

         The fifth index to vRtrInetStaticRouteTable identifies a
         specific next-hop route to distinguish it from other
         routes that share the same destination address."
    ::= { vRtrInetStaticRouteIndexEntry 1 }

--
-- VRtr instance aggregation objects
--

vRtrInetInstAggrTblLastChged OBJECT-TYPE
    SYNTAX      TimeStamp
    MAX-ACCESS  read-only
    STATUS      current
    DESCRIPTION
        "Timestamp of the last change to the vRtrInetInstAggrTable
         either from adding a row or removing a row."
    ::= { tmnxVRtrObjs 26 }

-- vRtrInetInstAggrTable replaces the vRtrInstanceAggregationTable
-- that supports configuration of aggregate routes using only the
-- IPv4 address style. The vRtrInetInstAggrTable is IP version
-- neutral and allows configuration of aggregate routes using IPv4 or
-- IPv6 InetAddress style.

vRtrInetInstAggrTable  OBJECT-TYPE
    SYNTAX      SEQUENCE OF VRtrInetInstAggrEntry
    MAX-ACCESS  not-accessible
    STATUS      current
    DESCRIPTION
        "The vRtrInetInstAggrTable is the list of configured
         virtual router aggregations and their operational
         status information.

         vRtrInetInstAggrTable specifies the route aggregates
         that should be generated into the virtual router if at
         least one contributing route (more specific) is learned.

         A route could match multiple aggregate statements.
         For instance, with the following entries:
         aggregate 10.0.0.0/8
         aggregate 10.1.0.0/16

         If the route 10.1.1.0/24 is learned, both aggregates would be
         generated."
    ::= { tmnxVRtrObjs 27 }

vRtrInetInstAggrEntry  OBJECT-TYPE
    SYNTAX      VRtrInetInstAggrEntry
    MAX-ACCESS  not-accessible
    STATUS      current
    DESCRIPTION
        "vRtrInetInstAggrEntry indicates an entry (conceptual row)
         in the vRtrInetInstAggrTable.
         Entries are created and destroyed by user."
    INDEX { vRtrID,
            vRtrInetAggrIpPrefixType,
            vRtrInetAggrIpPrefix,
            vRtrInetAggrIpPrefixLen }
    ::= { vRtrInetInstAggrTable 1 }

VRtrInetInstAggrEntry ::= SEQUENCE {
    vRtrInetAggrIpPrefixType     InetAddressType,
    vRtrInetAggrIpPrefix         InetAddress,
    vRtrInetAggrIpPrefixLen      InetAddressPrefixLength,
    vRtrInetAggrRowStatus        RowStatus,
    vRtrInetAggrLastChanged      TimeStamp,
    vRtrInetAggrSummaryOnly      TruthValue,
    vRtrInetAggrASSet            TruthValue,
    vRtrInetAggrAggregatorAS     TmnxBgpAutonomousSystem,
    vRtrInetAggrAggregatorIPAddr IpAddress,
    vRtrInetAggrOperState        TmnxOperState
    }

vRtrInetAggrIpPrefixType  OBJECT-TYPE
    SYNTAX      InetAddressType
    MAX-ACCESS  not-accessible
    STATUS      current
    DESCRIPTION
        "The value of vRtrInetAggrIpPrefixType indicates
         the IP address type of vRtrInetAggrIpPrefix."
    ::= { vRtrInetInstAggrEntry 1 }

vRtrInetAggrIpPrefix  OBJECT-TYPE
    SYNTAX      InetAddress
    MAX-ACCESS  not-accessible
    STATUS      current
    DESCRIPTION
        "The value of vRtrInetAggrIpPrefixType indicates
         the IP address prefix to match for the aggregation."
    ::= { vRtrInetInstAggrEntry 2 }


vRtrInetAggrIpPrefixLen  OBJECT-TYPE
    SYNTAX      InetAddressPrefixLength
    MAX-ACCESS  not-accessible
    STATUS      current
    DESCRIPTION
        "The value of vRtrInetAggrIpPrefixLen indicates
         the prefix length for vRtrInetAggrIpPrefix, to match
         for the aggregation."
    ::= { vRtrInetInstAggrEntry 3 }

vRtrInetAggrRowStatus  OBJECT-TYPE
    SYNTAX      RowStatus
    MAX-ACCESS  read-create
    STATUS      current
    DESCRIPTION
        "vRtrInetAggrRowStatus controls the creation
         and deletion of rows in the table."
    ::= { vRtrInetInstAggrEntry 4 }

vRtrInetAggrLastChanged  OBJECT-TYPE
    SYNTAX      TimeStamp
    MAX-ACCESS  read-create
    STATUS      current
    DESCRIPTION
        "The value of vRtrInetAggrLastChanged specifies the
         time stamp of the last change to this row of
         vRtrInetInstAggrTable ."
    ::= { vRtrInetInstAggrEntry 5 }

vRtrInetAggrSummaryOnly  OBJECT-TYPE
    SYNTAX      TruthValue
    MAX-ACCESS  read-create
    STATUS      current
    DESCRIPTION
        "The value of vRtrInetAggrSummaryOnly specifies if
         specific routes that make up aggregates are advertised or
         not.

         When vRtrInetAggrSummaryOnly has value of 'true(1)', only the
         aggregate is advertised, the more specfic routes that make
         up the aggregate are not.

         When vRtrInetAggrSummaryOnly has value of 'false(2)', both the
         aggregate and more specific components are advertised."
    DEFVAL { false }
    ::= { vRtrInetInstAggrEntry 6 }

vRtrInetAggrASSet  OBJECT-TYPE
    SYNTAX      TruthValue
    MAX-ACCESS  read-create
    STATUS      current
    DESCRIPTION
        "The value of vRtrInetAggrASSet specifies whether the
         aggregate route has AS-SET.

         When vRtrInetAggrASSet has value of 'true(1)', the AS-Path
         of the resulting aggregate will contain an AS-SET
         containing all AS numbers from the contributing routes.

         When vRtrInetAggrASSet has value of 'false(2)', the AS-Path
         will contain no AS-SET and will be originated by the ESR."
    DEFVAL { false }
    ::= { vRtrInetInstAggrEntry 7 }

vRtrInetAggrAggregatorAS  OBJECT-TYPE
    SYNTAX      TmnxBgpAutonomousSystem
    MAX-ACCESS  read-create
    STATUS      current
    DESCRIPTION
        "The value of vRtrInetAggrAggregatorAS specifies the
         aggregator's ASN.

         When vRtrInetAggrAggregatorAS is set to non zero, and
         vRtrInetAggrAggregatorIPAddr is set to non-zero,
         the supplied ASN and IP address will be used for the
         aggregator path attributes.

         When vRtrInetAggrAggregatorAS is not set, the aggregate
         routes ASN & Router-ID will be used for the aggregator
         path attributes."
    DEFVAL { 0 }
    ::= { vRtrInetInstAggrEntry 8 }

vRtrInetAggrAggregatorIPAddr  OBJECT-TYPE
    SYNTAX      IpAddress
    MAX-ACCESS  read-create
    STATUS      current
    DESCRIPTION
        "The value of vRtrInetAggrAggregatorIPAddr specifies the
         aggregator's IP address.

         When vRtrInetAggrAggregatorAS is set to non zero, and
         vRtrInetAggrAggregatorIPAddr is set to non-zero,
         the supplied ASN and IP address will be used for the
         aggregator path attributes.

         When vRtrInetAggrAggregatorIPAddr is not set, the aggregate
         routes ASN & Router-ID will be used for the aggregator
         path attributes."
    DEFVAL { '00000000'H }  -- 0.0.0.0 means not-set
    ::= { vRtrInetInstAggrEntry 9 }

 vRtrInetAggrOperState  OBJECT-TYPE
    SYNTAX      TmnxOperState
    MAX-ACCESS  read-only
    STATUS      current
    DESCRIPTION
        "The value of vRtrInetAggrOperState specifies the current
         operational status of the aggregation entry."
    ::= { vRtrInetInstAggrEntry 10 }

--
--  Virtual Router Service Interface IP Address Range table
--  IP-version independent
--
vRtrInetSvcIpRangeTable  OBJECT-TYPE
    SYNTAX      SEQUENCE OF VRtrInetSvcIpRangeEntry
    MAX-ACCESS  not-accessible
    STATUS      current
    DESCRIPTION
        "The vRtrInetSvcIpRangeTable has an entry for each IP address
         range configured for a virtual interface in a virtual router
         in the system.  An interface on the virtual router may have
         more than one Service IP address range assigned to it."
    ::= { tmnxVRtrObjs 28 }

vRtrInetSvcIpRangeEntry  OBJECT-TYPE
    SYNTAX      VRtrInetSvcIpRangeEntry
    MAX-ACCESS  not-accessible
    STATUS      current
    DESCRIPTION
        "Each row entry represents an IP address range assigned a
         virtual router service interface. Setting RowStatus to
         'active' requires values for all column variables to have
         been assigned."
    INDEX { vRtrID,
            vRtrInetSvcIpRangeAddrType,
            vRtrInetSvcIpRangeAddr,
            vRtrInetSvcIpRangePfxLen
            }
    ::= { vRtrInetSvcIpRangeTable 1 }

VRtrInetSvcIpRangeEntry ::=
    SEQUENCE {
        vRtrInetSvcIpRangeAddrType   InetAddressType,
        vRtrInetSvcIpRangeAddr       InetAddress,
        vRtrInetSvcIpRangePfxLen     InetAddressPrefixLength,
        vRtrInetSvcIpRangeRowStatus  RowStatus,
        vRtrInetSvcIpRangeExclusive  TruthValue
    }

vRtrInetSvcIpRangeAddrType       OBJECT-TYPE
    SYNTAX      InetAddressType
    MAX-ACCESS  not-accessible
    STATUS      current
    DESCRIPTION
        "The value of vRtrInetSvcIpRangeAddrType indicates the IP
         address type of vRtrInetSvcIpRangeAddr."
    ::= { vRtrInetSvcIpRangeEntry 1 }

vRtrInetSvcIpRangeAddr  OBJECT-TYPE
    SYNTAX      InetAddress
    MAX-ACCESS  not-accessible
    STATUS      current
    DESCRIPTION
        "The value of vRtrInetSvcIpRangeAddr indicates the IP address
         service range assigned to a router's service interface. The
         address type of vRtrInetSvcIpRangeAddr is indicated by
         vRtrInetSvcIpRangeAddrType."
    ::= { vRtrInetSvcIpRangeEntry 2 }

vRtrInetSvcIpRangePfxLen  OBJECT-TYPE
    SYNTAX      InetAddressPrefixLength
    MAX-ACCESS  not-accessible
    STATUS      current
    DESCRIPTION
        "The value of vRtrInetSvcIpRangePfxLen specifies the prefix length
         to be used with vRtrInetSvcIpRangeAddr for determining the IP
         address range."
    ::= { vRtrInetSvcIpRangeEntry 3 }

vRtrInetSvcIpRangeRowStatus  OBJECT-TYPE
    SYNTAX      RowStatus
    MAX-ACCESS  read-create
    STATUS      current
    DESCRIPTION
        "The value of vRtrInetSvcIpRangeRowStatus is used for creation and
         deletion of IP service prefix ranges."
    ::= { vRtrInetSvcIpRangeEntry 4 }

vRtrInetSvcIpRangeExclusive  OBJECT-TYPE
    SYNTAX      TruthValue
    MAX-ACCESS  read-create
    STATUS      current
    DESCRIPTION
        "The value of vRtrInetSvcIpRangeExclusive specifies how the set
         of addresses specified by this entry are interpreted. When the
         value is 'true', they are reserved for services only and cannot be
         assigned to network ports.  When the value is 'false',
         it could be used for services as well as network ports."
    DEFVAL { false }
    ::= { vRtrInetSvcIpRangeEntry 5 }

--
--  Augmentation of the IP-MIB ipNetToPhysicalTable.
--  Use of AUGMENTS clause implies a one-to-one dependent relationship between
--  the base table, ipNetToPhysicalTable, and the augmenting table,
--  vRtrIpNetToPhysicalTable.  This in effect extends the ipNetToPhysicalTable
--  with additional columns.  Creation (or deletion) of a row in the
--  ipNetToPhysicalTable results in the same fate for the row in the
--  vRtrIpNetToPhysicalTable.
--

--  ALCATEL CHANG
--vRtrIpNetToPhysicalTable  OBJECT-TYPE
--    SYNTAX      SEQUENCE OF VRtrIpNetToPhysicalEntry
--    MAX-ACCESS  not-accessible
--    STATUS      current
--    DESCRIPTION
--        "The vRtrIpNetToPhysicalTable provides an extension of the
--         ipNetToPhysicalTable in the IP-MIB."
--    ::= { tmnxVRtrObjs 29 }
--
--vRtrIpNetToPhysicalEntry  OBJECT-TYPE
--    SYNTAX      VRtrIpNetToPhysicalEntry
--    MAX-ACCESS  not-accessible
--    STATUS      current
--    DESCRIPTION
--        "Each row entry in the vRtrIpNetToPhysicalTable represents additional
--         columns for attributes specific to the Alcatel 7x50 SR series
--         implementation for the vRtrIpNetToPhysicalTable."
--   AUGMENTS { ipNetToPhysicalEntry }
--   ::= { vRtrIpNetToPhysicalTable 1 }
--
--VRtrIpNetToPhysicalEntry ::=
--    SEQUENCE {
--        vRtrIpNetToPhysicalTimer        Unsigned32,
--        vRtrIpNetToPhysicalOperState    TmnxOperState,
--        vRtrIpNetToPhysicalIsRouter     TruthValue,
--        vRtrIpNetToPhysicalMTU          Unsigned32,
--        vRtrIpNetToPhysicalPort         TmnxPortID,
--        vRtrIpNetToPhysicalEncap        TmnxEncapVal
--        }
--
--vRtrIpNetToPhysicalTimer  OBJECT-TYPE
--    SYNTAX      Unsigned32 (0..65535)
--    UNITS       "seconds"
--    MAX-ACCESS  read-only
--    STATUS      current
--    DESCRIPTION
--         "The value of vRtrIpNetToPhysicalTimer indicates how much longer an ARP
--          entry associated with an vRtrIpNetToPhysicalTable entry remains in the
--          ARP cache. It is initially set to vRtrIfArpTimeout. When
--          vRtrIpNetToPhysicalTimer has a value of zero, '0', the entry is cleared
--          from the cache."
--     ::= { vRtrIpNetToPhysicalEntry 1 }
--
--vRtrIpNetToPhysicalOperState  OBJECT-TYPE
--    SYNTAX      TmnxOperState
--    MAX-ACCESS  read-only
--    STATUS      current
--    DESCRIPTION
--         "The value of vRtrIpNetToPhysicalOperState indicates if the ARP entry is
--          being used actively in the ARP Table. When ipNetToPhysicalType has a
--          value 'dynamic', vRtrIpNetToPhysicalOperState will never have a value of
--          'outOfService'."
--     ::= { vRtrIpNetToPhysicalEntry 2 }
--
--vRtrIpNetToPhysicalIsRouter OBJECT-TYPE
--    SYNTAX      TruthValue
--    MAX-ACCESS  read-only
--    STATUS      current
--    DESCRIPTION
--        "The value of vRtrIpNetToPhysicalIsRouter indicates whether this
--         ipNetToPhysicalEntry is a router."
--     ::= { vRtrIpNetToPhysicalEntry 3 }
--
--vRtrIpNetToPhysicalMTU  OBJECT-TYPE
--    SYNTAX      Unsigned32
--    MAX-ACCESS  read-only
--    STATUS      current
--    DESCRIPTION
--        "The value of vRtrIpNetToPhysicalMTU indicates the MTU of the link
--         attached to this ipNetToPhysicalEntry."
--     ::= { vRtrIpNetToPhysicalEntry 4 }
--
--vRtrIpNetToPhysicalPort OBJECT-TYPE
--    SYNTAX      TmnxPortID
--    MAX-ACCESS  read-only
--    STATUS      current
--    DESCRIPTION
--        "The value of vRtrIpNetToPhysicalPort indicates the ID of the port
--         on which this entry was learned."
--     ::= { vRtrIpNetToPhysicalEntry 5 }
--
--vRtrIpNetToPhysicalEncap        OBJECT-TYPE
--    SYNTAX      TmnxEncapVal
--    MAX-ACCESS  read-only
--    STATUS      current
--    DESCRIPTION
--        "The value of vRtrIpNetToPhysicalEncap indicates the encap value
--         of the SAP this entry was learned on. If this entry was learned
--         on a network port or null-encap SAP, the value of this object
--         will be zero."
--      ::= { vRtrIpNetToPhysicalEntry 6 }
--   ALCATEL CHANG

--  ALCATEL CHANG
--  Augmentation of the IP-FORWARD-MIB inetCidrRouteTable.
--  Use of AUGMENTS clause implies a one-to-one dependent relationship between
--  the base table, inetCidrRouteTable, and the augmenting table,
--  vRtrInetCidrRouteTable.  This in effect extends the inetCidrRouteTable with
--  additional columns.  Creation (or deletion) of a row in the
--  inetCidrRouteTable results in the same fate for the row in the
--  vRtrInetCidrRouteTable.
--

--vRtrInetCidrRouteTable  OBJECT-TYPE
--    SYNTAX      SEQUENCE OF VRtrInetCidrRouteEntry
--    MAX-ACCESS  not-accessible
--    STATUS      current
--    DESCRIPTION
--        "The vRtrInetCidrRouteTable provides an extension of the
--         inetCidrRouteTable in the IP-FORWARD-MIB."
--    ::= { tmnxVRtrObjs 30 }
--
--vRtrInetCidrRouteEntry  OBJECT-TYPE
--    SYNTAX      VRtrInetCidrRouteEntry
--    MAX-ACCESS  not-accessible
--    STATUS      current
--    DESCRIPTION
--        "Each row entry in the vRtrInetCidrRouteTable represents additional
--         columns for attributes specific to the Alcatel 7x50 SR series
--         implementation for the IP route table."
--   AUGMENTS { inetCidrRouteEntry }
--   ::= { vRtrInetCidrRouteTable 1 }
--
--VRtrInetCidrRouteEntry ::=
--    SEQUENCE {
--        vRtrInetCidrRouteLastEnabledTime   TimeStamp,
--        vRtrInetCidrRoutePreference        Unsigned32,
--        vRtrInetCidrRouteMetric            Unsigned32,
--        vRtrInetCidrRouteIfVRtrId          TmnxVRtrIDOrZero
--        }
--
--vRtrInetCidrRouteLastEnabledTime  OBJECT-TYPE
--    SYNTAX      TimeStamp
--    MAX-ACCESS  read-only
--    STATUS      current
--    DESCRIPTION
--        "The vRtrInetCidrRouteLastEnabledTime variable indicates the sysUpTime
--         value when ipCidrRouteStatus was last set to active (1) to
--         allow IP forwarding on this route entry."
--    ::= { vRtrInetCidrRouteEntry 1 }
--
--
--vRtrInetCidrRoutePreference  OBJECT-TYPE
--    SYNTAX      Unsigned32 (0..255)
--    MAX-ACCESS  read-only
--    STATUS      current
--    DESCRIPTION
--        "The value of vRtrInetCidrRoutePreference specifies the priority
--         of this static route versus the routes from different sources
--         such as BGP or OSPF etc, when ipCidrRouteProto has a value of
--         'netmgmt' to indicate that this entry is a static route.
--
--         Different protocols should not be configured with the same
--         preference, if this occurs the tiebreaker is determined per the
--         default preference value as defined in the table below.
--
--         If multiple routes are learned with an identical preference
--         using the same protocol, the lowest cost is used. If multiple
--         routes are learned with an identical preference using the same
--         protocol and the costs (metrics) are equal, then the decision
--         as to what route to use is determined by the configuration of
--         the ecmp command.
--
--         Default preferences:
--
--         Route Type             Preference      Configurable
--         ----------             ----------      ------------
--         Direct attached                 0                no
--         Static-route                    5               yes
--         MPLS (post FCS)                 7
--         OSPF Internal routes           10                no
--         OSPF External                 150               yes
--         BGP                           170               yes
--         "
--    DEFVAL { 5 }
--    ::= { vRtrInetCidrRouteEntry 2 }
--
--vRtrInetCidrRouteMetric  OBJECT-TYPE
--    SYNTAX      Unsigned32
--    MAX-ACCESS  read-only
--    STATUS      current
--    DESCRIPTION
--        "The value of vRtrInetCidrRouteMetric indicates the primary routing
--         metric  for this route. The semantics of this metric are determined
--         by the routing-protocol specified in the route's ipCidrRouteProto
--         value."
--    ::= { vRtrInetCidrRouteEntry 3 }
--
--vRtrInetCidrRouteIfVRtrId       OBJECT-TYPE
--    SYNTAX      TmnxVRtrIDOrZero
--    MAX-ACCESS  read-only
--    STATUS      current
--    DESCRIPTION
--        "The value of vRtrInetCidrRouteIfVRtrId indicates the virtual router
--         instance of the egress interface defined by inetCidrRouteIfIndex.
--         This object is valid only for subscriber management routes. For all
--         other route types, this object will have a value of zero."
--    ::= { vRtrInetCidrRouteEntry 4 }

--
-- Alcatel 7x50 SR series Virtual Router Global InterfaceIndex to
-- vRtrID and vRtrIfIndex Mapping Table
--  ALCATEL CHANG
vRtrIfGlobalIndexTable OBJECT-TYPE
    SYNTAX      SEQUENCE OF VRtrIfGlobalIndexEntry
    MAX-ACCESS  not-accessible
    STATUS      current
    DESCRIPTION
        "This is a read-only table, each row of which represents a one to
         one equivalence between a unique system wide router interface index
         (vRtrIfGlobalIndex) and its corresponding virtual router ID (vRtrID)
         and index in the vRtrIfTable (vRtrIfIndex)."
    ::= { tmnxVRtrObjs 37 }

vRtrIfGlobalIndexEntry OBJECT-TYPE
    SYNTAX      VRtrIfGlobalIndexEntry
    MAX-ACCESS  not-accessible
    STATUS      current
    DESCRIPTION
        "Each row entry in the vRtrIfGlobalIndexTable corresponds to a row
         in the vRtrIfTable. When an entry is created or deleted in the
         vRtrIfTable, a corresponding entry is created or deleted in this
         table."
    INDEX { vRtrIfGlobalIndex }
    ::= { vRtrIfGlobalIndexTable 1 }

VRtrIfGlobalIndexEntry ::=
    SEQUENCE {
        vRtrIfGlobalIndexvRtrID        TmnxVRtrID,
        vRtrIfGlobalIndexvRtrIfIndex   InterfaceIndex
        }

vRtrIfGlobalIndexvRtrID  OBJECT-TYPE
    SYNTAX      TmnxVRtrID
    MAX-ACCESS  read-only
    STATUS      current
    DESCRIPTION
        "The value of vRtrIfGlobalIndexvRtrID indicates the vRtrID that
         maps to the vRtrIfGlobalIndex. The combination of a vRtrID and
         a vRtrIfIndex correspond to a system wide unique vRtrIfGlobalIndex.
         This value represents the specific instance of virtual router
         which the vRtrIfGlobalIndex belongs to."
    ::= { vRtrIfGlobalIndexEntry 1 }

vRtrIfGlobalIndexvRtrIfIndex  OBJECT-TYPE
    SYNTAX      InterfaceIndex
    MAX-ACCESS  read-only
    STATUS      current
    DESCRIPTION
        "The value of vRtrIfGlobalIndexvRtrIfIndex gives the value of
         vRtrIfIndex for a row in the vRtrIfTable. This row corresponds
         to the virtual router interface that maps to the
         vRtrIfGlobalIndex. The combination of a vRtrID and
         a vRtrIfIndex correspond to a system wide unique vRtrIfGlobalIndex."
    ::= { vRtrIfGlobalIndexEntry 2 }


--
--  Alcatel 7x50 SR series Virtual Router Interface Proxy Neigbor
--  Discovery Table
--
--  Augmentation of the vRtrIfTable.
--  Use of AUGMENTS clause implies a one-to-one dependent relationship
--  between the base table, vRtrIfTable, and the augmenting table,
--  vRtrIfProxyNDTable. This in effect extends the vRtrIfTable with
--  additional columns. Creation (or deletion) of a row in the
--  vRtrIfTable results in the same fate for the row in the
--  vRtrIfProxyNDTable.
--

vRtrIfProxyNDTable  OBJECT-TYPE
    SYNTAX      SEQUENCE OF VRtrIfProxyNDEntry
    MAX-ACCESS  not-accessible
    STATUS      current
    DESCRIPTION
        "The vRtrIfProxyNDTable provides an extension to the vRtrIfTable.
         It has an entry for each virtual router interface configured in
         the system."
    ::= { tmnxVRtrObjs 38 }

vRtrIfProxyNDEntry  OBJECT-TYPE
    SYNTAX      VRtrIfProxyNDEntry
    MAX-ACCESS  not-accessible
    STATUS      current
    DESCRIPTION
        "Each row entry represents information related to Proxy Neighbor
         Discovery for a virtual router interface in the system.

         Entries cannot be created and deleted via SNMP SET operations."
    AUGMENTS { vRtrIfEntry }
    ::= { vRtrIfProxyNDTable 1 }

VRtrIfProxyNDEntry ::=
    SEQUENCE {
        vRtrIfProxyNDLocal         TruthValue,
        vRtrIfProxyNDPolicy1       TPolicyStatementNameOrEmpty,
        vRtrIfProxyNDPolicy2       TPolicyStatementNameOrEmpty,
        vRtrIfProxyNDPolicy3       TPolicyStatementNameOrEmpty,
        vRtrIfProxyNDPolicy4       TPolicyStatementNameOrEmpty,
        vRtrIfProxyNDPolicy5       TPolicyStatementNameOrEmpty
        }

vRtrIfProxyNDLocal  OBJECT-TYPE
    SYNTAX      TruthValue
    MAX-ACCESS  read-create
    STATUS      current
    DESCRIPTION
        "If the value of vRtrIfProxyNDLocal is set to 'true', local proxy
         Neighbor Discovery is enabled, that is, the interface will reply to
         Neighbor Solicitation requests when both the hosts are on the same
         subnet. In this case ICMP redirects will be disabled. If the value
         of vRtrIfProxyNDLocal is set to 'false', the interface will not
         reply to Neighbor Solicitation requests if both the hosts are on the
         same subnet."
    DEFVAL { false }
    ::= { vRtrIfProxyNDEntry 1 }

vRtrIfProxyNDPolicy1    OBJECT-TYPE
    SYNTAX      TPolicyStatementNameOrEmpty
    MAX-ACCESS  read-create
    STATUS      current
    DESCRIPTION
        "The value of vRtrIfProxyNDPolicy1 specifies the first proxy ND
         policy for this interface. This policy determines networks and
         sources for which proxy ND will be attempted, when local proxy
         ND is enabled."
    DEFVAL      { ''H }
    ::= { vRtrIfProxyNDEntry 2 }

vRtrIfProxyNDPolicy2    OBJECT-TYPE
    SYNTAX      TPolicyStatementNameOrEmpty
    MAX-ACCESS  read-create
    STATUS      current
    DESCRIPTION
        "The value of vRtrIfProxyNDPolicy2 specifies the second proxy ND
         policy for this interface. This policy determines networks and
         sources for which proxy ND will be attempted, when local proxy
         ND is enabled."
    DEFVAL      { ''H }
    ::= { vRtrIfProxyNDEntry 3 }

vRtrIfProxyNDPolicy3    OBJECT-TYPE
    SYNTAX      TPolicyStatementNameOrEmpty
    MAX-ACCESS  read-create
    STATUS      current
    DESCRIPTION
        "The value of vRtrIfProxyNDPolicy3 specifies the third proxy ND
         policy for this interface. This policy determines networks and
         sources for which proxy ND will be attempted, when local proxy
         ND is enabled."
    DEFVAL      { ''H }
    ::= { vRtrIfProxyNDEntry 4 }

vRtrIfProxyNDPolicy4    OBJECT-TYPE
    SYNTAX      TPolicyStatementNameOrEmpty
    MAX-ACCESS  read-create
    STATUS      current
    DESCRIPTION
        "The value of vRtrIfProxyNDPolicy4 specifies the fourth proxy ND
         policy for this interface. This policy determines networks and
         sources for which proxy ND will be attempted, when local proxy
         ND is enabled."
    DEFVAL      { ''H }
    ::= { vRtrIfProxyNDEntry 5 }

vRtrIfProxyNDPolicy5    OBJECT-TYPE
    SYNTAX      TPolicyStatementNameOrEmpty
    MAX-ACCESS  read-create
    STATUS      current
    DESCRIPTION
        "The value of vRtrIfProxyNDPolicy5 specifies the fifth proxy ND
         policy for this interface. This policy determines networks and
         sources for which proxy ND will be attempted, when local proxy
         ND is enabled."
    DEFVAL      { ''H }
    ::= { vRtrIfProxyNDEntry 6 }

--
--  Alcatel 7x50 SR series
--  Virtual Router DHCP6 prefix Delegation table
--
vRtrIfDHCP6PfxDelegationLstChgd  OBJECT-TYPE
    SYNTAX      TimeStamp
    MAX-ACCESS  read-only
    STATUS      current
    DESCRIPTION
        "The value of the object vRtrIfDHCP6PfxDelegationLstChgd indicates
         the Timestamp of the last change to any row the
         vRtrIfDHCP6PfxDelegationTable"
    ::= { tmnxVRtrObjs 39 }

vRtrIfDHCP6PfxDelegationTable  OBJECT-TYPE
    SYNTAX      SEQUENCE OF VRtrIfDHCP6PfxDelegationEntry
    MAX-ACCESS  not-accessible
    STATUS      current
    DESCRIPTION
        "The table vRtrIfDHCP6PfxDelegationTable is used to configure
         the feature of automated delegation of IPv6 prefixes using DHCP6.

         This feature is intended for delegating a long-lived prefix from
         a delegating router to a requesting router, where the delegating
         router does not require knowledge about the topology of the
         links in the network to which the prefixes will be assigned."
    ::= { tmnxVRtrObjs 40 }

vRtrIfDHCP6PfxDelegationEntry  OBJECT-TYPE
    SYNTAX      VRtrIfDHCP6PfxDelegationEntry
    MAX-ACCESS  not-accessible
    STATUS      current
    DESCRIPTION
        "Each row entry represents a delegated IPv6 prefix.
         Entries can be created and deleted via SNMP SET operations.
         Creation requires a SET request containing the vRtrRowStatus."
    INDEX { vRtrID,
            vRtrIfIndex,
            vRtrIfDHCP6PfxdPrefix,
            vRtrIfDHCP6PfxdPrefixLen }
    ::= { vRtrIfDHCP6PfxDelegationTable 1 }

VRtrIfDHCP6PfxDelegationEntry ::=
    SEQUENCE {
        vRtrIfDHCP6PfxdPrefix         InetAddressIPv6,
        vRtrIfDHCP6PfxdPrefixLen      InetAddressPrefixLength,
        vRtrIfDHCP6PfxdRowStatus      RowStatus,
        vRtrIfDHCP6PfxdLastChanged    TimeStamp,
        vRtrIfDHCP6PfxdDUID           OCTET STRING,
        vRtrIfDHCP6PfxdIAID           Unsigned32,
        vRtrIfDHCP6PfxdPrefLifetime   Unsigned32,
        vRtrIfDHCP6PfxdValidLifetime  Unsigned32
    }

vRtrIfDHCP6PfxdPrefix  OBJECT-TYPE
    SYNTAX      InetAddressIPv6
    MAX-ACCESS  not-accessible
    STATUS      current
    DESCRIPTION
        "The value of the object vRtrIfDHCP6PfxdPrefix specifies,
         together with the object vRtrIfDHCP6PfxdPrefixLen the ipv6
         prefix that will be delegated."
    ::= { vRtrIfDHCP6PfxDelegationEntry 1 }

vRtrIfDHCP6PfxdPrefixLen  OBJECT-TYPE
    SYNTAX      InetAddressPrefixLength
    MAX-ACCESS  not-accessible
    STATUS      current
    DESCRIPTION
        "The value of the object vRtrIfDHCP6PfxdPrefixLen specifies,
         together with the object vRtrIfDHCP6PfxdPrefix the ipv6
         prefix that will be delegated by this system."
    ::= { vRtrIfDHCP6PfxDelegationEntry 2 }

vRtrIfDHCP6PfxdRowStatus  OBJECT-TYPE
    SYNTAX      RowStatus
    MAX-ACCESS  read-create
    STATUS      current
    DESCRIPTION
        "The value of the object vRtrIfDHCP6PfxdRowStatus specifies the
         Row status of this table row. This object is used to create or
         delete rows in this table.

         The only allowed values for this object are: active(1),
         createAndGo(4), and destroy(6)."
    ::= { vRtrIfDHCP6PfxDelegationEntry 3 }

vRtrIfDHCP6PfxdLastChanged  OBJECT-TYPE
    SYNTAX      TimeStamp
    MAX-ACCESS  read-only
    STATUS      current
    DESCRIPTION
        "The value of vRtrIfDHCP6PfxdLastChanged indicates the sysUpTime
         when any object of the row is last changed."
    ::= { vRtrIfDHCP6PfxDelegationEntry 4 }

vRtrIfDHCP6PfxdDUID  OBJECT-TYPE
    SYNTAX      OCTET STRING (SIZE (0..64))
    MAX-ACCESS  read-create
    STATUS      current
    DESCRIPTION
        "The value of the object vRtrIfDHCP6PfxdDUID specifies
         the ID of the requesting router. If set to a non zero value
         the prefix defined in this row will only be delegated to this
         router. If set to zero, the prefix will be delegated to any
         requesting router."
    DEFVAL { ''H }      -- the empty string
    ::= { vRtrIfDHCP6PfxDelegationEntry 6 }

vRtrIfDHCP6PfxdIAID  OBJECT-TYPE
    SYNTAX      Unsigned32
    MAX-ACCESS  read-create
    STATUS      current
    DESCRIPTION
        "The value of the object vRtrIfDHCP6PfxdIAID specifies
         the IAID from the requesting router
         that needs to match in order to delegate the prefix defined
         in this row.If set to 0 no match on the received IAID is done."
    DEFVAL { 0 }
    ::= { vRtrIfDHCP6PfxDelegationEntry 7 }

vRtrIfDHCP6PfxdPrefLifetime  OBJECT-TYPE
    SYNTAX      Unsigned32 (0..4294967295)
    UNITS       "seconds"
    MAX-ACCESS  read-create
    STATUS      current
    DESCRIPTION
        "The value of the object vRtrIfDHCP6PfxdPrefLifetime specifies
         the time in seconds that this prefix remains preferred.

         The value of vRtrIfDHCP6PfxdPrefLifetime cannot be bigger then
         the value of vRtrIfDHCP6PfxdValidLifetime.

         The value 4294967295 is considered equal to infinity."
    DEFVAL { 604800 } -- 7 days
    ::= { vRtrIfDHCP6PfxDelegationEntry 8 }

vRtrIfDHCP6PfxdValidLifetime  OBJECT-TYPE
    SYNTAX      Unsigned32 (0..4294967295)
    UNITS       "seconds"
    MAX-ACCESS  read-create
    STATUS      current
    DESCRIPTION
        "The value of the object vRtrIfDHCP6PfxdValidLifetime specifies
         the time in seconds that the prefix is valid.
         The value 4294967295 is considered equal to infinity."
    DEFVAL { 2592000 } -- 30 days
    ::= { vRtrIfDHCP6PfxDelegationEntry 9 }

--
--  Alcatel 7x50 SR series Virtual Router DHCP6 Statistics Table
--
vRtrDHCP6DropStatTable OBJECT-TYPE
    SYNTAX      SEQUENCE OF VRtrDHCP6DropStatEntry
    MAX-ACCESS  not-accessible
    STATUS      current
    DESCRIPTION
        "The vRtrDHCP6DropStatTable has an entry for each virtual router
         configured in the system."
    ::= { tmnxVRtrObjs 41 }

vRtrDHCP6DropStatEntry  OBJECT-TYPE
    SYNTAX      VRtrDHCP6DropStatEntry
    MAX-ACCESS  not-accessible
    STATUS      current
    DESCRIPTION
        "Each row entry represents a collection of DHCP6 drop reason
         statistics for a virtual router in the system.

        Entries cannot be created and deleted via SNMP SET operations."
    INDEX { vRtrID,
            vRtrDHCP6DropStatReason }
    ::= { vRtrDHCP6DropStatTable 1 }

VRtrDHCP6DropStatEntry ::=
     SEQUENCE {
         vRtrDHCP6DropStatReason      INTEGER,
         vRtrDHCP6DropStatLastCleared TimeStamp,
         vRtrDHCP6DropStatPktsDropped Gauge32
     }

vRtrDHCP6DropStatReason  OBJECT-TYPE
    SYNTAX INTEGER {
               none                 ( 0 ),
               srcOperDown          ( 1 ),
               dstOperDown          ( 2 ),
               rlyReplyOnClientItf  ( 3 ),
               hopCount             ( 4 ),
               badRelayedMsg        ( 5 ),
               clientItfNotFound    ( 6 ),
               noMemory             ( 7 ),
               noGlobalPfx          ( 8 ),
               noSrcIp              ( 9 ),
               noRteToServer        ( 10 ),
               subMgmtUpdFail       ( 11 ),
               relayForw            ( 12 ),
               msgTooSmall          ( 13 ),
               msgNotForServer      ( 14 ),
               noServerId           ( 15 ),
               noClientId           ( 16 ),
               serverIdInClientMsg  ( 17 ),
               wrongServerId        ( 18 ),
               illegalUnicast       ( 19 ),
               illegalSrcIp         ( 20 ),
               pdMsgNotSupported    ( 21 ),
               nbrAddrsExceeded     ( 22 ),
               clientMacNotResolved ( 23 ),
               illegalAssignedAddr  ( 24 ),
               msgEncodingError   ( 25 )
           }
    MAX-ACCESS  not-accessible
    STATUS      current
    DESCRIPTION
        "The object vRtrDHCP6DropStatReason indicates the drop reason for
         which the object vRtrDHCP6DropStatPktsDropped contains the counter.
         none
         srcOperDown            Dhcp6 oper state is not Up on src itf
         dstOperDown            Dhcp6 oper state is not Up on dst itf
         rlyReplyOnClientItf    Relay Reply Msg on Client Itf
         hopCount               Hop Count Limit reached
         badRelayedMsg          Missing Relay Msg option, or illegal msg type
         clientItfNotFound      Unable to determine destinatinon client Itf
         noMemory               Out of Memory
         noGlobalPfx            No global Pfx on Client Itf
         noSrcIp                Unable to determine src Ip Addr
         noRteToServer          No route to server
         subMgmtUpdFail         Subscr. Mgmt. Update failed
         relayForw              Received Relay Forw Message
         msgTooSmall            Packet too small to contain valid dhcp6 msg
         msgNotForServer        Server cannot respond to this message
         noServerId             No Server Id option in msg from server
         noClientId             No Client Id option in msg from client
         serverIdInClientMsg    Server Id option in client msg
         wrongServerId          Server DUID in client msg does not match ours
         illegalUnicast         Client sent message to unicast while not
                                allowed
         illegalSrcIp           Client sent message with illegal src Ip
         pdMsgNotSupported      Client message type not supported in
                                pfx delegation
         nbrAddrsExceeded       Nbr of addrs or pfxs exceeds allowed
                                maximum in msg
         clientMacNotResolved   Unable to resolve client's mac address
         illegalAssignedAddr    The client was assigned an illegal address
         msgEncodingError       Illegal pfx length in a IA_PREFIX option
        "
    ::= { vRtrDHCP6DropStatEntry 1 }

vRtrDHCP6DropStatLastCleared  OBJECT-TYPE
    SYNTAX      TimeStamp
    MAX-ACCESS  read-only
    STATUS      current
    DESCRIPTION
        "The value of vRtrDHCP6DropStatLastCleared indicates the sysUpTime
         when the counters of this row were last reset. A value of zero for
         this object indicates that the counters have not been reset since the
         system has last been initialized."
    ::= { vRtrDHCP6DropStatEntry 2 }

vRtrDHCP6DropStatPktsDropped  OBJECT-TYPE
    SYNTAX      Gauge32
    MAX-ACCESS  read-only
    STATUS      current
    DESCRIPTION
        "The value of vRtrDHCP6DropStatPktsDropped indicates the number of
         DHCP6 packets were dropped for the reason described in
         vRtrDHCP6DropStatReason."
    ::= { vRtrDHCP6DropStatEntry 3 }

--
--  Alcatel 7x50 SR series Virtual Router DHCP6 msg type Statistics Table
--
vRtrDHCP6MsgStatTable OBJECT-TYPE
    SYNTAX  SEQUENCE OF VRtrDHCP6MsgStatEntry
    MAX-ACCESS  not-accessible
    STATUS      current
    DESCRIPTION
        "The vRtrDHCP6MsgStatTable has an entry for each virtual router
         configured in the system."
    ::= { tmnxVRtrObjs 42 }

vRtrDHCP6MsgStatEntry  OBJECT-TYPE
    SYNTAX      VRtrDHCP6MsgStatEntry
    MAX-ACCESS  not-accessible
    STATUS      current
    DESCRIPTION
        "Each row entry represents a collection of counters for each DHCP6
         message type for a virtual router in the system.

        Entries cannot be created and deleted via SNMP SET operations."
    INDEX { vRtrID,
            vRtrDHCP6MsgStatsMsgType }
    ::= { vRtrDHCP6MsgStatTable 1 }

VRtrDHCP6MsgStatEntry ::=
     SEQUENCE {
         vRtrDHCP6MsgStatsMsgType  TmnxDHCP6MsgType,
         vRtrDHCP6MsgStatsLstClrd  TimeStamp,
         vRtrDHCP6MsgStatsRcvd     Gauge32,
         vRtrDHCP6MsgStatsSent     Gauge32,
         vRtrDHCP6MsgStatsDropped  Gauge32
     }

vRtrDHCP6MsgStatsMsgType  OBJECT-TYPE
    SYNTAX      TmnxDHCP6MsgType
    MAX-ACCESS  not-accessible
    STATUS      current
    DESCRIPTION
        "The object vRtrDHCP6MsgStatsMsgType indicates the DHCP6 message type
         for which statistics are kept on a per vrtr basis."
    ::= { vRtrDHCP6MsgStatEntry 1 }

vRtrDHCP6MsgStatsLstClrd  OBJECT-TYPE
    SYNTAX      TimeStamp
    MAX-ACCESS  read-only
    STATUS      current
    DESCRIPTION
        "The value of vRtrDHCP6MsgStatsLstClrd indicates the sysUpTime
         when the counters of this row were last reset. A value of zero for
         this object indicates that the counters have not been reset since the
         system has last been initialized."
    ::= { vRtrDHCP6MsgStatEntry 2 }

vRtrDHCP6MsgStatsRcvd  OBJECT-TYPE
    SYNTAX      Gauge32
    MAX-ACCESS  read-only
    STATUS      current
    DESCRIPTION
        "The value of vRtrDHCP6MsgStatsRcvd indicates the number of
         DHCP6 packets were received of the DHCP6 message type indicated by
         vRtrDHCP6MsgStatsMsgType."
    ::= { vRtrDHCP6MsgStatEntry 3 }

vRtrDHCP6MsgStatsSent  OBJECT-TYPE
    SYNTAX      Gauge32
    MAX-ACCESS  read-only
    STATUS      current
    DESCRIPTION
        "The value of vRtrDHCP6MsgStatsSent indicates the number of
         DHCP6 packets were sent of the DHCP6 message type indicated by
         vRtrDHCP6MsgStatsMsgType."
    ::= { vRtrDHCP6MsgStatEntry 4 }

vRtrDHCP6MsgStatsDropped  OBJECT-TYPE
    SYNTAX      Gauge32
    MAX-ACCESS  read-only
    STATUS      current
    DESCRIPTION
        "The value of vRtrDHCP6MsgStatsDropped indicates the number of
         DHCP6 packets were dropped of the DHCP6 message type indicated by
         vRtrDHCP6MsgStatsMsgType."
    ::= { vRtrDHCP6MsgStatEntry 5 }

--
--  Virtual Router Interface IPCP table
--  Use of AUGMENTS clause implies a one-to-one dependent relationship
--  between the base table, vRtrIfTable, and the augmenting table,
--  vRtrIfIpcpTable. This in effect extends the vRtrIfTable with
--  additional columns. Creation (or deletion) of a row in the
--  vRtrIfTable results in the same fate for the row in the
--  vRtrIfIpcpTable.
--

vRtrIfIpcpTable OBJECT-TYPE
    SYNTAX     SEQUENCE OF VRtrIfIpcpEntry
    MAX-ACCESS not-accessible
    STATUS     current
    DESCRIPTION
        "The vRtrIfIpcpTable table contains the configuration for
         IPCP interface configuration on the vRtrIfEntry
         with the same indices."
    ::= { tmnxVRtrObjs 43 }

vRtrIfIpcpEntry OBJECT-TYPE
    SYNTAX     VRtrIfIpcpEntry
    MAX-ACCESS not-accessible
    STATUS     current
    DESCRIPTION
        "Each row entry represents the IPCP configuration for an
         interface. Entries are created and deleted when entries
         in the vRtrIfTable are created and deleted."
    AUGMENTS { vRtrIfEntry }
    ::= { vRtrIfIpcpTable 1 }

VRtrIfIpcpEntry ::=
    SEQUENCE {
        vRtrIfIpcpPeerAddrType      InetAddressType,
        vRtrIfIpcpPeerAddr          InetAddress,
        vRtrIfIpcpPriDnsAddrType    InetAddressType,
        vRtrIfIpcpPriDnsAddr        InetAddress,
        vRtrIfIpcpSecDnsAddrType    InetAddressType,
        vRtrIfIpcpSecDnsAddr        InetAddress
    }

vRtrIfIpcpPeerAddrType  OBJECT-TYPE
    SYNTAX      InetAddressType
    MAX-ACCESS  read-create
    STATUS      current
    DESCRIPTION
        "The value of vRtrIfIpcpPeerAddrType specifies the type of
         vRtrIfIpcpPeerAddr, the remote peer's IP address.         
         
         vRtrIfIpcpPeerAddrType can be set to non-default only when the 
         following rules are met for objects in vRtrIfEntry with the same 
         indices:
          - The value of vRtrIfType is set to serviceIes(3) or serviceVprn(5)
          - The value of tmnxPortEncapType in tmnxPortEntry indexed using
            the value of vRtrIfPortID is set to unknown (0) or nullEncap (1) 
            or ipcpEncap (6)
         
         When the value of vRtrIfIpcpPeerAddrType is unknown, the value of 
         vRtrIfIpcpPeerAddr is assumed to be of size 0."
    DEFVAL { unknown }
    ::= { vRtrIfIpcpEntry 1 }
    
vRtrIfIpcpPeerAddr     OBJECT-TYPE
    SYNTAX      InetAddress (SIZE(0|4|16))
    MAX-ACCESS  read-create
    STATUS      current
    DESCRIPTION
        "The value of vRtrIfIpcpPeerAddr specifies the IP address that will
         be exchanged by IPCP, if applicable on a given interface, to configure
         the remote peer's IP address. The type of this address is specified 
         by the value of vRtrIfIpcpPeerAddrType
         
         vRtrIfIpcpPeerAddr can be set to on-default only when the following 
         rules are met for objects in vRtrIfEntry with the same indices:
          - The value of vRtrIfType is set to serviceIes(3) or serviceVprn(5)
          - The value of tmnxPortEncapType in tmnxPortEntry indexed using
            the value of vRtrIfPortID is set to unknown (0) or nullEncap (1)
            or ipcpEncap (6)"
    DEFVAL { ''H } 
    ::= { vRtrIfIpcpEntry 2 }

vRtrIfIpcpPriDnsAddrType  OBJECT-TYPE
    SYNTAX      InetAddressType
    MAX-ACCESS  read-create
    STATUS      current
    DESCRIPTION
        "The value of vRtrIfIpcpPriDnsAddrType specifies the type of
         vRtrIfIpcpPriDnsAddr, the IP address of the primary DNS to be used 
         by the remote peer.         
         
         vRtrIfIpcpPriDnsAddrType can be set ito non-default only when the 
         following rules are met for objects in vRtrIfEntry with the same 
         indices:
          - The value of vRtrIfType is set to serviceIes(3) or serviceVprn(5)
          - The value of tmnxPortEncapType in tmnxPortEntry indexed using
            the value of vRtrIfPortID is set to unknown (0) or nullEncap (1) 
            or ipcpEncap (6)
 
         When the value of vRtrIfIpcpPriDnsAddrType is unknown, the value of 
         vRtrIfIpcpPriDnsAddr is assumed to be of size 0."
    DEFVAL { unknown }
    ::= { vRtrIfIpcpEntry 3 }

vRtrIfIpcpPriDnsAddr       OBJECT-TYPE
    SYNTAX      InetAddress (SIZE(0|4|16))
    MAX-ACCESS  read-create
    STATUS      current
    DESCRIPTION
        "The value of vRtrIfIpcpPriDnsAddr specifies the IP address that will
         be exchanged by IPCP, if applicable on a given interface, to configure
         the primary DNS's IP address on the remote peer. The type of this 
         address is specified by the value of vRtrIfIpcpPriDnsAddrType
         
         vRtrIfIpcpPriDnsAddr can be set to non-default only when the following 
         rules are met for objects in vRtrIfEntry with the same indices:
          - The value of vRtrIfType is set to serviceIes(3) or serviceVprn(5)
          - The value of tmnxPortEncapType in tmnxPortEntry indexed using
            the value of vRtrIfPortID is set to unknown (0) or nullEncap (1)
            or ipcpEncap (6)" 
    DEFVAL { ''H } 
    ::= { vRtrIfIpcpEntry 4 }

vRtrIfIpcpSecDnsAddrType  OBJECT-TYPE
    SYNTAX      InetAddressType
    MAX-ACCESS  read-create
    STATUS      current
    DESCRIPTION
        "The value of vRtrIfIpcpSecDnsAddrType specifies the type of
         vRtrIfIpcpSecDnsAddr, the IP address of the secondary DNS to be used 
         by the remote peer.         
         
         vRtrIfIpcpSecDnsAddrType can be set to non-deffault only when the 
         following rules are met for objects in vRtrIfEntry with the same 
         indices:
          - The value of vRtrIfType is set to serviceIes(3) or serviceVprn(5)
          - The value of tmnxPortEncapType in tmnxPortEntry indexed using
            the value of vRtrIfPortID is set to unknown (0) or nullEncap (1) 
            or ipcpEncap (6)
          
         When the value of vRtrIfIpcpSecDnsAddrType is unknown, the value of 
         vRtrIfIpcpSecDnsAddr is assumed to be of size 0."
    DEFVAL { unknown }
    ::= { vRtrIfIpcpEntry 5 }

vRtrIfIpcpSecDnsAddr        OBJECT-TYPE
    SYNTAX      InetAddress (SIZE(0|4|16))
    MAX-ACCESS  read-create
    STATUS      current
    DESCRIPTION
        "The value of vRtrIfIpcpSecDnsAddr specifies the IP address that will
         be exchanged by IPCP, if applicable on a given interface, to configure
         the secondary DNS's IP address on the remote peer. The type of this 
         address is specified by the value of vRtrIfIpcpSecDnsAddrType.
         
         vRtrIfIpcpSecDnsAddr can be set to non-default only when the following 
         rules are met for objects in vRtrIfEntry with the same indices:
          - The value of vRtrIfType is set to serviceIes(3) or serviceVprn(5)
          - The value of tmnxPortEncapType in tmnxPortEntry indexed using
            the value of vRtrIfPortID is set to unknown (0) or nullEncap (1)
            or ipcpEncap (6)"
    DEFVAL { ''H } 
    ::= { vRtrIfIpcpEntry 6 }

--
--  Alcatel 7x50 SR series Virtual Router Static Route CPE Check Statistics Table
--
vRtrInetStatRteCpeChkStatsTable  OBJECT-TYPE
    SYNTAX      SEQUENCE OF VRtrInetStatRteCpeChkStatsEntry
    MAX-ACCESS  not-accessible
    STATUS      current
    DESCRIPTION
        "The vRtrInetStatRteCpeChkStatsTable has an entry for each entry
         in the vRtrInetStaticRouteTable that has a non-default values set
         for the vRtrInetStaticRouteCpeAddrType and vRtrInetStaticRouteCpeAddr
         objects."
    ::= { tmnxVRtrObjs 44 }

vRtrInetStatRteCpeChkStatsEntry OBJECT-TYPE
    SYNTAX      VRtrInetStatRteCpeChkStatsEntry
    MAX-ACCESS  not-accessible
    STATUS      current
    DESCRIPTION
        "Each row entry represents a collection of
         Customer-Provided Equipment (CPE) availability statistics
         for a virtual router static route in the system with non-default
         values set for the vRtrInetStaticRouteCpeAddrType and
         vRtrInetStaticRouteCpeAddr objects.

         Entries cannot be created and deleted via SNMP SET operations."
    INDEX {
        vRtrID,
        vRtrInetStaticRouteDestType,
        vRtrInetStaticRouteDest,
        vRtrInetStaticRouteDestPfxLen,
        vRtrInetStaticRouteIndex
        }
    ::= { vRtrInetStatRteCpeChkStatsTable 1 }

VRtrInetStatRteCpeChkStatsEntry ::=
    SEQUENCE {
        vRtrInetStatRteCpeChkUpTime       TimeTicks,
        vRtrInetStatRteCpeChkInPktCnt     Counter32,
        vRtrInetStatRteCpeChkOutPktCnt    Counter32,
        vRtrInetStatRteCpeChkDownTrans    Gauge32,
        vRtrInetStatRteCpeChkUpTrans      Gauge32,
        vRtrInetStatRteCpeChkTTL          Unsigned32
    }

vRtrInetStatRteCpeChkUpTime OBJECT-TYPE
    SYNTAX      TimeTicks
    MAX-ACCESS  read-only
    STATUS      current
    DESCRIPTION
        "The value of vRtrInetStatRteCpeChkUpTime indicates
         how long (in hundredths of a second) that the CPE has been
         available."
    ::= { vRtrInetStatRteCpeChkStatsEntry 1 }

vRtrInetStatRteCpeChkInPktCnt        OBJECT-TYPE
    SYNTAX      Counter32
    MAX-ACCESS  read-only
    STATUS      current
    DESCRIPTION
        "The value of vRtrInetStatRteCpeChkInPktCnt indicates the 
         number of echo-reply packets received."
    ::= { vRtrInetStatRteCpeChkStatsEntry 2 }

vRtrInetStatRteCpeChkOutPktCnt       OBJECT-TYPE
    SYNTAX      Counter32
    MAX-ACCESS  read-only
    STATUS      current
    DESCRIPTION
        "The value of vRtrInetStatRteCpeChkOutPktCnt indicates the 
         number of echo-request packets sent."
    ::= { vRtrInetStatRteCpeChkStatsEntry 3 }

vRtrInetStatRteCpeChkDownTrans OBJECT-TYPE
    SYNTAX          Gauge32
    MAX-ACCESS      read-only
    STATUS          current
    DESCRIPTION
        "The value of vRtrInetStatRteCpeChkDownTrans indicates the number of
         times the CPE has transitioned to the unavailable state."
    ::= { vRtrInetStatRteCpeChkStatsEntry 4 }

vRtrInetStatRteCpeChkUpTrans OBJECT-TYPE
    SYNTAX          Gauge32
    MAX-ACCESS      read-only
    STATUS          current
    DESCRIPTION
        "The value of vRtrInetStatRteCpeChkUpTrans indicates the number of
         times the CPE has transitioned to the available state."
    ::= { vRtrInetStatRteCpeChkStatsEntry 5 }

vRtrInetStatRteCpeChkTTL       OBJECT-TYPE
    SYNTAX      Unsigned32
    UNITS       "seconds"
    MAX-ACCESS  read-only
    STATUS      current
    DESCRIPTION
        "The value of vRtrInetStatRteCpeChkTTL indicates the time, in seconds,
         before the CPE will be declared down. Upon receipt of an echo
         reply, it has the value of 
         vRtrInetStaticRouteCpeInterval * vRtrInetStaticRouteCpeDropCnt and is
         decremented by 1 every second."
    ::= { vRtrInetStatRteCpeChkStatsEntry 6 }


--
-- Application Id -> DSCP value mapping table
--

tmnxDscpAppTableLastChanged OBJECT-TYPE
    SYNTAX      TimeStamp
    MAX-ACCESS  read-only
    STATUS      current
    DESCRIPTION
        "The value of tmnxDscpAppTableLastChanged indicates the sysUpTime
         at the time of the last modification of tmnxDscpAppTable.

         If no changes were made to the table since the last
         re-initialization of the local network management subsystem,
         then this object contains a zero value."
    ::= { tmnxVRtrObjs 45 }

tmnxDscpAppTable OBJECT-TYPE
    SYNTAX      SEQUENCE OF TmnxDscpAppEntry
    MAX-ACCESS  not-accessible
    STATUS      current
    DESCRIPTION
        "The tmnxDscpAppTable has an entry for each application to
         Differential Services Code Point (DSCP) mapping in a
         virtual routing context on this system."
    ::= { tmnxVRtrObjs 46 }

tmnxDscpAppEntry    OBJECT-TYPE
    SYNTAX      TmnxDscpAppEntry
    MAX-ACCESS  not-accessible
    STATUS      current
    DESCRIPTION
        "Each row represents a mapping from an application to a DSCP
         value for particular virtual routing context.

         Entries are created at system initialization."
    INDEX { vRtrID, tmnxDscpAppId }
    ::= { tmnxDscpAppTable 1}

TmnxDscpAppEntry ::= SEQUENCE
    {
        tmnxDscpAppId          TDSCPAppId,
        tmnxDscpAppLastChanged TimeStamp,
        tmnxDscpAppDscpValue   TDSCPValueOrNone
    }

tmnxDscpAppId      OBJECT-TYPE
    SYNTAX      TDSCPAppId
    MAX-ACCESS  not-accessible
    STATUS      current
    DESCRIPTION
        "The value of tmnxDscpAppId indicates the DSCP application identifier
         for a protocol on the Alcatel 7x50 SR router which generates
         control traffic over IP."
    ::= { tmnxDscpAppEntry 1 }

tmnxDscpAppLastChanged OBJECT-TYPE
    SYNTAX      TimeStamp
    MAX-ACCESS  read-only
    STATUS      current
    DESCRIPTION
        "The value of tmnxDscpAppLastChanged indicates the sysUpTime
         at the time of the last modification of this entry.

         If no changes were made to the entry since the last
         re-initialization of the local network management subsystem,
         then this object contains a zero value."
    ::= { tmnxDscpAppEntry 2 }

tmnxDscpAppDscpValue OBJECT-TYPE
    SYNTAX      TDSCPValueOrNone
    MAX-ACCESS  read-write
    STATUS      current
    DESCRIPTION
        "The value of tmnxDscpAppDscpValue specifies a DSCP Value
         to assign to the traffic generated by the application
         specified by tmnxDscpAppId.

         A value of -1 specifies that no explicit DSCP re-marking
         will be done for the traffic generated by the application
         specified by tmnxDscpAppId.

         The default value is protocol specific."
    ::= { tmnxDscpAppEntry 3 }

--
-- DSCP Name -> Forwarding Class mapping table
--

tmnxDscpFCTableLastChanged OBJECT-TYPE
    SYNTAX      TimeStamp
    MAX-ACCESS  read-only
    STATUS      current
    DESCRIPTION
        "The value of tmnxDscpFCTableLastChanged indicates the sysUpTime
         at the time of the last modification of tmnxDscpFCTable.

         If no changes were made to the entry since the last
         re-initialization of the local network management subsystem,
         then this object contains a zero value."
    ::= { tmnxVRtrObjs 47 }

tmnxDscpFCTable OBJECT-TYPE
    SYNTAX      SEQUENCE OF TmnxDscpFCEntry
    MAX-ACCESS  not-accessible
    STATUS      current
    DESCRIPTION
        "The tmnxDscpFCTable has an entry for each mapping between
         a DSCP value and a Forwarding Class for self-generated
         protocol traffic in a virtual routing context on this system."
    ::= { tmnxVRtrObjs 48 }

tmnxDscpFCEntry    OBJECT-TYPE
    SYNTAX      TmnxDscpFCEntry
    MAX-ACCESS  not-accessible
    STATUS      current
    DESCRIPTION
        "Each row represents a mapping between a DSCP value and a
         Forwarding Class for self-generated protocol traffic
         in particular virtual routing context.

         Entries are created at system initialization."
    INDEX { vRtrID, tmnxDscpFCDscpValue }
    ::= { tmnxDscpFCTable 1}

TmnxDscpFCEntry ::= SEQUENCE
    {
        tmnxDscpFCDscpValue   TDSCPValue,
        tmnxDscpFCLastChanged TimeStamp,
        tmnxDscpFCValue       TFCType
    }

tmnxDscpFCDscpValue OBJECT-TYPE
    SYNTAX      TDSCPValue
    MAX-ACCESS  not-accessible
    STATUS      current
    DESCRIPTION
        "The value of tmnxDscpFCDscpValue specifies a DSCP value which
         will be mapped to the Forwarding Class specified by
         tmnxDscpFCValue."
    ::= { tmnxDscpFCEntry 1 }

tmnxDscpFCLastChanged OBJECT-TYPE
    SYNTAX      TimeStamp
    MAX-ACCESS  read-only
    STATUS      current
    DESCRIPTION
        "The value of tmnxDscpFCLastChanged indicates the sysUpTime
         at the time of the last modification of this entry.

         If no changes were made to the entry since the last
         re-initialization of the local network management subsystem,
         then this object contains a zero value."
    ::= { tmnxDscpFCEntry 3 }

tmnxDscpFCValue OBJECT-TYPE
    SYNTAX       TFCType
    MAX-ACCESS   read-write
    STATUS       current
    DESCRIPTION
        "The value of tmnxDscpFCValue specifies the Forwarding Class value
         for this mapping entry.

         The default value is best effort, which is specified by a value of 0."
    DEFVAL { be }
    ::= { tmnxDscpFCEntry 4 }


--
-- Application Id -> 802.1p value mapping table
--

tmnxDot1pAppTableLastChanged OBJECT-TYPE
    SYNTAX      TimeStamp
    MAX-ACCESS  read-only
    STATUS      current
    DESCRIPTION
        "The value of tmnxDot1pAppTableLastChanged indicates the
         sysUpTime at the time of the last modification of
         tmnxDot1pAppTable.

         If no changes were made to the table since the last
         re-initialization of the local network management
         subsystem, then this object contains a zero value."
    ::= { tmnxVRtrObjs 49 }

tmnxDot1pAppTable OBJECT-TYPE
    SYNTAX      SEQUENCE OF TmnxDot1pAppEntry
    MAX-ACCESS  not-accessible
    STATUS      current
    DESCRIPTION
        "The tmnxDot1pAppTable has an entry for each application to
         IEEE 802.1p priority (Dot1p) mapping in a virtual routing
         context on this system."
    ::= { tmnxVRtrObjs 50 }

tmnxDot1pAppEntry    OBJECT-TYPE
    SYNTAX      TmnxDot1pAppEntry
    MAX-ACCESS  not-accessible
    STATUS      current
    DESCRIPTION
        "Each row represents a mapping from an application to a Dot1p
         value for particular virtual routing context.

         Entries are created at system initialization."
    INDEX { vRtrID, tmnxDot1pAppId }
    ::= { tmnxDot1pAppTable 1}

TmnxDot1pAppEntry ::= SEQUENCE
    {
        tmnxDot1pAppId          TDot1pAppId,
        tmnxDot1pAppLastChanged TimeStamp,
        tmnxDot1pAppValue       Dot1PPriority
    }

tmnxDot1pAppId      OBJECT-TYPE
    SYNTAX      TDot1pAppId
    MAX-ACCESS  not-accessible
    STATUS      current
    DESCRIPTION
        "The value of tmnxDot1pAppId indicates the Dot1p application
         identifier for a Layer-2 protocol on the Alcatel 7x50 SR router."
    ::= { tmnxDot1pAppEntry 1 }

tmnxDot1pAppLastChanged OBJECT-TYPE
    SYNTAX      TimeStamp
    MAX-ACCESS  read-only
    STATUS      current
    DESCRIPTION
        "The value of tmnxDot1pAppLastChanged indicates the sysUpTime
         at the time of the last modification of this entry.

         If no changes were made to the entry since the last
         re-initialization of the local network management subsystem,
         then this object contains a zero value."
    ::= { tmnxDot1pAppEntry 2 }

tmnxDot1pAppValue OBJECT-TYPE
    SYNTAX      Dot1PPriority
    MAX-ACCESS  read-write
    STATUS      current
    DESCRIPTION
        "The value of tmnxDot1pAppValue specifies a Dot1p
         value to assign to the traffic generated by the application
         specified by tmnxDot1pAppId.

         The default value is protocol specific."
    ::= { tmnxDot1pAppEntry 3 }

--%%%%%%%%%%%%%%%%%%%%%%%%%%%%%%%%%%%%%%%%%%%%%%%%%%%%%%%%%%%%%%%%%%%%%
--
--      Objects for AutoFilter trap

tmnxVRtrNotificationObjects     OBJECT IDENTIFIER ::= {tmnxVRtrObjs 21}

vRtrAutoFilterDHCPClientAddress  OBJECT-TYPE
    SYNTAX      IpAddress
    MAX-ACCESS  accessible-for-notify
    STATUS      obsolete
    DESCRIPTION
        "The Client IP address from the PDU causing the trap.
         Used by tmnxVRtrDHCPAFEntriesExceeded to report
         the client's IP address."
    ::= { tmnxVRtrNotificationObjects 1 }

vRtrAutoFilterDHCPClientLease  OBJECT-TYPE
    SYNTAX      Unsigned32
    MAX-ACCESS  accessible-for-notify
    STATUS      obsolete
    DESCRIPTION
        "The lease time specified in the PDU causing the trap.
         Used by tmnxVRtrDHCPAFEntriesExceeded to report
         the lease time."
    ::= { tmnxVRtrNotificationObjects 2 }

--%%%%%%%%%%%%%%%%%%%%%%%%%%%%%%%%%%%%%%%%%%%%%%%%%%%%%%%%%%%%%%%%%%%%%
--
--      Objects for DHCP traps

vRtrDHCPClientLease
   OBJECT-TYPE
    SYNTAX         Integer32
    MAX-ACCESS     accessible-for-notify
    STATUS         obsolete
    DESCRIPTION    "The value of the object vRtrDHCPClientLease indicates the
                    lease time specified in the PDU causing the trap."
    ::= { tmnxVRtrNotificationObjects 3}

vRtrDhcpLseStateOldCiAddr
   OBJECT-TYPE
    SYNTAX         IpAddress
    MAX-ACCESS     accessible-for-notify
    STATUS         obsolete
    DESCRIPTION    "The value of the object vRtrDhcpLseStateOldCiAddr indicates
                    the Client IP address that was formerly assigned to this
                    Least state."
    ::= { tmnxVRtrNotificationObjects 4}

vRtrDhcpLseStateOldChAddr
   OBJECT-TYPE
    SYNTAX         MacAddress
    MAX-ACCESS     accessible-for-notify
    STATUS         obsolete
    DESCRIPTION    "The value of the object vRtrDhcpLseStateOldChAddr indicates
                    the Client MAC address that was formerly assigned to this
                    Least state."
    ::= { tmnxVRtrNotificationObjects 5}

vRtrDhcpLseStateNewCiAddr
   OBJECT-TYPE
    SYNTAX         IpAddress
    MAX-ACCESS     accessible-for-notify
    STATUS         obsolete
    DESCRIPTION    "The value of the object vRtrDhcpLseStateNewCiAddr indicates
                    the Client IP address specified in the PDU causing
                    the trap."
    ::= { tmnxVRtrNotificationObjects 6}

vRtrDhcpLseStateNewChAddr
   OBJECT-TYPE
    SYNTAX         MacAddress
    MAX-ACCESS     accessible-for-notify
    STATUS         obsolete
    DESCRIPTION    "The value of the object vRtrDhcpLseStateNewChAddr indicates
                    the Client MAC address specified in the PDU causing
                    the trap."
    ::= { tmnxVRtrNotificationObjects 7}

vRtrDhcpRestoreLseStateCiAddr
   OBJECT-TYPE
    SYNTAX         IpAddress
    MAX-ACCESS     accessible-for-notify
    STATUS         obsolete
    DESCRIPTION    "The value of the object vRtrDhcpRestoreLseStateCiAddr indicates
                    the IP address specified in the persistency record causing
                    the trap."
    ::= { tmnxVRtrNotificationObjects 8}

vRtrDhcpRestoreLseStateVRtrId
   OBJECT-TYPE
    SYNTAX         TmnxVRtrID
    MAX-ACCESS     accessible-for-notify
    STATUS         obsolete
    DESCRIPTION    "The value of the object vRtrDhcpRestoreLseStateVRtrId indicates
                    the serviceId specified in the persistency record causing
                    the trap."
    ::= { tmnxVRtrNotificationObjects 9}

vRtrDhcpRestoreLseStateIfIndex
   OBJECT-TYPE
    SYNTAX         InterfaceIndex
    MAX-ACCESS     accessible-for-notify
    STATUS         obsolete
    DESCRIPTION    "The value of the object vRtrDhcpRestoreLseStateIfIndex indicates
                    the Port ID specified in the persistency record causing
                    the trap."
    ::= { tmnxVRtrNotificationObjects 10}

vRtrDhcpRestoreLseStateProblem
   OBJECT-TYPE
    SYNTAX         DisplayString
    MAX-ACCESS     accessible-for-notify
    STATUS         obsolete
    DESCRIPTION    "The value of the object vRtrDhcpRestoreLseStateProblem
                    indicates why the persisency record cannot be restored."
    ::= { tmnxVRtrNotificationObjects 11}

vRtrDhcpPacketProblem
   OBJECT-TYPE
    SYNTAX         DisplayString
    MAX-ACCESS     accessible-for-notify
    STATUS         current
    DESCRIPTION    "The value of the object vRtrDhcpPacketProblem indicates
                    information on a received DHCP packet is considered
                    suspicious by the system."
    ::= { tmnxVRtrNotificationObjects 12}

vRtrDhcpLseStatePopulateError
   OBJECT-TYPE
    SYNTAX         DisplayString
    MAX-ACCESS     accessible-for-notify
    STATUS         obsolete
    DESCRIPTION    "The value of the object vRtrDhcpLseStatePopulateError
                    indicates the reason why the system was unable to update
                    the Lease state table with the information contained in
                    the received DHCP ACK message."
    ::= { tmnxVRtrNotificationObjects 13}

vRtrBfdSlotNumber
   OBJECT-TYPE
    SYNTAX         TmnxSlotNum
    MAX-ACCESS     accessible-for-notify
    STATUS         current
    DESCRIPTION    "The value of vRtrBfdSlotNumber indicates the IOM slot
                    number where the number of supported BFD sessions has
                    reached the maximum value. This object is reported
                    when the tmnxVRtrBfdMaxSessionOnSlot notification
                    is generated."
    ::= { tmnxVRtrNotificationObjects 14}

vRtrNumberOfBfdSessionsOnSlot
   OBJECT-TYPE
    SYNTAX         Unsigned32
    MAX-ACCESS     accessible-for-notify
    STATUS         current
    DESCRIPTION    "The value of vRtrNumberOfBfdSessionsOnSlot indicates the
                    current number of BFD sessions on the slot indicated by
                    vRtrBfdSlotNumber. This object is reported when the
                    tmnxVRtrBfdMaxSessionOnSlot notification is generated."
    ::= { tmnxVRtrNotificationObjects 15}

vRtrBfdMaxSessionReason
   OBJECT-TYPE
    SYNTAX         BITS {
                      maxSessionsPerSlot(0),
                      maxTxPacketRate(1),
                      maxRxPacketRate(2)
                   }
    MAX-ACCESS     accessible-for-notify
    STATUS         current
    DESCRIPTION    "The value of vRtrBfdMaxSessionReason indicates the
                    reason the maximum numbers of sessions on this IOM
                    slot was reached. This object is reported when the
                    tmnxVRtrBfdMaxSessionOnSlot notification is
                    generated."
    ::= { tmnxVRtrNotificationObjects 16}

vRtrDHCP6ServerNetAddrType
   OBJECT-TYPE
    SYNTAX         InetAddressType
    MAX-ACCESS     accessible-for-notify
    STATUS         current
    DESCRIPTION    "The value of the object vRtrDHCP6ServerNetAddrType
                    indicates the address type of vRtrDHCP6ServerNetAddr."
    ::= { tmnxVRtrNotificationObjects 17 }

vRtrDHCP6ServerNetAddr
   OBJECT-TYPE
    SYNTAX         InetAddress
    MAX-ACCESS     accessible-for-notify
    STATUS         current
    DESCRIPTION    "The value of the object vRtrDHCP6ServerNetAddr
                    indicates the IP address of the DHCP server."
    ::= { tmnxVRtrNotificationObjects 18 }

vRtrDHCP6ClientNetAddrType
   OBJECT-TYPE
    SYNTAX         InetAddressType
    MAX-ACCESS     accessible-for-notify
    STATUS         current
    DESCRIPTION    "The value of the object vRtrDHCP6ClientNetAddrType
                    indicates the address type of vRtrDHCP6ClientNetAddr."
    ::= { tmnxVRtrNotificationObjects 19 }

vRtrDHCP6ClientNetAddr
   OBJECT-TYPE
    SYNTAX         InetAddress
    MAX-ACCESS     accessible-for-notify
    STATUS         current
    DESCRIPTION    "The value of the object vRtrDHCP6ClientNetAddr
                    indicates the IP address of the DHCP client."
    ::= { tmnxVRtrNotificationObjects 20 }

vRtrDHCP6AssignedNetAddrType
   OBJECT-TYPE
    SYNTAX         InetAddressType
    MAX-ACCESS     accessible-for-notify
    STATUS         current
    DESCRIPTION    "The value of the object vRtrDHCP6AssignedNetAddrType
                    indicates the address type of vRtrDHCP6AssignedNetAddr."
    ::= { tmnxVRtrNotificationObjects 21 }

vRtrDHCP6AssignedNetAddr
   OBJECT-TYPE
    SYNTAX         InetAddress
    MAX-ACCESS     accessible-for-notify
    STATUS         current
    DESCRIPTION    "The value of the object vRtrDHCP6AssignedNetAddr
                    indicates the IP address assigned to the DHCP client."
    ::= { tmnxVRtrNotificationObjects 22 }

vRtrDHCP6AssignedPrefixLen
   OBJECT-TYPE
    SYNTAX         InetAddressPrefixLength
    MAX-ACCESS     accessible-for-notify
    STATUS         current
    DESCRIPTION    "The value of vRtrDHCP6AssignedPrefixLen specifies
                    the length of the IP netmask for vRtrDHCP6AssignedNetAddr."
    ::= { tmnxVRtrNotificationObjects 23 }

vRtrDHCP6OldAssignedNetAddrType
   OBJECT-TYPE
    SYNTAX         InetAddressType
    MAX-ACCESS     accessible-for-notify
    STATUS         current
    DESCRIPTION    "The value of the object vRtrDHCP6OldAssignedNetAddrType
                    indicates the address type of vRtrDHCP6OldAssignedNetAddr."
    ::= { tmnxVRtrNotificationObjects 24 }

vRtrDHCP6OldAssignedNetAddr
   OBJECT-TYPE
    SYNTAX         InetAddress
    MAX-ACCESS     accessible-for-notify
    STATUS         current
    DESCRIPTION    "The value of the object vRtrDHCP6OldAssignedNetAddr
                    indicates the IP address formerly assigned to the DHCP
                    client."
    ::= { tmnxVRtrNotificationObjects 25 }

vRtrDHCP6OldAssignedPrefixLen
   OBJECT-TYPE
    SYNTAX         InetAddressPrefixLength
    MAX-ACCESS     accessible-for-notify
    STATUS         current
    DESCRIPTION    "The value of vRtrDHCP6OldAssignedPrefixLen specifies the
                    length of the IP netmask for vRtrDHCP6OldAssignedNetAddr."
    ::= { tmnxVRtrNotificationObjects 26 }

vRtrDHCP6NewClientId
   OBJECT-TYPE
    SYNTAX          OCTET STRING (SIZE (0..255))
    MAX-ACCESS      accessible-for-notify
    STATUS          current
    DESCRIPTION     "The value of vRtrDHCP6NewClientId indicates the new
                     DHCP6 clients unique identifier (DUID)."
    ::= { tmnxVRtrNotificationObjects 27 }

vRtrDHCP6OldClientId
   OBJECT-TYPE
    SYNTAX          OCTET STRING (SIZE (0..255))
    MAX-ACCESS      accessible-for-notify
    STATUS          current
    DESCRIPTION     "The value of vRtrDHCP6OldClientId indicates the old
                     DHCP6 clients unique identifier (DUID)."
    ::= { tmnxVRtrNotificationObjects 28 }

vRtrDHCP6LeaseOverrideResult
   OBJECT-TYPE
    SYNTAX          DisplayString
    MAX-ACCESS      accessible-for-notify
    STATUS          current
    DESCRIPTION     "The value of the object vRtrDHCP6LeaseOverrideResult
                     indicates whether or not the lease state has been
                     overridden."
    ::= { tmnxVRtrNotificationObjects 29 }

vRtrInetStatRteCpeNotifyAddrType
   OBJECT-TYPE
    SYNTAX         InetAddressType
    MAX-ACCESS     accessible-for-notify
    STATUS         current
    DESCRIPTION    "The value of the object vRtrInetStatRteCpeNotifyAddrType
                    indicates the address type of
                    vRtrInetStatRteCpeNotifyAddr."
    ::= { tmnxVRtrNotificationObjects 30 }

vRtrInetStatRteCpeNotifyAddr
   OBJECT-TYPE
    SYNTAX         InetAddress
    MAX-ACCESS     accessible-for-notify
    STATUS         current
    DESCRIPTION    "The value of the object vRtrInetStatRteCpeNotifyAddr
                    indicates the IP address of the CPE."
    ::= { tmnxVRtrNotificationObjects 31 }

vRtrInetStaticRouteCpeStatus
   OBJECT-TYPE
    SYNTAX          INTEGER {
                        reachable   (0),
                        unreachable (1)
                    }
    MAX-ACCESS      accessible-for-notify
    STATUS          current
    DESCRIPTION     "The value of the object vRtrInetStaticRouteCpeStatus
                     indicates whether or not the CPE associated with a
                     static route is 'reachable' or 'unreachable'."
    ::= { tmnxVRtrNotificationObjects 32 }

vRtrManagedRouteInetAddrType OBJECT-TYPE
    SYNTAX          InetAddressType
    MAX-ACCESS      accessible-for-notify
    STATUS          current
    DESCRIPTION     "The value of vRtrManagedRouteInetAddrType indicates
                     the address type of vRtrManagedRouteInetAddr."
    ::= { tmnxVRtrNotificationObjects 33 }

vRtrManagedRouteInetAddr OBJECT-TYPE
    SYNTAX          InetAddress (SIZE(0|4))
    MAX-ACCESS      accessible-for-notify
    STATUS          current
    DESCRIPTION     "The value of vRtrManagedRouteInetAddr indicates
                     the IP address of the managed route."
    ::= { tmnxVRtrNotificationObjects 34 }

vRtrManagedRoutePrefixLen OBJECT-TYPE
    SYNTAX          InetAddressPrefixLength
    MAX-ACCESS      accessible-for-notify
    STATUS          current
    DESCRIPTION     "The value of vRtrManagedRoutePrefixLen indicates
                     the prefix length of the subnet associated with
                     vRtrManagedRouteInetAddr."
    ::= { tmnxVRtrNotificationObjects 35 }

vRtrFailureDescription OBJECT-TYPE
    SYNTAX          DisplayString
    MAX-ACCESS      accessible-for-notify
    STATUS          current
    DESCRIPTION     "The value of the object vRtrFailureDescription is a
                     printable character string which contains information
                     about the reason why the notification is sent."
    ::= { tmnxVRtrNotificationObjects 36 }

--%%%%%%%%%%%%%%%%%%%%%%%%%%%%%%%%%%%%%%%%%%%%%%%%%%%%%%%%%%%%%%%%%%%%%
--
--      TIMETRA-VRTR-MIB Notifications
--

tmnxVRtrMidRouteTCA     NOTIFICATION-TYPE
    OBJECTS {
                    vRtrStatCurrNumRoutes,
                    vRtrMidRouteThreshold
        }
    STATUS      current
    DESCRIPTION
        "The tmnxVRtrMidRouteTCA notification is generated when the number
         of routes contained in a VPRN exceeds the value specified by
         vRtrMidRouteThreshold.  No other notifications of this type
         are generated until after the soak period specified by
         vRtrRouteThresholdSoakTime has expired."
    ::= { tmnxVRtrNotifications 1 }

tmnxVRtrHighRouteTCA    NOTIFICATION-TYPE
    OBJECTS     {
                    vRtrStatCurrNumRoutes,
                    vRtrHighRouteThreshold
                }
    STATUS      current
    DESCRIPTION
        "The tmnxVRtrHighRouteTCA notification is generated when the number
         of routes contained in a VPRN exceeds the value specified by
         vRtrHighRouteThreshold.  No other notifications of this type
         are generated until after the soak period specified by
         vRtrRouteThresholdSoakTime has expired."
    ::= { tmnxVRtrNotifications 2 }

tmnxVRtrHighRouteCleared    NOTIFICATION-TYPE
    OBJECTS     {
                    vRtrStatCurrNumRoutes,
                    vRtrHighRouteThreshold
                }
    STATUS      current
    DESCRIPTION
        "The tmnxVRtrHighRouteCleared notification is generated when the
         number of routes contained in a VPRN has dropped below the
         vRtrHighRouteThreshold value following the generation of a
         tmnxVRtrHighRouteTCA notification."
    ::= { tmnxVRtrNotifications 3 }

tmnxVRtrIllegalLabelTCA     NOTIFICATION-TYPE
    OBJECTS     {
                    vRtrStatIllegalLabels,
                    vRtrIllegalLabelThreshold
                }
    STATUS      current
    DESCRIPTION
        "The tmnxVRtrIllegalLabelTCA notification is generated when the
         number of illegal label violations on a VRF has exceeded the
         value specified by vRtrIllegalLabelThreshold."
    ::= { tmnxVRtrNotifications 4 }

tmnxVRtrMcastMidRouteTCA     NOTIFICATION-TYPE
    OBJECTS     {
                    vRtrMulticastRoutes,
                    vRtrMcastMidRouteThreshold
                }
    STATUS      current
    DESCRIPTION
        "The tmnxVRtrMcastMidRouteTCA notification is generated when the number
         of multicast routes contained in a VPRN exceeds the value specified by
         vRtrMcastMidRouteThreshold.  No other notifications of this type
         are generated until after the soak period specified by
         vRtrRouteThresholdSoakTime has expired."
    ::= { tmnxVRtrNotifications 5 }

tmnxVRtrMcastMaxRoutesTCA    NOTIFICATION-TYPE
    OBJECTS     {
                    vRtrMulticastRoutes,
                    vRtrMaxMcastNumRoutes
                }
    STATUS      current
    DESCRIPTION
        "The tmnxVRtrMcastMaxRoutesTCA notification is generated when the number
         of multicast routes contained in a VPRN exceeds the value specified by
         vRtrMaxMcastNumRoutes.  No other notifications of this type
         are generated until after the soak period specified by
         vRtrRouteThresholdSoakTime has expired."
    ::= { tmnxVRtrNotifications 6 }

tmnxVRtrMcastMaxRoutesCleared    NOTIFICATION-TYPE
    OBJECTS     {
                    vRtrMulticastRoutes,
                    vRtrMaxMcastNumRoutes
                }
    STATUS      current
    DESCRIPTION
        "The tmnxVRtrMcastMaxRoutesCleared notification is generated when the
         number of multicast routes contained in a VPRN has dropped below the
         vRtrMaxMcastNumRoutes value following the generation of a
         tmnxVRtrMcastMaxRoutesTCA notification."
    ::= { tmnxVRtrNotifications 7 }

tmnxVRtrMaxArpEntriesTCA        NOTIFICATION-TYPE
    OBJECTS     {
                    vRtrStatActiveARPEntries,
                    vRtrStatTotalARPEntries,
                    vRtrMaxARPEntries
                }
    STATUS      current
    DESCRIPTION
        "The tmnxVRtrMaxArpEntriesTCA notification is generated when the
         number of ARP entries in a VPRN exceeds the maximum supported."
    ::= { tmnxVRtrNotifications 8 }

tmnxVRtrMaxArpEntriesCleared    NOTIFICATION-TYPE
    OBJECTS     {
                    vRtrStatActiveARPEntries,
                    vRtrStatTotalARPEntries,
                    vRtrMaxARPEntries
                }
    STATUS      current
    DESCRIPTION
        "The tmnxVRtrMaxArpEntriesCleared notification is generated when the
         number of ARP entries contained in a VPRN has dropped below the
         maximum value following the generation of a tmnxVRtrMaxArpEntriesTCA
         notification."
    ::= { tmnxVRtrNotifications 9 }

tmnxVRtrDHCPAFEntriesExceeded   NOTIFICATION-TYPE
    OBJECTS     {
                    vRtrIfDHCPOperAutoFilter,
                    vRtrIfIndex,
                    vRtrAutoFilterDHCPClientAddress,
                    vRtrAutoFilterDHCPClientLease
                }
    STATUS      obsolete
    DESCRIPTION
        "The tmnxVRtrDHCPAFEntriesExceeded notification is generated
        when the number of DHCP 'AutoFilter' entries on a given interface
        reaches a user configurable upper limit given by vRtrIfDHCPAutoFilter."
    ::= {tmnxVRtrNotifications 10}

tmnxVRtrMaxRoutes    NOTIFICATION-TYPE
    OBJECTS {
        vRtrStatCurrNumRoutes,
        vRtrMaxNumRoutes
    }
    STATUS          current
    DESCRIPTION     "The tmnxVRtrMaxRoutes notification is
                     generated when the number of routes contained in a
                     VPRN reaches the value specified by vRtrMaxNumRoutes."
    ::= { tmnxVRtrNotifications 11 }

tmnxVRtrDHCPLseStsExceeded   NOTIFICATION-TYPE
    OBJECTS {
        vRtrID,
        vRtrServiceId,
        vRtrIfIndex,
        vRtrDhcpLseStateNewCiAddr,
        vRtrDhcpLseStateNewChAddr,
        vRtrDHCPClientLease
    }
    STATUS          obsolete
    DESCRIPTION     "The tmnxVRtrDHCPLseStsExceeded notification is
                     generated when the number  of  DHCP  lease states
                     entries on a given interface reaches a user configurable
                     upper limit."
    ::= {tmnxVRtrNotifications 12}

tmnxVRtrDHCPLeaseStateOverride NOTIFICATION-TYPE
    OBJECTS {
        vRtrID,
        vRtrServiceId,
        vRtrIfIndex,
        vRtrDhcpLseStateNewCiAddr,
        vRtrDhcpLseStateNewChAddr,
        vRtrDhcpLseStateOldCiAddr,
        vRtrDhcpLseStateOldChAddr
    }
    STATUS          obsolete
    DESCRIPTION     "The tmnxVRtrDHCPLeaseStateOverride notification is
                     generated when an existing DHCP lease state is
                     overridden by a new lease state which has the same
                     IP address but a different MAC address."
    ::= {tmnxVRtrNotifications 13}

tmnxVRtrDHCPSuspiciousPcktRcvd NOTIFICATION-TYPE
    OBJECTS {
        vRtrID,
        vRtrServiceId,
        vRtrIfIndex,
        vRtrDhcpPacketProblem
    }
    STATUS          current
    DESCRIPTION     "The tmnxVRtrDHCPSuspiciousPcktRcvd notification is
                     generated when a DHCP packet is received with suspicious
                     content."
    ::= {tmnxVRtrNotifications 14}

tmnxVRtrDHCPLseStRestoreProblem NOTIFICATION-TYPE
    OBJECTS {
        vRtrDhcpRestoreLseStateVRtrId,
        vRtrDhcpRestoreLseStateIfIndex,
        vRtrDhcpRestoreLseStateCiAddr,
        vRtrDhcpRestoreLseStateProblem
    }
    STATUS          obsolete
    DESCRIPTION     "The tmnxVRtrDHCPLseStRestoreProblem notification is
                     generated when an an error is detected while
                     processing a persistency record."
    ::= {tmnxVRtrNotifications 15}

tmnxVRtrDHCPLseStatePopulateErr NOTIFICATION-TYPE
    OBJECTS {
        vRtrID,
        vRtrServiceId,
        vRtrIfIndex,
        vRtrDhcpLseStatePopulateError
    }
    STATUS          obsolete
    DESCRIPTION     "The tmnxVRtrDHCPLseStatePopulateErr notification
                     indicates that the system was unable to update the
                     Lease State Table with the information contained in
                     the DHCP ACK message. The DHCP ACK message has been
                     discarded."
    ::= {tmnxVRtrNotifications 16}

tmnxVRtrBfdSessionDown  NOTIFICATION-TYPE
    OBJECTS {
        vRtrIfBfdSessionLclDisc,
        vRtrIfBfdSessionOperFlags
    }
    STATUS          current
    DESCRIPTION     "The tmnxVRtrBfdSessionDown notification is generated when
                     a BFD session goes down."
    ::= {tmnxVRtrNotifications 17}

tmnxVRtrBfdMaxSessionOnSlot    NOTIFICATION-TYPE
    OBJECTS {
        vRtrBfdSlotNumber,
        vRtrNumberOfBfdSessionsOnSlot,
        vRtrBfdMaxSessionReason
    }
    STATUS          current
    DESCRIPTION     "The tmnxVRtrBfdMaxSessionOnSlot notification is generated
                     when the maximum number of BFD sessions has been reached
                     on the slot indicated in 'vRtrBfdSlotNumber'."
    ::= {tmnxVRtrNotifications 18}

tmnxVRtrBfdPortTypeNotSupported NOTIFICATION-TYPE
    OBJECTS {
        tmnxPortNotifyPortId,
        tmnxPortType
    }
    STATUS          current
    DESCRIPTION     "The tmnxVRtrBfdPortTypeNotSupported notification is
                     generated when BFD is not supported on the port specified
                     in 'tmnxPortNotifyPortId'."
    ::= {tmnxVRtrNotifications 19}

tmnxVRtrDHCPIfLseStatesExceeded  NOTIFICATION-TYPE
    OBJECTS {
        vRtrID,
        vRtrServiceId,
        vRtrIfIndex,
        sapPortId,
        sapEncapValue,
        vRtrIfDHCPLeasePopulate,
        svcDhcpLseStateNewCiAddr,
        svcDhcpLseStateNewChAddr,
        svcDhcpClientLease
    }
    STATUS          current
    DESCRIPTION     "The tmnxVRtrDHCPIfLseStatesExceeded notifications is
                     generated when the number of lease states on an interface
                     exceeds vRtrIfDHCPLeasePopulate."
    ::= {tmnxVRtrNotifications 20}

tmnxVRtrDHCP6RelayLseStExceeded  NOTIFICATION-TYPE
    OBJECTS {
        vRtrID,
        vRtrServiceId,
        vRtrIfIndex,
        vRtrIfDHCP6LeasePopulate,
        vRtrDHCP6AssignedNetAddrType,
        vRtrDHCP6AssignedNetAddr,
        vRtrDHCP6AssignedPrefixLen,
        vRtrDHCP6NewClientId,
        svcDhcpClientLease
    }
    STATUS          current
    DESCRIPTION     "The tmnxVRtrDHCP6RelayLseStExceeded notifications is
                     generated when the number of lease states populated by
                     dhcp6 relay on an interface exceeds
                     vRtrIfDHCP6LeasePopulate."
    ::= {tmnxVRtrNotifications 21}

tmnxVRtrDHCP6ServerLseStExceeded  NOTIFICATION-TYPE
    OBJECTS {
        vRtrID,
        vRtrServiceId,
        vRtrIfIndex,
        vRtrIfDHCP6ServerMaxLeaseStates,
        vRtrDHCP6AssignedNetAddrType,
        vRtrDHCP6AssignedNetAddr,
        vRtrDHCP6AssignedPrefixLen,
        vRtrDHCP6NewClientId,
        svcDhcpClientLease
    }
    STATUS          current
    DESCRIPTION     "The tmnxVRtrDHCP6ServerLseStExceeded notifications is
                     generated when the number of lease states populated by
                     dhcp6 server on an interface exceeds
                     vRtrIfDHCP6ServerMaxLeaseStates."
    ::= {tmnxVRtrNotifications 22}

tmnxVRtrDHCP6LseStateOverride NOTIFICATION-TYPE
    OBJECTS {
        vRtrID,
        vRtrServiceId,
        vRtrIfIndex,
        vRtrDHCP6OldAssignedNetAddrType,
        vRtrDHCP6OldAssignedNetAddr,
        vRtrDHCP6OldAssignedPrefixLen,
        vRtrDhcpLseStateOldChAddr,
        vRtrDHCP6OldClientId,
        vRtrDHCP6AssignedNetAddrType,
        vRtrDHCP6AssignedNetAddr,
        vRtrDHCP6AssignedPrefixLen,
        vRtrDhcpLseStateNewChAddr,
        vRtrDHCP6NewClientId,
        vRtrDHCP6LeaseOverrideResult
    }
    STATUS          current
    DESCRIPTION     "The tmnxVRtrDHCP6LseStateOverride notifications is
                     generated when an existing DHCP6 lease state can be
                     overridden by a new lease state.

                     This is allowed if the new lease state has the same IP
                     address but a different client id or mac address.
                     This is not allowed if the new lease state has the same IP
                     address but a different prefix length."
    ::= {tmnxVRtrNotifications 23}

tmnxVRtrDHCP6RelayReplyStripUni  NOTIFICATION-TYPE
    OBJECTS {
        vRtrID,
        vRtrServiceId,
        vRtrIfIndex,
        vRtrDHCP6ServerNetAddrType,
        vRtrDHCP6ServerNetAddr
    }
    STATUS          current
    DESCRIPTION     "The tmnxVRtrDHCP6RelayReplyStripUni notifications is
                     generated when a unicast option is stripped from a message
                     relayed from a server to a client
                     in a relay reply message."
    ::= {tmnxVRtrNotifications 24}

tmnxVRtrDHCP6IllegalClientAddr  NOTIFICATION-TYPE
    OBJECTS {
        vRtrID,
        vRtrServiceId,
        vRtrIfIndex,
        vRtrDHCP6ClientNetAddrType,
        vRtrDHCP6ClientNetAddr
    }
    STATUS          current
    DESCRIPTION     "The tmnxVRtrDHCP6IllegalClientAddr notifications is
                     generated when an incoming message is dropped
                     because the client's source IP does not match the subnet
                     of the incoming interface."
    ::= {tmnxVRtrNotifications 25}

tmnxVRtrDHCP6AssignedIllegSubnet  NOTIFICATION-TYPE
    OBJECTS {
        vRtrID,
        vRtrServiceId,
        vRtrIfIndex,
        vRtrDHCP6ClientNetAddrType,
        vRtrDHCP6ClientNetAddr,
        vRtrDHCP6AssignedNetAddrType,
        vRtrDHCP6AssignedNetAddr,
        vRtrDHCP6AssignedPrefixLen
    }
    STATUS          current
    DESCRIPTION     "The tmnxVRtrDHCP6AssignedIllegSubnet notifications is
                     generated when an IP address assigned to the client
                     does not match the subnet of the interface."
    ::= {tmnxVRtrNotifications 26}

tmnxVRtrDHCP6ClientMacUnresolved NOTIFICATION-TYPE
    OBJECTS {
        vRtrID,
        vRtrServiceId,
        vRtrIfIndex,
        vRtrDHCP6ClientNetAddrType,
        vRtrDHCP6ClientNetAddr
    }
    STATUS          current
    DESCRIPTION     "The tmnxVRtrDHCP6ClientMacUnresolved notifications is
                     generated when we receive a relay reply for a client,
                     and the client's MAC address has not been resolved yet."
    ::= {tmnxVRtrNotifications 27}

tmnxVRtrBfdSessionUp  NOTIFICATION-TYPE
    OBJECTS {
        vRtrIfBfdSessionLclDisc
    }
    STATUS          current
    DESCRIPTION     "The tmnxVRtrBfdSessionUp notification is generated when
                     a BFD session goes up."
    ::= {tmnxVRtrNotifications 28}

tmnxVRtrIPv6MidRouteTCA NOTIFICATION-TYPE
    OBJECTS {
        vRtrV6StatCurrNumRoutes,
        vRtrIPv6MidRouteThreshold
    }
    STATUS          current
    DESCRIPTION     "The tmnxVRtrIPv6MidRouteTCA notification is generated when
                     the number of IPv6 routes contained in a VPRN exceeds
                     the value specified by vRtrIPv6MidRouteThreshold. No other
                     notifications of this type are generated until after the
                     soak period specified by vRtrIPv6RouteThresholdSoakTime
                     has expired."
    ::= { tmnxVRtrNotifications 29 }

tmnxVRtrIPv6HighRouteTCA NOTIFICATION-TYPE
    OBJECTS {
        vRtrV6StatCurrNumRoutes,
        vRtrIPv6HighRouteThreshold
    }
    STATUS          current
    DESCRIPTION     "The tmnxVRtrIPv6HighRouteTCA notification is generated when
                     the number of IPv6 routes contained in a VPRN exceeds
                     the value specified by vRtrIPv6HighRouteThreshold. No other
                     notifications of this type are generated until after the
                     soak period specified by vRtrIPv6RouteThresholdSoakTime
                     has expired."
    ::= { tmnxVRtrNotifications 30 }

tmnxVRtrIPv6HighRouteCleared NOTIFICATION-TYPE
    OBJECTS {
        vRtrV6StatCurrNumRoutes,
        vRtrIPv6HighRouteThreshold
    }
    STATUS          current
    DESCRIPTION     "The tmnxVRtrIPv6HighRouteCleared notification is generated
                     when the number of IPv6 routes contained in a VPRN has
                     dropped below the vRtrIPv6HighRouteThreshold value
                     following the generation of a tmnxVRtrIPv6HighRouteTCA
                     notification."
    ::= { tmnxVRtrNotifications 31 }

tmnxVRtrStaticRouteCPEStatus  NOTIFICATION-TYPE
    OBJECTS {
        vRtrID,
        vRtrInetStatRteCpeNotifyAddrType,
        vRtrInetStatRteCpeNotifyAddr,
        vRtrInetStaticRouteCpeStatus
    }
    STATUS          current
    DESCRIPTION     "The tmnxVRtrStaticRouteCPEStatus notification is generated
                     when a CPE associated with a static route, as specified
                     by the vRtrInetStatRteCpeNotifyAddr object, becomes
                     reachable or unreachable."
    ::= { tmnxVRtrNotifications 32 }
    
tmnxVRtrBfdSessionDeleted  NOTIFICATION-TYPE
    OBJECTS {
        vRtrIfBfdSessionLclDisc,
        vRtrIfBfdSessionOperFlags
    }
    STATUS          current
    DESCRIPTION     "The tmnxVRtrBfdSessionDeleted notification is generated when
                     a BFD session is deleted."
    ::= {tmnxVRtrNotifications 33 }

tmnxVRtrBfdSessionProtChange  NOTIFICATION-TYPE
    OBJECTS {
        vRtrIfBfdSessionLclDisc,
        vRtrIfBfdSessionProtocols
    }
    STATUS          current
    DESCRIPTION     "The tmnxVRtrBfdSessionProtChange notification is generated when
                     there is a change in the list of protocols using the BFD session."
    ::= {tmnxVRtrNotifications 34 }

tmnxVRtrManagedRouteAddFailed NOTIFICATION-TYPE
    OBJECTS {
        vRtrID,
        vRtrManagedRouteInetAddrType,
        vRtrManagedRouteInetAddr,
        vRtrManagedRoutePrefixLen,
        vRtrFailureDescription
    }
    STATUS          current
    DESCRIPTION     "The tmnxVRtrManagedRouteAddFailed notification
                     is generated when a managed route could not be installed."
    ::= { tmnxVRtrNotifications 35 }

--
-- Conformance Information
--
tmnxVRtrCompliances OBJECT IDENTIFIER ::= { tmnxVRtrConformance 1 }
tmnxVRtrGroups      OBJECT IDENTIFIER ::= { tmnxVRtrConformance 2 }

-- compliance statements

-- tmnxVRtrCompliance  MODULE-COMPLIANCE
--    ::= { tmnxVRtrCompliances 1 }

-- tmnxVRtrR2r1Compliance  MODULE-COMPLIANCE
--    ::= { tmnxVRtrCompliances 2 }

-- tmnxVRtrV3v0Compliance  MODULE-COMPLIANCE
--    ::= { tmnxVRtrCompliances 3 }

tmnxVRtr7450V4v0Compliance  MODULE-COMPLIANCE
    STATUS  obsolete
    DESCRIPTION
            "The compliance statement for management of VRTR instances
             on Alcatel 7450 ESS series systems release R4.0."
    MODULE  -- this module
        MANDATORY-GROUPS {
            tmnxVRtrGlobalR2r1Group,
            tmnxVRtrV4v0Group,
            tmnxVRtrIfV4v0Group,
            tmnxVRtrIpV4v0Group,
            -- tmnxVRtrIPv6V4v0Group,
            -- tmnxVRtrIPv6IpV4v0Group,
            -- tmnxVRtrIPv6IfV4v0Group,
            tmnxVRtrNotificationV4v0Group,
            tmnxVRtrIfSubscrAuthV3v0Group,
            tmnxVRtrBfdV4v0Group
        }
    ::= { tmnxVRtrCompliances 4 }

tmnxVRtr7750V4v0Compliance  MODULE-COMPLIANCE
    STATUS  obsolete
    DESCRIPTION
            "The compliance statement for management of VRTR instances
             on Alcatel 7750 SR series systems release R4.0."
    MODULE  -- this module
        MANDATORY-GROUPS {
            tmnxVRtrGlobalR2r1Group,
            tmnxVRtrV4v0Group,
            tmnxVRtrIfV4v0Group,
            tmnxVRtrIpV4v0Group,
            tmnxVRtrIPv6V4v0Group,
            tmnxVRtrIPv6IpV4v0Group,
            tmnxVRtrIPv6IfV4v0Group,
            tmnxVRtrNotificationV4v0Group,
            tmnxVRtrIfSubscrAuthV3v0Group,
            tmnxVRtrBfdV4v0Group
        }
    ::= { tmnxVRtrCompliances 5 }

tmnxVRtr7450V5v0Compliance  MODULE-COMPLIANCE
    STATUS  obsolete
    DESCRIPTION
            "The compliance statement for management of VRTR instances
             on Alcatel 7450 ESS series systems release R5.0."
    MODULE  -- this module
        MANDATORY-GROUPS {
            tmnxVRtrGlobalR2r1Group,
            tmnxVRtrV5v0Group,
            tmnxVRtrIfV5v0Group,
            tmnxVRtrIpV5v0Group,
            -- tmnxVRtrIPv6V4v0Group,
            -- tmnxVRtrIPv6IpV5v0Group,
            -- tmnxVRtrIPv6IfV4v0Group,
            tmnxVRtrNotificationV5v0Group,
            tmnxVRtrIfSubscrAuthV3v0Group,
            tmnxVRtrBfdV4v0Group
        }
    ::= { tmnxVRtrCompliances 6 }

tmnxVRtr7750V5v0Compliance  MODULE-COMPLIANCE
    STATUS  obsolete
    DESCRIPTION
            "The compliance statement for management of VRTR instances
             on Alcatel 7750 SR series systems release R5.0."
    MODULE  -- this module
        MANDATORY-GROUPS {
            tmnxVRtrGlobalR2r1Group,
            tmnxVRtrV5v0Group,
            tmnxVRtrIfV5v0Group,
            tmnxVRtrIpV5v0Group,
            tmnxVRtrIPv6V4v0Group,
            tmnxVRtrIPv6IpV5v0Group,
            tmnxVRtrIPv6IfV4v0Group,
            tmnxVRtrNotificationV5v0Group,
            tmnxVRtrIfSubscrAuthV3v0Group,
            tmnxVRtrBfdV4v0Group
        }
    ::= { tmnxVRtrCompliances 7 }

tmnxVRtr7450V6v0Compliance  MODULE-COMPLIANCE
    STATUS  current
    DESCRIPTION
            "The compliance statement for management of VRTR instances
             on Alcatel 7450 ESS series systems release R6.0."
    MODULE  -- this module
        MANDATORY-GROUPS {
            tmnxVRtrGlobalV6v0Group,
            tmnxVRtrV6v0Group,
            tmnxVRtrIfV5v0Group,
            tmnxVRtrIpV5v0Group,
            -- tmnxVRtrIPv6V4v0Group,
            -- tmnxVRtrIPv6IpV5v0Group,
            -- tmnxVRtrIPv6IfV4v0Group,
            -- tmnxVRtrIfDhcpServerGroup,
            tmnxVRtrNotificationV6v0Group,
            tmnxVRtrIfSubscrAuthV3v0Group,
            tmnxVRtrBfdV6v0Group,
            tmnxVRtrStaticRteCPEChkV6v0Group,
            -- tmnxVRtrIfIpcpV6v0Group,
            tmnxDscpAppV6v0Group,
            tmnxVRtrIfDHCPRelayGroup
        }
    ::= { tmnxVRtrCompliances 8 }

tmnxVRtr77x0V6v0Compliance  MODULE-COMPLIANCE
    STATUS  current
    DESCRIPTION
            "The compliance statement for management of VRTR instances
             on Alcatel 7x50 SR series systems release R6.0."
    MODULE  -- this module
        MANDATORY-GROUPS {
            tmnxVRtrGlobalV6v0Group,
            tmnxVRtrV6v0Group,
            tmnxVRtrIfV5v0Group,
            tmnxVRtrIpV5v0Group,
            tmnxVRtrIPv6V4v0Group,
            tmnxVRtrIPv6IpV5v0Group,
            tmnxVRtrIPv6IfV4v0Group,
            tmnxVRtrIfDhcpServerGroup,
            tmnxVRtrNotificationV6v0Group,
            tmnxVRtrIfSubscrAuthV3v0Group,
            tmnxVRtrBfdV6v0Group,
            tmnxVRtrStaticRteCPEChkV6v0Group,
            tmnxVRtrIfIpcpV6v0Group,
            tmnxVRtrIfCpmProtectGroup,
            tmnxDscpAppV6v0Group,
            tmnxVRtrIfDHCPRelayGroup
         }
    ::= { tmnxVRtrCompliances 9 }

-- units of conformance

-- tmnxVRtrGlobalGroup   OBJECT-GROUP
--    ::= { tmnxVRtrGroups 1 }

-- tmnxVRtrGroup       OBJECT-GROUP
--    ::= { tmnxVRtrGroups 2 }

-- tmnxVRtrIfGroup       OBJECT-GROUP
--    ::= { tmnxVRtrGroups 3 }

-- tmnxVRtrIpGroup       OBJECT-GROUP
--    ::= { tmnxVRtrGroups 4 }

-- tmnxVRtrNotificationGroup NOTIFICATION-GROUP
--    ::= { tmnxVRtrGroups 5 }

-- tmnxVRtrR2r1Group       OBJECT-GROUP
--    ::= { tmnxVRtrGroups 6 }

-- tmnxVRtrIpR2r1Group       OBJECT-GROUP
--    ::= { tmnxVRtrGroups 7 }

-- tmnxVRtrNotificationR2r1Group NOTIFICATION-GROUP
--    ::= { tmnxVRtrGroups 8 }

-- tmnxVRtrIfR2r1Group       OBJECT-GROUP
--    ::= { tmnxVRtrGroups 9 }

tmnxVRtrGlobalR2r1Group   OBJECT-GROUP
    OBJECTS {   vRtrNextVRtrID,
                vRtrConfiguredVRtrs,
                vRtrActiveVRtrs,
                vRtrRouteThresholdSoakTime,
                vRtrMaxARPEntries
            }
    STATUS        obsolete
    DESCRIPTION
        "The group of objects supporting management of general
         capabilities for transport and virtual routers
         on version 2.1 Alcatel 7x50 SR series systems."
    ::= { tmnxVRtrGroups 10 }

tmnxVRtrIfSubscrAuthV3v0Group       OBJECT-GROUP
    OBJECTS {   vRtrIfDHCPAuthPolicy,
                vRtrIfDHCPRelayAuthPktsDiscarded,
                vRtrIfDHCPRelayAuthPktsSuccess
            }
    STATUS        current
    DESCRIPTION
        "The  group  of  objects  supporting management of DHCP
         authentication  on  version  3.0 Alcatel 7x50 SR series
         systems."
    ::= { tmnxVRtrGroups 11 }

-- tmnxVRtrIfV3v0Group       OBJECT-GROUP
--    ::= { tmnxVRtrGroups 12 }

-- tmnxVRtrNotificationV3v0Group NOTIFICATION-GROUP
--    ::= { tmnxVRtrGroups 13 }

tmnxVRtrV4v0Group       OBJECT-GROUP
    OBJECTS {   vRtrRowStatus,
                vRtrAdminState,
                vRtrName,
                vRtrMaxNumRoutes,
                vRtrBgpStatus,
                vRtrMplsStatus,
                vRtrOspfStatus,
                vRtrRipStatus,
                vRtrRsvpStatus,
                vRtrEcmpMaxRoutes,
                vRtrAS,
                vRtrNewIfIndex,
                vRtrLdpStatus,
                vRtrIsIsStatus,
                vRtrRouterId,
                vRtrTriggeredPolicy,
                vRtrConfederationAS,
                vRtrRouteDistinguisher,
                vRtrMidRouteThreshold,
                vRtrHighRouteThreshold,
                vRtrIllegalLabelThreshold,
                vRtrVpnId,
                vRtrDescription,
                vRtrGracefulRestart,
                vRtrGracefulRestartType,
                vRtrType,
                vRtrServiceId,
                vRtrCustId,
                vRtrIgmpStatus,
                vRtrMaxNumRoutesLogOnly,
                vRtrVrfTarget,
                vRtrVrfExportTarget,
                vRtrVrfImportTarget,
                vRtrPimStatus,
                vRtrMaxMcastNumRoutes,
                vRtrMaxMcastNumRoutesLogOnly,
                vRtrMcastMidRouteThreshold,
                vRtrIgnoreIcmpRedirect,
                vRtrOspfv3Status,
                vRtrImportPolicy1,
                vRtrImportPolicy2,
                vRtrImportPolicy3,
                vRtrImportPolicy4,
                vRtrImportPolicy5,
                vRtrExportPolicy1,
                vRtrExportPolicy2,
                vRtrExportPolicy3,
                vRtrExportPolicy4,
                vRtrExportPolicy5,
                vRtrOperState,
                vRtrDirectRoutes,
                vRtrDirectActiveRoutes,
                vRtrStaticRoutes,
                vRtrStaticActiveRoutes,
                vRtrOSPFRoutes,
                vRtrOSPFActiveRoutes,
                vRtrBGPRoutes,
                vRtrBGPActiveRoutes,
                vRtrISISRoutes,
                vRtrISISActiveRoutes,
                vRtrRIPRoutes,
                vRtrRIPActiveRoutes,
                vRtrAggregateRoutes,
                vRtrAggregateActiveRoutes,
                vRtrStatConfiguredIfs,
                vRtrStatActiveIfs,
                vRtrStatIllegalLabels,
                vRtrStatCurrNumRoutes,
                vRtrStatBGPVpnRoutes,
                vRtrStatBGPVpnActiveRoutes,
                vRtrStatTotalLdpTunnels,
                vRtrStatTotalSdpTunnels,
                vRtrStatActiveLdpTunnels,
                vRtrStatActiveSdpTunnels,
                vRtrMulticastRoutes,
                vRtrStatActiveARPEntries,
                vRtrStatTotalARPEntries,
                vRtrSubMgmtRoutes,
                vRtrSubMgmtActiveRoutes
            }
    STATUS        obsolete
    DESCRIPTION
        "The group of objects supporting management of transport and
         virtual routers on version 4.0 Alcatel 7x50 SR series systems."
    ::= { tmnxVRtrGroups 14 }

tmnxVRtrIfV4v0Group       OBJECT-GROUP
    OBJECTS {   vRtrIfTotalNumber,
                vRtrIfRowStatus,
                vRtrIfType,
                vRtrIfName,
                vRtrIfPortID,
                vRtrIfChannelID,
                vRtrIfEncapValue,
                vRtrIfAdminState,
                vRtrIfOperState,
                vRtrIfAlias,
                vRtrIfPhysicalAddress,
                vRtrIfArpTimeout,
                vRtrIfIcmpMaskReply,
                vRtrIfIcmpRedirects,
                vRtrIfIcmpNumRedirects,
                vRtrIfIcmpRedirectsTime,
                vRtrIfIcmpUnreachables,
                vRtrIfIcmpNumUnreachables,
                vRtrIfIcmpUnreachablesTime,
                vRtrIfIcmpTtlExpired,
                vRtrIfIcmpNumTtlExpired,
                vRtrIfIcmpTtlExpiredTime,
                vRtrIfNtpBroadcast,
                vRtrIfUnnumbered,
                vRtrIfMtu,
                vRtrIfQosPolicyId,
                vRtrIfIngressFilterId,
                vRtrIfEgressFilterId,
                vRtrIfDirectedBroadcast,
                vRtrIfMplsStatus,
                vRtrIfUnnumberedIf,
                vRtrIfCflowd,
                vRtrIfVPNClass,
                vRtrIfDescription,
                vRtrIfProtocol,
                vRtrIfTosMarkingTrusted,
                vRtrIfServiceId,
                vRtrIfArpPopulate,
                vRtrIfProxyArp,
                vRtrIfProxyArpLocal,
                vRtrIfProxyArpPolicy1,
                vRtrIfProxyArpPolicy2,
                vRtrIfProxyArpPolicy3,
                vRtrIfProxyArpPolicy4,
                vRtrIfProxyArpPolicy5,
                vRtrIfNameIndex,
                vRtrIfDHCPRelayInfoAction,
                vRtrIfDHCPRelayCircuitId,
                vRtrIfDHCPRelayRemoteId,
                vRtrIfDHCPRelayServer1,
                vRtrIfDHCPRelayServer2,
                vRtrIfDHCPRelayServer3,
                vRtrIfDHCPRelayServer4,
                vRtrIfDHCPRelayServer5,
                vRtrIfDHCPRelayServer6,
                vRtrIfDHCPRelayServer7,
                vRtrIfDHCPRelayServer8,
                vRtrIfDHCPRelayTrusted,
                vRtrIfDHCPAdminState,
                vRtrIfDHCPDescription,
                vRtrIfDHCPRelayRxPkts,
                vRtrIfDHCPRelayTxPkts,
                vRtrIfDHCPRelayRxMalformedPkts,
                vRtrIfDHCPRelayRxUntrustedPkts,
                vRtrIfDHCPRelayClientPktsDiscarded,
                vRtrIfDHCPRelayClientPktsRelayed,
                vRtrIfDHCPRelayServerPktsDiscarded,
                vRtrIfDHCPRelayServerPktsRelayed,
                vRtrIfDHCPRelayClientPktsSnooped,
                vRtrIfDHCPRelayServerPktsSnooped,
                vRtrIfDHCPLeasePopulate,
                vRtrIfDHCPOperLeasePopulate,
                vRtrIfDHCPGiAddressType,
                vRtrIfDHCPGiAddress,
                vRtrIfDHCPGiAddressAsSrc,
                vRtrIfDHCPMatchOption82
            }
    STATUS        obsolete
    DESCRIPTION
        "The group of objects supporting management of virtual
         interfaces on version 4.0 Alcatel 7x50 SR series systems."
    ::= { tmnxVRtrGroups 15 }

tmnxVRtrIpV4v0Group       OBJECT-GROUP
    OBJECTS {   vRiaRowStatus,
                vRiaIpAddress,
                vRiaNetMask,
                vRiaBcastAddrFormat,
                vRiaReasmMaxSize,
                vRiaIgpInhibit,
                vRiaInetAddressType,
                vRiaInetAddress,
                vRiaInetPrefixLen,
                vRiaInetAddrState,
                vRiaInetEui64,
                vRiaInetOperAddress,
                vRtrIpCidrRouteLastEnabledTime,
                vRtrIpCidrRoutePreference,
                vRtrIpCidrRouteMetric,
                vRtrStaticRouteDest,
                vRtrStaticRouteMask,
                vRtrStaticRouteIndex,
                vRtrStaticRouteNumber,
                vRtrStaticRouteRowStatus,
                vRtrStaticRouteLastEnabledTime,
                vRtrStaticRouteStatus,
                vRtrStaticRouteStaticType,
                vRtrStaticRoutePreference,
                vRtrStaticRouteMetric,
                vRtrStaticRouteEgressIfIndex,
                vRtrStaticRouteNextHop,
                vRtrStaticRouteNextHopUnnumberedIf,
                vRtrStaticRouteAdminState,
                vRtrStaticRouteIgpShortcut,
                vRtrStaticRouteDisallowIgp,
                vRtrStaticRouteTag,
                vRtrStaticRouteIndexDest,
                vRtrStaticRouteIndexMask,
                vRtrStaticRouteAvailableIndex,
                vRtrInetStaticRouteRowStatus,
                vRtrInetStaticRouteLastEnabledTime,
                vRtrInetStaticRouteStatus,
                vRtrInetStaticRouteStaticType,
                vRtrInetStaticRoutePreference,
                vRtrInetStaticRouteMetric,
                vRtrInetStaticRouteEgressIfIndex,
                vRtrInetStaticRouteNextHopType,
                vRtrInetStaticRouteNextHop,
                vRtrInetStaticRouteNextHopIf,
                vRtrInetStaticRouteAdminState,
                vRtrInetStaticRouteIgpShortcut,
                vRtrInetStaticRouteDisallowIgp,
                vRtrInetStaticRouteTag,
                vRtrInetStaticRouteEnableBfd,
                vRtrInetStaticRouteAvailIndex,
                vRtrSvcIpRangeAddress,
                vRtrSvcIpRangeMask,
                vRtrSvcIpRangeRowStatus,
                vRtrSvcIpRangeExclusive,
                vRtrIpNetToMediaTimer,
                vRtrIpNetToMediaOperState,
                vRtrInstanceAggregationTableLastChanged,
                vRtrAggregationRowStatus,
                vRtrAggregationLastChanged,
                vRtrAggregationSummaryOnly,
                vRtrAggregationASSet,
                vRtrAggregationAggregatorAS,
                vRtrAggregationAggregatorIPAddr,
                vRtrAggregationOperState,
                vRtrTunnelMetric,
                vRtrTunnelAge,
                vRtrAdvPrefixOnLinkFlag,
                vRtrAdvPrefixAutonomousFlag,
                vRtrAdvPrefixPreferredLifetime,
                vRtrAdvPrefixValidLifetime,
                vRtrAdvPrefixRowStatus,
                vRtrInetInstAggrTblLastChged,
                vRtrInetAggrRowStatus,
                vRtrInetAggrLastChanged,
                vRtrInetAggrSummaryOnly,
                vRtrInetAggrASSet,
                vRtrInetAggrAggregatorAS,
                vRtrInetAggrAggregatorIPAddr,
                vRtrInetAggrOperState,
                vRtrInetSvcIpRangeRowStatus,
--              ALCATEL CHANG
--              vRtrInetSvcIpRangeExclusive,
                vRtrInetSvcIpRangeExclusive
--              ALCATEL CHANGE    
--              ALCATEL CHANGE    
--              vRtrIpNetToPhysicalTimer,
--              vRtrIpNetToPhysicalOperState,
--              vRtrIpNetToPhysicalIsRouter,
--              vRtrIpNetToPhysicalMTU,
--              vRtrIpNetToPhysicalPort,
--              vRtrIpNetToPhysicalEncap,
--              vRtrInetCidrRouteLastEnabledTime,
--              vRtrInetCidrRoutePreference,
--              vRtrInetCidrRouteMetric
--              ALCATEL CHANG
            }
    STATUS        obsolete
    DESCRIPTION
        "The group of objects supporting management of IP capabilities
         for transport and virtual routers on version 4.0 Alcatel 7x50 SR
         series systems."
    ::= { tmnxVRtrGroups 16 }

tmnxVRtrObsoletedObjectsV4v0Group OBJECT-GROUP
    OBJECTS {
                vRtrIfDHCPLseStateChAddr,
                vRtrIfDHCPLseStateRemainLseTime,
                vRtrIfDHCPLseStateOption82,
                vRtrIfDHCPLseStatePersistKey,
                vRtrDHCPClientLease,
                vRtrDhcpLseStateOldCiAddr,
                vRtrDhcpLseStateOldChAddr,
                vRtrDhcpLseStateNewCiAddr,
                vRtrDhcpLseStateNewChAddr,
                vRtrDhcpRestoreLseStateCiAddr,
                vRtrDhcpRestoreLseStateVRtrId,
                vRtrDhcpRestoreLseStateIfIndex,
                vRtrDhcpRestoreLseStateProblem,
                vRtrDhcpLseStatePopulateError,
                vRtrIfDHCPRelayInfoOption,
                vRtrIfDHCPAutoFilter,
                vRtrIfDHCPSnooping,
                vRtrIfDHCPAutoFilterId,
                vRtrIfDHCPOperAutoFilter,
                vRtrAutoFilterDHCPClientAddress,
                vRtrAutoFilterDHCPClientLease
            }
    STATUS      current
    DESCRIPTION
        "The group of objects no longer supported in version 4.0
         of Alcatel 7x50 SR  series systems."
    ::= { tmnxVRtrGroups 17 }

tmnxVRtrBfdV4v0Group    OBJECT-GROUP
    OBJECTS {
                vRtrIfBfdAdminState,
                vRtrIfBfdTransmitInterval,
                vRtrIfBfdReceiveInterval,
                vRtrIfBfdMultiplier,
                vRtrIfBfdSessionOperState,
                vRtrIfBfdSessionState,
                vRtrIfBfdSessionOperFlags,
                vRtrIfBfdSessionMesgRecv,
                vRtrIfBfdSessionMesgSent,
                vRtrIfBfdSessionLastDownTime,
                vRtrIfBfdSessionLastUpTime,
                vRtrIfBfdSessionUpCount,
                vRtrIfBfdSessionDownCount,
                vRtrIfBfdSessionLclDisc,
                vRtrIfBfdSessionRemDisc,
                vRtrIfBfdSessionProtocols,
                vRtrIfBfdSessionTxInterval,
                vRtrIfBfdSessionRxInterval
            }
     STATUS     obsolete
     DESCRIPTION
         "The group of objects supporting Bi-directional Forwarding
          Detection on version 4.0 Alcatel 7x50 series systems."
     ::= { tmnxVRtrGroups 18 }

tmnxVRtrNotificationV4v0Group NOTIFICATION-GROUP
    NOTIFICATIONS   {   tmnxVRtrMidRouteTCA,
                        tmnxVRtrHighRouteTCA,
                        tmnxVRtrHighRouteCleared,
                        tmnxVRtrIllegalLabelTCA,
                        tmnxVRtrMcastMidRouteTCA,
                        tmnxVRtrMcastMaxRoutesTCA,
                        tmnxVRtrMcastMaxRoutesCleared,
                        tmnxVRtrMaxArpEntriesTCA,
                        tmnxVRtrMaxArpEntriesCleared,
                        tmnxVRtrMaxRoutes,
                        tmnxVRtrDHCPSuspiciousPcktRcvd,
                        tmnxVRtrBfdSessionDown,
                        tmnxVRtrBfdMaxSessionOnSlot,
                        tmnxVRtrBfdPortTypeNotSupported
                    }
    STATUS        obsolete
    DESCRIPTION
        "The group of notifications supporting the transport and
         virtual router capabilities on version 4.0 Alcatel 7x50 SR series
         systems."
    ::= { tmnxVRtrGroups 19 }

tmnxVRtrIPv6IfV4v0Group       OBJECT-GROUP
    OBJECTS {   vRtrIfIPv6ConfigAllowed,
                vRtrIfIPv6OperState,
                vRtrIfIPv6IngressFilterId,
                vRtrIfIPv6EgressFilterId,
                vRtrIfIcmpV6Redirects,
                vRtrIfIcmpV6NumRedirects,
                vRtrIfIcmpV6RedirectsTime,
                vRtrIfIcmpV6Unreachables,
                vRtrIfIcmpV6NumUnreachables,
                vRtrIfIcmpV6UnreachablesTime,
                vRtrIfIcmpV6TimeExceeded,
                vRtrIfIcmpV6NumTimeExceeded,
                vRtrIfIcmpV6TimeExceededTime,
                vRtrIfIcmpV6PktTooBig,
                vRtrIfIcmpV6NumPktTooBig,
                vRtrIfIcmpV6PktTooBigTime,
                vRtrIfIcmpV6ParamProblem,
                vRtrIfIcmpV6NumParamProblem,
                vRtrIfIcmpV6ParamProblemTime,
                vRtrIfLinkLocalAddressType,
                vRtrIfLinkLocalAddressState,
                vRtrIfLinkLocalAddress,
                vRtrIfIcmp6InMsgs,
                vRtrIfIcmp6InErrors,
                vRtrIfIcmp6InDestUnreachs,
                vRtrIfIcmp6InAdminProhibs,
                vRtrIfIcmp6InTimeExcds,
                vRtrIfIcmp6InParmProblems,
                vRtrIfIcmp6InPktTooBigs,
                vRtrIfIcmp6InEchos,
                vRtrIfIcmp6InEchoReplies,
                vRtrIfIcmp6InRtrSolicits,
                vRtrIfIcmp6InRtrAdvertisements,
                vRtrIfIcmp6InNbrSolicits,
                vRtrIfIcmp6InNbrAdvertisements,
                vRtrIfIcmp6InRedirects,
                vRtrIfIcmp6InGrpMembQueries,
                vRtrIfIcmp6InGrpMembResponses,
                vRtrIfIcmp6InGrpMembReductions,
                vRtrIfIcmp6OutMsgs,
                vRtrIfIcmp6OutErrors,
                vRtrIfIcmp6OutDestUnreachs,
                vRtrIfIcmp6OutAdminProhibs,
                vRtrIfIcmp6OutTimeExcds,
                vRtrIfIcmp6OutParmProblems,
                vRtrIfIcmp6OutPktTooBigs,
                vRtrIfIcmp6OutEchos,
                vRtrIfIcmp6OutEchoReplies,
                vRtrIfIcmp6OutRtrSolicits,
                vRtrIfIcmp6OutRtrSolicitsTime,
                vRtrIfIcmp6OutRtrAdvertisements,
                vRtrIfIcmp6OutRtrAdvTime,
                vRtrIfIcmp6OutNbrSolicits,
                vRtrIfIcmp6OutNbrSolicitsTime,
                vRtrIfIcmp6OutNbrAdvertisements,
                vRtrIfIcmp6OutNbrAdvTime,
                vRtrIfIcmp6OutRedirects,
                vRtrIfIcmp6OutGrpMembQueries,
                vRtrIfIcmp6OutGrpMembResponses,
                vRtrIfIcmp6OutGrpMembReductions,
                vRtrIcmp6InMsgs,
                vRtrIcmp6InErrors,
                vRtrIcmp6InDestUnreachs,
                vRtrIcmp6InAdminProhibs,
                vRtrIcmp6InTimeExcds,
                vRtrIcmp6InParmProblems,
                vRtrIcmp6InPktTooBigs,
                vRtrIcmp6InEchos,
                vRtrIcmp6InEchoReplies,
                vRtrIcmp6InRtrSolicits,
                vRtrIcmp6InRtrAdvertisements,
                vRtrIcmp6InNbrSolicits,
                vRtrIcmp6InNbrAdvertisements,
                vRtrIcmp6InRedirects,
                vRtrIcmp6InGrpMembQueries,
                vRtrIcmp6InGrpMembResponses,
                vRtrIcmp6InGrpMembReductions,
                vRtrIcmp6OutMsgs,
                vRtrIcmp6OutErrors,
                vRtrIcmp6OutDestUnreachs,
                vRtrIcmp6OutAdminProhibs,
                vRtrIcmp6OutTimeExcds,
                vRtrIcmp6OutParmProblems,
                vRtrIcmp6OutPktTooBigs,
                vRtrIcmp6OutEchos,
                vRtrIcmp6OutEchoReplies,
                vRtrIcmp6OutRtrSolicits,
                vRtrIcmp6OutRtrAdvertisements,
                vRtrIcmp6OutNbrSolicits,
                vRtrIcmp6OutNbrAdvertisements,
                vRtrIcmp6OutRedirects,
                vRtrIcmp6OutGrpMembQueries,
                vRtrIcmp6OutGrpMembResponses,
                vRtrIcmp6OutGrpMembReductions
            }
    STATUS        current
    DESCRIPTION
        "The group of objects supporting management of IPv6 virtual
         interfaces on version 4.0 Alcatel 7x50 SR series systems."
    ::= { tmnxVRtrGroups 20 }

tmnxVRtrIPv6V4v0Group       OBJECT-GROUP
    OBJECTS {   vRtrV6DirectRoutes,
                vRtrV6DirectActiveRoutes,
                vRtrV6StaticRoutes,
                vRtrV6StaticActiveRoutes,
                vRtrV6OSPFRoutes,
                vRtrV6OSPFActiveRoutes,
                vRtrV6BGPRoutes,
                vRtrV6BGPActiveRoutes,
                vRtrV6ISISRoutes,
                vRtrV6ISISActiveRoutes,
                vRtrV6RIPRoutes,
                vRtrV6RIPActiveRoutes,
                vRtrV6AggregateRoutes,
                vRtrV6AggregateActiveRoutes,
                vRtrV6StatConfiguredIfs,
                vRtrV6StatActiveIfs,
                vRtrV6StatIllegalLabels,
                vRtrV6StatCurrNumRoutes,
                vRtrV6StatBGPVpnRoutes,
                vRtrV6StatBGPVpnActiveRoutes,
                vRtrV6StatTotalLdpTunnels,
                vRtrV6StatTotalSdpTunnels,
                vRtrV6StatActiveLdpTunnels,
                vRtrV6StatActiveSdpTunnels,
                vRtrV6MulticastRoutes,
                vRtrV6StatActiveNbrEntries,
                vRtrV6StatTotalNbrEntries
            }
    STATUS        current
    DESCRIPTION
        "The group of objects supporting management of IPv6 transport and
         virtual routers on version 4.0 Alcatel 7x50 SR series systems."
    ::= { tmnxVRtrGroups 21 }

tmnxVRtrIPv6IpV4v0Group       OBJECT-GROUP
    OBJECTS {   vRtrAdvPrefixOnLinkFlag,
                vRtrAdvPrefixAutonomousFlag,
                vRtrAdvPrefixPreferredLifetime,
                vRtrAdvPrefixValidLifetime,
                vRtrAdvPrefixRowStatus
            }
    STATUS        obsolete
    DESCRIPTION
        "The group of objects supporting management of Ipv6 IP capabilities
         for transport and virtual routers on version 4.0 Alcatel 7x50 SR
         series systems."
    ::= { tmnxVRtrGroups 22 }

tmnxVRtrObsoleteNotificationGroup NOTIFICATION-GROUP
    NOTIFICATIONS   {   tmnxVRtrDHCPAFEntriesExceeded,
                        tmnxVRtrDHCPLseStsExceeded,
                        tmnxVRtrDHCPLeaseStateOverride,
                        tmnxVRtrDHCPLseStRestoreProblem,
                        tmnxVRtrDHCPLseStatePopulateErr
                    }
    STATUS        current
    DESCRIPTION
        "The group of obsolete notifications for the transport and
         virtual router capabilities on Alcatel 7x50 SR series systems."
    ::= { tmnxVRtrGroups 23 }

tmnxVRtrIPv6IpV5v0Group       OBJECT-GROUP
    OBJECTS {   vRtrAdvPrefixOnLinkFlag,
                vRtrAdvPrefixAutonomousFlag,
                vRtrAdvPrefixPreferredLifetime,
                vRtrAdvPrefixValidLifetime,
                vRtrAdvPrefixRowStatus,
                vRtrIfDHCP6TableLastChanged,
                vRtrIfDHCP6LastChanged,
                vRtrIfDHCP6AdminState,
                vRtrIfDHCP6OperState,
                vRtrIfDHCP6Description,
                vRtrIfDHCP6RelayServer1,
                vRtrIfDHCP6RelayServer2,
                vRtrIfDHCP6RelayServer3,
                vRtrIfDHCP6RelayServer4,
                vRtrIfDHCP6RelayServer5,
                vRtrIfDHCP6RelayServer6,
                vRtrIfDHCP6RelayServer7,
                vRtrIfDHCP6RelayServer8,
                vRtrIfDHCP6RelayItfIdOption,
                vRtrIfDHCP6LeasePopulate,
                vRtrIfDHCP6CurrLeasePopulate,
                vRtrIfDHCP6SourceAddress,
                vRtrIfDHCP6EnableNgbrResolution,
                vRtrIfDHCP6RemoteIdOption,
                vRtrIfDHCP6PfxdAdminState,
                vRtrIfDHCP6ServerMaxLeaseStates,
                vRtrIfDHCP6CurrServerLeaseStates,
                vRtrIfDHCP6ItfIdString,
                vRtrIfProxyNDLocal,
                vRtrIfProxyNDPolicy1,
                vRtrIfProxyNDPolicy2,
                vRtrIfProxyNDPolicy3,
                vRtrIfProxyNDPolicy4,
                vRtrIfProxyNDPolicy5,
                vRtrIfDHCP6PfxdRowStatus,
                vRtrIfDHCP6PfxdLastChanged,
                vRtrIfDHCP6PfxdDUID,
                vRtrIfDHCP6PfxdIAID,
                vRtrIfDHCP6PfxdPrefLifetime,
                vRtrIfDHCP6PfxdValidLifetime,
                vRtrIfDHCP6PfxDelegationLstChgd
            }
    STATUS        current
    DESCRIPTION
        "The group of objects supporting management of Ipv6 IP capabilities
         for transport and virtual routers on version 5.0 Alcatel 7x50 SR
         series systems."
    ::= { tmnxVRtrGroups 24 }

tmnxVRtrIfV5v0Group       OBJECT-GROUP
    OBJECTS {   vRtrIfTotalNumber,
                vRtrIfRowStatus,
                vRtrIfType,
                vRtrIfName,
                vRtrIfPortID,
                vRtrIfEncapValue,
                vRtrIfAdminState,
                vRtrIfOperState,
                vRtrIfAlias,
                vRtrIfPhysicalAddress,
                vRtrIfArpTimeout,
                vRtrIfIcmpMaskReply,
                vRtrIfIcmpRedirects,
                vRtrIfIcmpNumRedirects,
                vRtrIfIcmpRedirectsTime,
                vRtrIfIcmpUnreachables,
                vRtrIfIcmpNumUnreachables,
                vRtrIfIcmpUnreachablesTime,
                vRtrIfIcmpTtlExpired,
                vRtrIfIcmpNumTtlExpired,
                vRtrIfIcmpTtlExpiredTime,
                vRtrIfNtpBroadcast,
                vRtrIfUnnumbered,
                vRtrIfMtu,
                vRtrIfQosPolicyId,
                vRtrIfIngressFilterId,
                vRtrIfEgressFilterId,
                vRtrIfDirectedBroadcast,
                vRtrIfMplsStatus,
                vRtrIfUnnumberedIf,
                vRtrIfCflowd,
                vRtrIfVPNClass,
                vRtrIfDescription,
                vRtrIfProtocol,
                vRtrIfTosMarkingTrusted,
                vRtrIfServiceId,
                vRtrIfArpPopulate,
                vRtrIfLastOperStateChange,
                vRtrIfOperMtu,
                vRtrIfGlobalIndex,
                vRtrIfProxyArp,
                vRtrIfProxyArpLocal,
                vRtrIfProxyArpPolicy1,
                vRtrIfProxyArpPolicy2,
                vRtrIfProxyArpPolicy3,
                vRtrIfProxyArpPolicy4,
                vRtrIfProxyArpPolicy5,
                vRtrIfNameIndex,
                vRtrIfDHCPRelayInfoAction,
                vRtrIfDHCPRelayCircuitId,
                vRtrIfDHCPRelayRemoteId,
                vRtrIfDHCPRelayServer1,
                vRtrIfDHCPRelayServer2,
                vRtrIfDHCPRelayServer3,
                vRtrIfDHCPRelayServer4,
                vRtrIfDHCPRelayServer5,
                vRtrIfDHCPRelayServer6,
                vRtrIfDHCPRelayServer7,
                vRtrIfDHCPRelayServer8,
                vRtrIfDHCPRelayTrusted,
                vRtrIfDHCPAdminState,
                vRtrIfDHCPDescription,
                vRtrIfDHCPRelayRxPkts,
                vRtrIfDHCPRelayTxPkts,
                vRtrIfDHCPRelayRxMalformedPkts,
                vRtrIfDHCPRelayRxUntrustedPkts,
                vRtrIfDHCPRelayClientPktsDiscarded,
                vRtrIfDHCPRelayClientPktsRelayed,
                vRtrIfDHCPRelayServerPktsDiscarded,
                vRtrIfDHCPRelayServerPktsRelayed,
                vRtrIfDHCPRelayClientPktsSnooped,
                vRtrIfDHCPRelayServerPktsSnooped,
                vRtrIfDHCPRelayClientPktsProxRad,
                vRtrIfDHCPRelayClientPktsProxLS,
                vRtrIfDHCPRelayPktsGenRelease,
                vRtrIfDHCPRelayPktsGenForceRenew,
                vRtrIfDHCPLeasePopulate,
                vRtrIfDHCPOperLeasePopulate,
                vRtrIfDHCPGiAddressType,
                vRtrIfDHCPGiAddress,
                vRtrIfDHCPGiAddressAsSrc,
                vRtrIfDHCPMatchOption82,
                vRtrIfDHCPRelayRemoteIdStr,
                vRtrIfDHCPProxyAdminState,
                vRtrIfDHCPProxyServerAddr,
                vRtrIfDHCPProxyLeaseTime,
                vRtrIfDHCPProxyLTRadiusOverride,
                vRtrIfDHCPVendorIncludeOptions,
                vRtrIfDHCPVendorOptionString,
                vRtrIfGlobalIndexvRtrID,
                vRtrIfGlobalIndexvRtrIfIndex,
                vRtrIfDelaySeconds,
                vRtrIfDelayUpTimer,
                vRtrIfInitDelayEnable
            }
    STATUS        current
    DESCRIPTION
        "The group of objects supporting management of virtual
         interfaces on version 5.0 Alcatel 7x50 SR series systems."
    ::= { tmnxVRtrGroups 25 }

tmnxVRtrIpV5v0Group       OBJECT-GROUP
    OBJECTS {   vRiaRowStatus,
                vRiaIpAddress,
                vRiaNetMask,
                vRiaBcastAddrFormat,
                vRiaReasmMaxSize,
                vRiaIgpInhibit,
                vRiaInetAddressType,
                vRiaInetAddress,
                vRiaInetPrefixLen,
                vRiaInetAddrState,
                vRiaInetEui64,
                vRiaInetOperAddress,
                vRiaInetGwAddressType,
                vRiaInetGwAddress,
                vRiaInetRemoteIpType,
                vRiaInetRemoteIp,
                vRtrIpCidrRouteLastEnabledTime,
                vRtrIpCidrRoutePreference,
                vRtrIpCidrRouteMetric,
                vRtrStaticRouteDest,
                vRtrStaticRouteMask,
                vRtrStaticRouteIndex,
                vRtrStaticRouteNumber,
                vRtrStaticRouteRowStatus,
                vRtrStaticRouteLastEnabledTime,
                vRtrStaticRouteStatus,
                vRtrStaticRouteStaticType,
                vRtrStaticRoutePreference,
                vRtrStaticRouteMetric,
                vRtrStaticRouteEgressIfIndex,
                vRtrStaticRouteNextHop,
                vRtrStaticRouteNextHopUnnumberedIf,
                vRtrStaticRouteAdminState,
                vRtrStaticRouteIgpShortcut,
                vRtrStaticRouteDisallowIgp,
                vRtrStaticRouteTag,
                vRtrStaticRouteIndexDest,
                vRtrStaticRouteIndexMask,
                vRtrStaticRouteAvailableIndex,
                vRtrInetStaticRouteRowStatus,
                vRtrInetStaticRouteLastEnabledTime,
                vRtrInetStaticRouteStatus,
                vRtrInetStaticRouteStaticType,
                vRtrInetStaticRoutePreference,
                vRtrInetStaticRouteMetric,
                vRtrInetStaticRouteEgressIfIndex,
                vRtrInetStaticRouteNextHopType,
                vRtrInetStaticRouteNextHop,
                vRtrInetStaticRouteNextHopIf,
                vRtrInetStaticRouteAdminState,
                vRtrInetStaticRouteIgpShortcut,
                vRtrInetStaticRouteDisallowIgp,
                vRtrInetStaticRouteTag,
                vRtrInetStaticRouteEnableBfd,
                vRtrInetStaticRouteAvailIndex,
                vRtrSvcIpRangeAddress,
                vRtrSvcIpRangeMask,
                vRtrSvcIpRangeRowStatus,
                vRtrSvcIpRangeExclusive,
                vRtrIpNetToMediaTimer,
                vRtrIpNetToMediaOperState,
                vRtrInstanceAggregationTableLastChanged,
                vRtrAggregationRowStatus,
                vRtrAggregationLastChanged,
                vRtrAggregationSummaryOnly,
                vRtrAggregationASSet,
                vRtrAggregationAggregatorAS,
                vRtrAggregationAggregatorIPAddr,
                vRtrAggregationOperState,
                vRtrTunnelMetric,
                vRtrTunnelAge,
                vRtrAdvPrefixOnLinkFlag,
                vRtrAdvPrefixAutonomousFlag,
                vRtrAdvPrefixPreferredLifetime,
                vRtrAdvPrefixValidLifetime,
                vRtrAdvPrefixRowStatus,
                vRtrInetInstAggrTblLastChged,
                vRtrInetAggrRowStatus,
                vRtrInetAggrLastChanged,
                vRtrInetAggrSummaryOnly,
                vRtrInetAggrASSet,
                vRtrInetAggrAggregatorAS,
                vRtrInetAggrAggregatorIPAddr,
                vRtrInetAggrOperState,
                vRtrInetSvcIpRangeRowStatus,
--              ALCATEL CHANG
--              vRtrInetSvcIpRangeExclusive,
                vRtrInetSvcIpRangeExclusive
--              ALCATEL CHANGE  
--              ALCATEL CHANGE  
--              vRtrIpNetToPhysicalTimer,
--              vRtrIpNetToPhysicalOperState,
--              vRtrIpNetToPhysicalIsRouter,
--              vRtrIpNetToPhysicalMTU,
--              vRtrIpNetToPhysicalPort,
--              vRtrIpNetToPhysicalEncap,
--              vRtrInetCidrRouteLastEnabledTime,
--              vRtrInetCidrRoutePreference,
--              vRtrInetCidrRouteMetric,
--              vRtrInetCidrRouteIfVRtrId
--              ALCATEL CHANG
            }
    STATUS        current
    DESCRIPTION
        "The group of objects supporting management of IP capabilities
         for transport and virtual routers on version 4.0 Alcatel 7x50 SR
         series systems."
    ::= { tmnxVRtrGroups 26 }

tmnxVRtrV5v0Group       OBJECT-GROUP
    OBJECTS {   vRtrRowStatus,
                vRtrAdminState,
                vRtrName,
                vRtrMaxNumRoutes,
                vRtrBgpStatus,
                vRtrMplsStatus,
                vRtrRipStatus,
                vRtrRsvpStatus,
                vRtrEcmpMaxRoutes,
                vRtrAS,
                vRtrNewIfIndex,
                vRtrLdpStatus,
                vRtrIsIsStatus,
                vRtrRouterId,
                vRtrTriggeredPolicy,
                vRtrConfederationAS,
                vRtrRouteDistinguisher,
                vRtrMidRouteThreshold,
                vRtrHighRouteThreshold,
                vRtrIllegalLabelThreshold,
                vRtrVpnId,
                vRtrDescription,
                vRtrGracefulRestart,
                vRtrGracefulRestartType,
                vRtrType,
                vRtrServiceId,
                vRtrCustId,
                vRtrIgmpStatus,
                vRtrMaxNumRoutesLogOnly,
                vRtrVrfTarget,
                vRtrVrfExportTarget,
                vRtrVrfImportTarget,
                vRtrPimStatus,
                vRtrMaxMcastNumRoutes,
                vRtrMaxMcastNumRoutesLogOnly,
                vRtrMcastMidRouteThreshold,
                vRtrIgnoreIcmpRedirect,
                vRtrMsdpStatus,
                vRtrVprnType,
                vRtrSecondaryVrfId,
                vRtrMldStatus,
                vRtrImportPolicy1,
                vRtrImportPolicy2,
                vRtrImportPolicy3,
                vRtrImportPolicy4,
                vRtrImportPolicy5,
                vRtrExportPolicy1,
                vRtrExportPolicy2,
                vRtrExportPolicy3,
                vRtrExportPolicy4,
                vRtrExportPolicy5,
                vRtrOperState,
                vRtrDirectRoutes,
                vRtrDirectActiveRoutes,
                vRtrStaticRoutes,
                vRtrStaticActiveRoutes,
                vRtrOSPFRoutes,
                vRtrOSPFActiveRoutes,
                vRtrBGPRoutes,
                vRtrBGPActiveRoutes,
                vRtrISISRoutes,
                vRtrISISActiveRoutes,
                vRtrRIPRoutes,
                vRtrRIPActiveRoutes,
                vRtrAggregateRoutes,
                vRtrAggregateActiveRoutes,
                vRtrStatConfiguredIfs,
                vRtrStatActiveIfs,
                vRtrStatIllegalLabels,
                vRtrStatCurrNumRoutes,
                vRtrStatBGPVpnRoutes,
                vRtrStatBGPVpnActiveRoutes,
                vRtrStatTotalLdpTunnels,
                vRtrStatTotalSdpTunnels,
                vRtrStatActiveLdpTunnels,
                vRtrStatActiveSdpTunnels,
                vRtrMulticastRoutes,
                vRtrStatActiveARPEntries,
                vRtrStatTotalARPEntries,
                vRtrSubMgmtRoutes,
                vRtrSubMgmtActiveRoutes,
                vRtrStatTotalRsvpTunnels,
                vRtrStatActiveRsvpTunnels,
                vRtrV6StatTotalRsvpTunnels,                   
                vRtrV6StatActiveRsvpTunnels, 
                vRtrDHCP6DropStatLastCleared,
                vRtrDHCP6DropStatPktsDropped,
                vRtrDHCP6MsgStatsLstClrd,
                vRtrDHCP6MsgStatsRcvd,
                vRtrDHCP6MsgStatsSent,
                vRtrDHCP6MsgStatsDropped
            }
    STATUS        obsolete
    DESCRIPTION
        "The group of objects supporting management of transport and
         virtual routers on version 5.0 Alcatel 7x50 SR series systems."
    ::= { tmnxVRtrGroups 27 }

tmnxVRtrNotificationV5v0Group NOTIFICATION-GROUP
    NOTIFICATIONS   {   tmnxVRtrMidRouteTCA,
                        tmnxVRtrHighRouteTCA,
                        tmnxVRtrHighRouteCleared,
                        tmnxVRtrIllegalLabelTCA,
                        tmnxVRtrMcastMidRouteTCA,
                        tmnxVRtrMcastMaxRoutesTCA,
                        tmnxVRtrMcastMaxRoutesCleared,
                        tmnxVRtrMaxArpEntriesTCA,
                        tmnxVRtrMaxArpEntriesCleared,
                        tmnxVRtrMaxRoutes,
                        tmnxVRtrDHCPSuspiciousPcktRcvd,
                        tmnxVRtrBfdSessionDown,
                        tmnxVRtrBfdMaxSessionOnSlot,
                        tmnxVRtrBfdPortTypeNotSupported,
                        tmnxVRtrDHCPIfLseStatesExceeded,
                        tmnxVRtrDHCP6RelayLseStExceeded,
                        tmnxVRtrDHCP6ServerLseStExceeded,
                        tmnxVRtrDHCP6LseStateOverride,
                        tmnxVRtrDHCP6RelayReplyStripUni,
                        tmnxVRtrDHCP6IllegalClientAddr,
                        tmnxVRtrDHCP6AssignedIllegSubnet,
                        tmnxVRtrDHCP6ClientMacUnresolved,
                        tmnxVRtrBfdSessionUp
                    }
    STATUS        obsolete
    DESCRIPTION
        "The group of notifications supporting the transport and
         virtual router capabilities on version 5.0 Alcatel 7xx0 SR series
         systems."
    ::= { tmnxVRtrGroups 28 }

tmnxVRtrObsoleteV5v0Group       OBJECT-GROUP
    OBJECTS {
                vRtrOspfStatus,
                vRtrOspfv3Status,
                vRtrIfChannelID
            }
    STATUS        current
    DESCRIPTION
        "The group of objects in TIMETRA-VRTR-MIB which are obsoleted in
         Alcatel 7x50 SR 5.0 series systems."
    ::= { tmnxVRtrGroups 29 }

tmnxVRtrNotificationObjV5v0Group OBJECT-GROUP
    OBJECTS {
                vRtrID,
                vRtrIfIndex,
                vRtrDhcpPacketProblem,
                vRtrBfdSlotNumber,
                vRtrNumberOfBfdSessionsOnSlot,
                vRtrBfdMaxSessionReason,
                vRtrDHCP6ServerNetAddrType,
                vRtrDHCP6ServerNetAddr,
                vRtrDHCP6ClientNetAddrType,
                vRtrDHCP6ClientNetAddr,
                vRtrDHCP6AssignedNetAddrType,
                vRtrDHCP6AssignedNetAddr,
                vRtrDHCP6AssignedPrefixLen,
                vRtrDHCP6OldAssignedNetAddrType,
                vRtrDHCP6OldAssignedNetAddr,
                vRtrDHCP6OldAssignedPrefixLen,
                vRtrDHCP6NewClientId,
                vRtrDHCP6OldClientId,
                vRtrDHCP6LeaseOverrideResult                
            }
    STATUS      obsolete
    DESCRIPTION
        "The group of objects supporting management of notification objects
         on Alcatel 7x50 SR 5.0 series systems."
    ::= { tmnxVRtrGroups 30 }

tmnxVRtrIfDhcpServerGroup       OBJECT-GROUP
    OBJECTS {
                vRtrIfLocalDhcpServerName
            }
    STATUS        current
    DESCRIPTION
        "The group of objects supporting the DHCP server capabilities
         on version 6.0 Alcatel 7x50 SR series systems."
    ::= { tmnxVRtrGroups 31 }

tmnxVRtrV6v0Group       OBJECT-GROUP
    OBJECTS {   vRtrRowStatus,
                vRtrAdminState,
                vRtrName,
                vRtrMaxNumRoutes,
                vRtrBgpStatus,
                vRtrMplsStatus,
                vRtrRipStatus,
                vRtrRsvpStatus,
                vRtrEcmpMaxRoutes,
                vRtrAS,
                vRtrNewIfIndex,
                vRtrLdpStatus,
                vRtrIsIsStatus,
                vRtrRouterId,
                vRtrTriggeredPolicy,
                vRtrConfederationAS,
                vRtrRouteDistinguisher,
                vRtrMidRouteThreshold,
                vRtrHighRouteThreshold,
                vRtrIllegalLabelThreshold,
                vRtrVpnId,
                vRtrDescription,
                vRtrGracefulRestart,
                vRtrGracefulRestartType,
                vRtrType,
                vRtrServiceId,
                vRtrCustId,
                vRtrIgmpStatus,
                vRtrMaxNumRoutesLogOnly,
                vRtrVrfTarget,
                vRtrVrfExportTarget,
                vRtrVrfImportTarget,
                vRtrPimStatus,
                vRtrMaxMcastNumRoutes,
                vRtrMaxMcastNumRoutesLogOnly,
                vRtrMcastMidRouteThreshold,
                vRtrIgnoreIcmpRedirect,
                vRtrMsdpStatus,
                vRtrVprnType,
                vRtrSecondaryVrfId,
                vRtrMldStatus,
                vRtrIPv6MaxNumRoutes,
                vRtrIPv6MidRouteThreshold,
                vRtrIPv6HighRouteThreshold,
                vRtrIPv6MaxNumRoutesLogOnly,
                vRtrIPv6IgnoreIcmpRedirect,
                vRtrMcPathMgmtPlcyName,
                vRtrImportPolicy1,
                vRtrImportPolicy2,
                vRtrImportPolicy3,
                vRtrImportPolicy4,
                vRtrImportPolicy5,
                vRtrExportPolicy1,
                vRtrExportPolicy2,
                vRtrExportPolicy3,
                vRtrExportPolicy4,
                vRtrExportPolicy5,
                vRtrOperState,
                vRtrDirectRoutes,
                vRtrDirectActiveRoutes,
                vRtrStaticRoutes,
                vRtrStaticActiveRoutes,
                vRtrOSPFRoutes,
                vRtrOSPFActiveRoutes,
                vRtrBGPRoutes,
                vRtrBGPActiveRoutes,
                vRtrISISRoutes,
                vRtrISISActiveRoutes,
                vRtrRIPRoutes,
                vRtrRIPActiveRoutes,
                vRtrAggregateRoutes,
                vRtrAggregateActiveRoutes,
                vRtrStatConfiguredIfs,
                vRtrStatActiveIfs,
                vRtrStatIllegalLabels,
                vRtrStatCurrNumRoutes,
                vRtrStatBGPVpnRoutes,
                vRtrStatBGPVpnActiveRoutes,
                vRtrStatTotalLdpTunnels,
                vRtrStatTotalSdpTunnels,
                vRtrStatActiveLdpTunnels,
                vRtrStatActiveSdpTunnels,
                vRtrMulticastRoutes,
                vRtrStatActiveARPEntries,
                vRtrStatTotalARPEntries,
                vRtrSubMgmtRoutes,
                vRtrSubMgmtActiveRoutes,
                vRtrStatTotalRsvpTunnels,
                vRtrStatActiveRsvpTunnels,
                vRtrV6StatTotalRsvpTunnels,                   
                vRtrV6StatActiveRsvpTunnels, 
                vRtrHostRoutes,
                vRtrHostActiveRoutes,
                vRtrV6HostRoutes,
                vRtrV6HostActiveRoutes,
                vRtrStatLocalARPEntries,
                vRtrStatStaticARPEntries,
                vRtrStatDynamicARPEntries,
                vRtrStatManagedARPEntries,
                vRtrStatInternalARPEntries,
                vRtrDHCP6DropStatLastCleared,
                vRtrDHCP6DropStatPktsDropped,
                vRtrDHCP6MsgStatsLstClrd,
                vRtrDHCP6MsgStatsRcvd,
                vRtrDHCP6MsgStatsSent,
                vRtrDHCP6MsgStatsDropped,
                vRtrManagedRoutes,
                vRtrManagedActiveRoutes
            }
    STATUS        current
    DESCRIPTION
        "The group of objects supporting management of transport and
         virtual routers on version 6.0 Alcatel 7x50 SR series systems."
    ::= { tmnxVRtrGroups 32 }

tmnxVRtrStaticRteCPEChkV6v0Group       OBJECT-GROUP
    OBJECTS {
                vRtrInetStaticRouteCpeAddrType,
                vRtrInetStaticRouteCpeAddr,
                vRtrInetStaticRouteCpeInterval,
                vRtrInetStaticRouteCpeDropCnt,
                vRtrInetStaticRouteCpeEnableLog,
                vRtrInetStatRteCpeChkUpTime,
                vRtrInetStatRteCpeChkInPktCnt,
                vRtrInetStatRteCpeChkOutPktCnt,
                vRtrInetStatRteCpeChkUpTrans,
                vRtrInetStatRteCpeChkDownTrans,
                vRtrInetStatRteCpeChkTTL
            }
    STATUS        current
    DESCRIPTION
        "The group of objects supporting the Static Route CPE Check
         capability on version 6.0 Alcatel 7x50 SR series systems."
    ::= { tmnxVRtrGroups 33 }

tmnxVRtrIfIpcpV6v0Group   OBJECT-GROUP
    OBJECTS {
                vRtrIfIpcpPeerAddrType,
                vRtrIfIpcpPeerAddr,
                vRtrIfIpcpPriDnsAddrType,
                vRtrIfIpcpPriDnsAddr,
                vRtrIfIpcpSecDnsAddrType,
                vRtrIfIpcpSecDnsAddr
            }
    STATUS        current
    DESCRIPTION
        "The group of objects supporting management of IPCP
        extensions for virtual interfaces on version 6.0 Alcatel 
        7x50 SR series systems"
        ::= { tmnxVRtrGroups 34 }

tmnxVRtrIfCpmProtectGroup  OBJECT-GROUP
    OBJECTS {
               vRtrIfCpmProtPolicyId,
               vRtrIfCpmProtUncfgdProtoDropCnt
            }
    STATUS      current
    DESCRIPTION
        "The group of objects supporting management of CPM Protection 
         for virtual interfaces on Alcatel 7xxx series systems."
    ::= { tmnxVRtrGroups 35 }

tmnxDscpAppV6v0Group OBJECT-GROUP
    OBJECTS {
               tmnxDscpAppLastChanged,
               tmnxDscpAppDscpValue,
               tmnxDscpFCLastChanged,
               tmnxDscpFCValue,
               tmnxDscpAppTableLastChanged,
               tmnxDscpFCTableLastChanged,
               tmnxDot1pAppTableLastChanged,
               tmnxDot1pAppLastChanged,
               tmnxDot1pAppValue
            }
    STATUS      current
    DESCRIPTION
        "The group of objects supporting management of DSCP marking for
         self-generated protocol control traffic on Alcatel 7x50 SR series
         systems release 6.0."
    ::= { tmnxVRtrGroups 36 }

tmnxVRtrIfDHCPRelayGroup   OBJECT-GROUP
    OBJECTS {
        vRtrIfDHCPRelayInfoAction,
        vRtrIfDHCPRelayCircuitId,
        vRtrIfDHCPRelayRemoteId,
        vRtrIfDHCPRelayServer1,
        vRtrIfDHCPRelayServer2,
        vRtrIfDHCPRelayServer3,
        vRtrIfDHCPRelayServer4,
        vRtrIfDHCPRelayServer5,
        vRtrIfDHCPRelayServer6,
        vRtrIfDHCPRelayServer7,
        vRtrIfDHCPRelayServer8,
        vRtrIfDHCPRelayTrusted,
        vRtrIfDHCPAdminState,
        vRtrIfDHCPDescription,
        vRtrIfDHCPRelayRxPkts,
        vRtrIfDHCPRelayTxPkts,
        vRtrIfDHCPRelayRxMalformedPkts,
        vRtrIfDHCPRelayRxUntrustedPkts,
        vRtrIfDHCPRelayClientPktsDiscarded,
        vRtrIfDHCPRelayClientPktsRelayed,
        vRtrIfDHCPRelayServerPktsDiscarded,
        vRtrIfDHCPRelayServerPktsRelayed,
        vRtrIfDHCPRelayClientPktsSnooped,
        vRtrIfDHCPRelayServerPktsSnooped,
        vRtrIfDHCPRelayClientPktsProxRad,
        vRtrIfDHCPRelayClientPktsProxLS,
        vRtrIfDHCPRelayPktsGenRelease,
        vRtrIfDHCPRelayPktsGenForceRenew,
        vRtrIfDHCPLeasePopulate,
        vRtrIfDHCPOperLeasePopulate,
        vRtrIfDHCPGiAddressType,
        vRtrIfDHCPGiAddress,
        vRtrIfDHCPGiAddressAsSrc,
        vRtrIfDHCPMatchOption82,
        vRtrIfDHCPRelayRemoteIdStr,
        vRtrIfDHCPProxyAdminState,
        vRtrIfDHCPProxyServerAddr,
        vRtrIfDHCPProxyLeaseTime,
        vRtrIfDHCPProxyLTRadiusOverride,
        vRtrIfDHCPVendorIncludeOptions,
        vRtrIfDHCPVendorOptionString,
        vRtrIfDHCPLayer2Header,
        vRtrIfDHCPAntiSpoofMacAddr,
        vRtrIfDHCPClientApplications,
        vRtrIfLdpSyncTimer
            }
    STATUS        current
    DESCRIPTION
        "The group of objects supporting management of DHCP Relay
        on virtual interfaces on version 6.0 Alcatel 7x50 SR series systems"
    ::= { tmnxVRtrGroups 37 }

tmnxVRtrGlobalV6v0Group   OBJECT-GROUP
    OBJECTS {
        vRtrNextVRtrID,
        vRtrConfiguredVRtrs,
        vRtrActiveVRtrs,
        vRtrRouteThresholdSoakTime,
        vRtrMaxARPEntries,
        vRtrIPv6RouteThresholdSoakTime
            }
    STATUS        current
    DESCRIPTION
        "The group of objects supporting management of general
         capabilities for transport and virtual routers
         on version 6.0 Alcatel 7x50 SR series systems."
    ::= { tmnxVRtrGroups 38 }

tmnxVRtrNotificationObjV6v0Group OBJECT-GROUP
    OBJECTS {
        vRtrID,
        vRtrIfIndex,
        vRtrDhcpPacketProblem,
        vRtrBfdSlotNumber,
        vRtrNumberOfBfdSessionsOnSlot,
        vRtrBfdMaxSessionReason,
        vRtrDHCP6ServerNetAddrType,
        vRtrDHCP6ServerNetAddr,
        vRtrDHCP6ClientNetAddrType,
        vRtrDHCP6ClientNetAddr,
        vRtrDHCP6AssignedNetAddrType,
        vRtrDHCP6AssignedNetAddr,
        vRtrDHCP6AssignedPrefixLen,
        vRtrDHCP6OldAssignedNetAddrType,
        vRtrDHCP6OldAssignedNetAddr,
        vRtrDHCP6OldAssignedPrefixLen,
        vRtrDHCP6NewClientId,
        vRtrDHCP6OldClientId,
        vRtrDHCP6LeaseOverrideResult,
        vRtrInetStatRteCpeNotifyAddrType,
        vRtrInetStatRteCpeNotifyAddr,
        vRtrInetStaticRouteCpeStatus,
        vRtrManagedRouteInetAddrType,
        vRtrManagedRouteInetAddr,
        vRtrManagedRoutePrefixLen,
        vRtrFailureDescription
            }
    STATUS        current
    DESCRIPTION
        "The group of objects supporting management of notification objects
         on Alcatel 7x50 SR 6.0 series systems."
    ::= { tmnxVRtrGroups 39 }

tmnxVRtrNotificationV6v0Group NOTIFICATION-GROUP
    NOTIFICATIONS {
        tmnxVRtrMidRouteTCA,
        tmnxVRtrHighRouteTCA,
        tmnxVRtrHighRouteCleared,
        tmnxVRtrIllegalLabelTCA,
        tmnxVRtrMcastMidRouteTCA,
        tmnxVRtrMcastMaxRoutesTCA,
        tmnxVRtrMcastMaxRoutesCleared,
        tmnxVRtrMaxArpEntriesTCA,
        tmnxVRtrMaxArpEntriesCleared,
        tmnxVRtrMaxRoutes,
        tmnxVRtrDHCPSuspiciousPcktRcvd,
        tmnxVRtrBfdSessionDown,
        tmnxVRtrBfdMaxSessionOnSlot,
        tmnxVRtrBfdPortTypeNotSupported,
        tmnxVRtrDHCPIfLseStatesExceeded,
        tmnxVRtrDHCP6RelayLseStExceeded,
        tmnxVRtrDHCP6ServerLseStExceeded,
        tmnxVRtrDHCP6LseStateOverride,
        tmnxVRtrDHCP6RelayReplyStripUni,
        tmnxVRtrDHCP6IllegalClientAddr,
        tmnxVRtrDHCP6AssignedIllegSubnet,
        tmnxVRtrDHCP6ClientMacUnresolved,
        tmnxVRtrBfdSessionUp,
        tmnxVRtrIPv6MidRouteTCA,
        tmnxVRtrIPv6HighRouteTCA,
        tmnxVRtrIPv6HighRouteCleared,
        tmnxVRtrStaticRouteCPEStatus,
        tmnxVRtrBfdSessionDeleted,
        tmnxVRtrBfdSessionProtChange,
        tmnxVRtrManagedRouteAddFailed
                  }
    STATUS        current
    DESCRIPTION
        "The group of notifications supporting the transport and
         virtual router capabilities on version 6.0 Alcatel 7xx0 SR series
         systems."
    ::= { tmnxVRtrGroups 40 }

tmnxVRtrBfdV6v0Group    OBJECT-GROUP
    OBJECTS {
                vRtrIfBfdAdminState,
                vRtrIfBfdTransmitInterval,
                vRtrIfBfdReceiveInterval,
                vRtrIfBfdMultiplier,
                vRtrIfBfdSessionOperState,
                vRtrIfBfdSessionState,
                vRtrIfBfdSessionOperFlags,
                vRtrIfBfdSessionMesgRecv,
                vRtrIfBfdSessionMesgSent,
                vRtrIfBfdSessionLastDownTime,
                vRtrIfBfdSessionLastUpTime,
                vRtrIfBfdSessionUpCount,
                vRtrIfBfdSessionDownCount,
                vRtrIfBfdSessionLclDisc,
                vRtrIfBfdSessionRemDisc,
                vRtrIfBfdSessionProtocols,
                vRtrIfBfdSessionTxInterval,
                vRtrIfBfdSessionRxInterval,
                vRtrIfBfdEchoInterval,
                vRtrIfBfdSessionType
            }
     STATUS     current
     DESCRIPTION
         "The group of objects supporting Bi-directional Forwarding
          Detection on version 6.0 Alcatel 7xxx series systems."
     ::= { tmnxVRtrGroups 41 }

END
