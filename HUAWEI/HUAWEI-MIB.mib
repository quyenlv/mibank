-- ============================================================================
-- Copyright (C) by  HUAWEI TECHNOLOGIES. All rights reserved.
--
-- Description:
-- Reference:
-- Version: V3.03
-- History:
-- updated By liu chenglong on Mar 20,2004 .
--
-- ============================================================================

HUAWEI-MIB DEFINITIONS ::= BEGIN

        IMPORTS
                enterprises
                        FROM SNMPv2-SMI;

         huawei OBJECT IDENTIFIER ::= { enterprises 2011 }

        hwLocal OBJECT IDENTIFIER               ::= { huawei 1 }
            quidway OBJECT IDENTIFIER              ::= { hwLocal 1 }
            hwTrans OBJECT IDENTIFIER              ::= { hwLocal 2 }
            hwInternetProtocol OBJECT IDENTIFIER   ::= { hwLocal 3 }
            hwNovellProtocol OBJECT IDENTIFIER     ::= { hwLocal 4 }
            
        hwProducts OBJECT IDENTIFIER            ::= { huawei 2 }

        atm                     OBJECT IDENTIFIER ::= { hwProducts 1 }
            atmAccess           OBJECT IDENTIFIER ::= { atm 1 }
            atmBone             OBJECT IDENTIFIER ::= { atm 2 }
            r8750               OBJECT IDENTIFIER ::= { atmBone 1 }

        router                  OBJECT IDENTIFIER ::= { hwProducts 2 }
            routerGeneral       OBJECT IDENTIFIER ::= { router 1 }
                ne08            OBJECT IDENTIFIER ::= { routerGeneral 7508 }
                ne16            OBJECT IDENTIFIER ::= { routerGeneral 7516 }
                attr            OBJECT IDENTIFIER ::= { routerGeneral 1 }

            module              OBJECT IDENTIFIER ::= { router 2 }
            flash               OBJECT IDENTIFIER ::= { router 3 }
            mixinfo             OBJECT IDENTIFIER ::= { router 4 }
            huaweiMemoryPool    OBJECT IDENTIFIER ::= { router 5 }
            configFile          OBJECT IDENTIFIER ::= { router 6 }
            netEngine           OBJECT IDENTIFIER ::= { router 8070 }

        access-server           OBJECT IDENTIFIER ::= { hwProducts 3 }
            as8010              OBJECT IDENTIFIER ::= { access-server 1 }

        lan-switch              OBJECT IDENTIFIER ::= { hwProducts 4 }
            switch2403          OBJECT IDENTIFIER ::= { lan-switch 1 }
                switch2403F     OBJECT IDENTIFIER ::= { switch2403 0 }
            switch3008          OBJECT IDENTIFIER ::= { lan-switch 2 }
            switch3016          OBJECT IDENTIFIER ::= { lan-switch 3 }
            switch2024-M        OBJECT IDENTIFIER ::= { lan-switch 4 }
            switch3025-M        OBJECT IDENTIFIER ::= { lan-switch 5 }

        xdsl                    OBJECT IDENTIFIER ::= { hwProducts 5 }
            adsl                OBJECT IDENTIFIER ::= { xdsl 1 }

        musa                    OBJECT IDENTIFIER ::= { hwProducts 6 }
            hwMusaV100R001Mib   OBJECT IDENTIFIER ::= { musa 1 }
            hwMA5200Mib         OBJECT IDENTIFIER ::= { musa 2 }
            hwMusaV100R002Mib   OBJECT IDENTIFIER ::= { musa 3 }
            hwMd5500Mib         OBJECT IDENTIFIER ::= { musa 4 }
            hwMa5100Mib         OBJECT IDENTIFIER ::= { musa 5 }
            hwMa5300Mib         OBJECT IDENTIFIER ::= { musa 6 }
            ias                 OBJECT IDENTIFIER ::= { musa 7 }

        mpeg-2                  OBJECT IDENTIFIER ::= { hwProducts 7 }
        gprs                    OBJECT IDENTIFIER ::= { hwProducts 8 }
        honet                   OBJECT IDENTIFIER ::= { hwProducts 9 }
        cc08                    OBJECT IDENTIFIER ::= { hwProducts 10 }
        sbs                     OBJECT IDENTIFIER ::= { hwProducts 11 }
        ip-phone                OBJECT IDENTIFIER ::= { hwProducts 12 }
        ups                     OBJECT IDENTIFIER ::= { hwProducts 13 }
        viewpoint               OBJECT IDENTIFIER ::= { hwProducts 14 }
        netManager              OBJECT IDENTIFIER ::= { hwProducts 15 }
        iNet                    OBJECT IDENTIFIER ::= { hwProducts 16 }
        ne80                    OBJECT IDENTIFIER ::= { hwProducts 17 }
        wireIn                  OBJECT IDENTIFIER ::= { hwProducts 18 }
            wireInScp           OBJECT IDENTIFIER ::= { wireIn 1 }
            wireInSdp           OBJECT IDENTIFIER ::= { wireIn 2 }
            wireInSmp           OBJECT IDENTIFIER ::= { wireIn 3 }
            wireInSsp           OBJECT IDENTIFIER ::= { wireIn 4 }
            wireInIP            OBJECT IDENTIFIER ::= { wireIn 5 }

        mobileIn                OBJECT IDENTIFIER ::= { hwProducts 19 }
            mobileInScp         OBJECT IDENTIFIER ::= { mobileIn 1 }
            mobileInSdp         OBJECT IDENTIFIER ::= { mobileIn 2 }
            mobileInSmp         OBJECT IDENTIFIER ::= { mobileIn 3 }
            mobileInSsp         OBJECT IDENTIFIER ::= { mobileIn 4 }
            mobileInIP          OBJECT IDENTIFIER ::= { mobileIn 5 }

        cdmaIn                  OBJECT IDENTIFIER ::= { hwProducts 20 }
            cdmaInScp           OBJECT IDENTIFIER ::= { cdmaIn 1 }
            cdmaInSdp           OBJECT IDENTIFIER ::= { cdmaIn 2 }
            cdmaInSmp           OBJECT IDENTIFIER ::= { cdmaIn 3 }
            cdmaInSsp           OBJECT IDENTIFIER ::= { cdmaIn 4 }
            cdmaInIP            OBJECT IDENTIFIER ::= { cdmaIn 5 }
        acdIn                   OBJECT IDENTIFIER ::= { hwProducts 21 }
        esr                     OBJECT IDENTIFIER ::= { hwProducts 22 }
            radium8750          OBJECT IDENTIFIER ::= { esr 2 }
            isn8850             OBJECT IDENTIFIER ::= { esr 3 }
            esr8825             OBJECT IDENTIFIER ::= { esr 5 }
            esrV5R3             OBJECT IDENTIFIER ::= { esr 6 }
            esrV5R58850         OBJECT IDENTIFIER ::= { esr 7 }
            esrV5R58825         OBJECT IDENTIFIER ::= { esr 8 }
        lanSw                   OBJECT IDENTIFIER ::= { hwProducts 23 }
            lswCommon           OBJECT IDENTIFIER ::= { lanSw 1 }
            s8016               OBJECT IDENTIFIER ::= { lanSw 11 }
                s8016Common     OBJECT IDENTIFIER ::= { s8016 1 }
                s8016A          OBJECT IDENTIFIER ::= { s8016 2 }
                s8016B          OBJECT IDENTIFIER ::= { s8016 3 }
            s3526               OBJECT IDENTIFIER ::= { lanSw 12 }
            s3026               OBJECT IDENTIFIER ::= { lanSw 13 }
            s3026V              OBJECT IDENTIFIER ::= { lanSw 14 }
            s2008               OBJECT IDENTIFIER ::= { lanSw 15 }
            s2016               OBJECT IDENTIFIER ::= { lanSw 16 }
            s3526F              OBJECT IDENTIFIER ::= { lanSw 17 }
            s5516               OBJECT IDENTIFIER ::= { lanSw 18 }
            s6506               OBJECT IDENTIFIER ::= { lanSw 19 }
            s3026F              OBJECT IDENTIFIER ::= { lanSw 20 }
            s3526E              OBJECT IDENTIFIER ::= { lanSw 21 }
            s2026               OBJECT IDENTIFIER ::= { lanSw 22 }
            s2403H              OBJECT IDENTIFIER ::= { lanSw 23 }
            s3026E              OBJECT IDENTIFIER ::= { lanSw 24 }
            s3026EFM           OBJECT IDENTIFIER ::= { lanSw 25 }
            s3026EFS           OBJECT IDENTIFIER ::= { lanSw 26 }
            s3526EFM           OBJECT IDENTIFIER ::= { lanSw 27 }
            s3526EFS           OBJECT IDENTIFIER ::= { lanSw 28 }
            s3050C              OBJECT IDENTIFIER ::= { lanSw 29 }
            s6503               OBJECT IDENTIFIER ::= { lanSw 30 }
            s8512               OBJECT IDENTIFIER ::= { lanSw 31 }
            s8505               OBJECT IDENTIFIER ::= { lanSw 32 }
            s6506R              OBJECT IDENTIFIER ::= { lanSw 33 }
            s3026c              OBJECT IDENTIFIER ::= { lanSw 34 }
            s3026g              OBJECT IDENTIFIER ::= { lanSw 35 }
            s3026t              OBJECT IDENTIFIER ::= { lanSw 36 }
            s3552G              OBJECT IDENTIFIER ::= { lanSw 37 }
            s3552P              OBJECT IDENTIFIER ::= { lanSw 38 }
            s3528G              OBJECT IDENTIFIER ::= { lanSw 39 }
            s3528P              OBJECT IDENTIFIER ::= { lanSw 40 }
            s3526c              OBJECT IDENTIFIER ::= { lanSw 41 }
            s3026c-24-12fs      OBJECT IDENTIFIER ::= { lanSw 42 }
            s3026c-24-12fm      OBJECT IDENTIFIER ::= { lanSw 43 }
            s3526c-24-12fs      OBJECT IDENTIFIER ::= { lanSw 44 }
            s3526c-24-12fm      OBJECT IDENTIFIER ::= { lanSw 45 }
            s5012G              OBJECT IDENTIFIER ::= { lanSw 46 }
            s5012G-DC           OBJECT IDENTIFIER ::= { lanSw 47 }
            s5012T-12-10GBC     OBJECT IDENTIFIER ::= { lanSw 48 }
            s5012T-12-10GBC-DC  OBJECT IDENTIFIER ::= { lanSw 49 }
            s5024G-24-20TP      OBJECT IDENTIFIER ::= { lanSw 50 }
            s5024G-24-20TP-DC   OBJECT IDENTIFIER ::= { lanSw 51 }
            s2026Z              OBJECT IDENTIFIER ::= { lanSw 52 }
            s2026C              OBJECT IDENTIFIER ::= { lanSw 53 }
            s3026G-SI           OBJECT IDENTIFIER ::= { lanSw 54 }
            s3026C-SI           OBJECT IDENTIFIER ::= { lanSw 55 }
            s3026S-SI           OBJECT IDENTIFIER ::= { lanSw 56 }

        apon                    OBJECT IDENTIFIER ::= { hwProducts 24 }
            ma5101              OBJECT IDENTIFIER ::= { apon 1 }
            ma5102              OBJECT IDENTIFIER ::= { apon 2 }

        transmission            OBJECT IDENTIFIER ::= { hwProducts 25 }
            optix155622H        OBJECT IDENTIFIER ::= { transmission 1 }
            optix10Gv2          OBJECT IDENTIFIER ::= { transmission 2 }

        hsr                     OBJECT IDENTIFIER ::= { hwProducts 26 }
            ne16E               OBJECT IDENTIFIER ::= { hsr 1 }
            ne08E               OBJECT IDENTIFIER ::= { hsr 2 }
            ne05                OBJECT IDENTIFIER ::= { hsr 3 }

        amg5000                 OBJECT IDENTIFIER ::= { hwProducts 27 }
        umg8900                 OBJECT IDENTIFIER ::= { hwProducts 28 }
        ne40-4                  OBJECT IDENTIFIER ::= { hwProducts 29 }
        ne40-2                  OBJECT IDENTIFIER ::= { hwProducts 30 }
        ne40-8                  OBJECT IDENTIFIER ::= { hwProducts 31 }
        
        wcdma                   OBJECT IDENTIFIER ::= { hwProducts 32 }
            sgsn                OBJECT IDENTIFIER ::= { wcdma 1 }

        mlsr                    OBJECT IDENTIFIER ::= { hwProducts 33 }
        
        dslw                    OBJECT IDENTIFIER ::= { hwProducts 34 }
            dlswNode            OBJECT IDENTIFIER ::= { dslw 1 }
            dlswTConn           OBJECT IDENTIFIER ::= { dslw 2 }
            dlswInterface       OBJECT IDENTIFIER ::= { dslw 3 }
            dlswDirectory       OBJECT IDENTIFIER ::= { dslw 4 }
            dlswCircuit         OBJECT IDENTIFIER ::= { dslw 5 }
            dlswSdlc            OBJECT IDENTIFIER ::= { dslw 6 }
            dlswLlc2            OBJECT IDENTIFIER ::= { dslw 7 }

        sm                      OBJECT IDENTIFIER ::= { hwProducts 35 }
            mmsc                OBJECT IDENTIFIER ::= { sm 1 }

        as                      OBJECT IDENTIFIER ::= { hwProducts 36 }
        p3                      OBJECT IDENTIFIER ::= { hwProducts 37 }
        
        iad                     OBJECT IDENTIFIER ::= { hwProducts 38 }
            iad132              OBJECT IDENTIFIER ::= { iad 1 }

        wlanAp                  OBJECT IDENTIFIER ::= { hwProducts 39 }
            wlanApCommon        OBJECT IDENTIFIER ::= { wlanAp 1 }
            wlanApWA1003        OBJECT IDENTIFIER ::= { wlanAp 2 }
            wlanApWA1003A       OBJECT IDENTIFIER ::= { wlanAp 3 }
            wlanApWA1005        OBJECT IDENTIFIER ::= { wlanAp 4 }
            wlanApWA1008        OBJECT IDENTIFIER ::= { wlanAp 5 }
            wlanApWA1208        OBJECT IDENTIFIER ::= { wlanAp 6 }
            wlanApWA1208H       OBJECT IDENTIFIER ::= { wlanAp 7 }
            wlanApWA1006E       OBJECT IDENTIFIER ::= { wlanAp 8 }
            wlanBridgeWB2010    OBJECT IDENTIFIER ::= { wlanAp 9 }
            wlanBridgeWB2011    OBJECT IDENTIFIER ::= { wlanAp 10}
            wA1208E             OBJECT IDENTIFIER ::= { wlanAp 11}

        hwinfoX                 OBJECT IDENTIFIER ::= { hwProducts 40 }
        wlanApWA1006            OBJECT IDENTIFIER ::= { hwProducts 43 }
        aR46-20                 OBJECT IDENTIFIER ::= { hwProducts 44 }
        aR46-40                 OBJECT IDENTIFIER ::= { hwProducts 45 }
        aR46-80                 OBJECT IDENTIFIER ::= { hwProducts 46 }
        nE20-2                  OBJECT IDENTIFIER ::= { hwProducts 47 }
        nE20-4                  OBJECT IDENTIFIER ::= { hwProducts 48 }
        nE20-8                  OBJECT IDENTIFIER ::= { hwProducts 49 }
        eUDEMON200              OBJECT IDENTIFIER ::= { hwProducts 50 }
        eUDEMON1000             OBJECT IDENTIFIER ::= { hwProducts 51 }
        vDG10-40                OBJECT IDENTIFIER ::= { hwProducts 52 }
        vDG10-41                OBJECT IDENTIFIER ::= { hwProducts 53 }
        hwSps                   OBJECT IDENTIFIER ::= { hwProducts 54 }
        aR18-18                 OBJECT IDENTIFIER ::= { hwProducts 55 }
        aR18-20                 OBJECT IDENTIFIER ::= { hwProducts 56 }
        aR18-30                 OBJECT IDENTIFIER ::= { hwProducts 57 }
        aR18-31                 OBJECT IDENTIFIER ::= { hwProducts 58 }
        aR18-32                 OBJECT IDENTIFIER ::= { hwProducts 59 }
        aR18-33                 OBJECT IDENTIFIER ::= { hwProducts 60 }
        aR18-34                 OBJECT IDENTIFIER ::= { hwProducts 61 }


        nE5000                  OBJECT IDENTIFIER ::= { hwProducts 62 }
            nE5000SysOid        OBJECT IDENTIFIER ::= { nE5000 2 }
                nE5000oem       OBJECT IDENTIFIER ::= { nE5000SysOid 1 }
                nE80E           OBJECT IDENTIFIER ::= { nE5000SysOid 2 }
                nE5000E         OBJECT IDENTIFIER ::= { nE5000SysOid 3 }
                nE5000EMulti    OBJECT IDENTIFIER ::= { nE5000SysOid 4 }
                nE40E           OBJECT IDENTIFIER ::= { nE5000SysOid 5 }

        gGSN9811                OBJECT IDENTIFIER ::= { hwProducts 63 }
        pDSN9660                OBJECT IDENTIFIER ::= { hwProducts 64 }
        eUDEMON2100             OBJECT IDENTIFIER ::= { hwProducts 65 }
        eUDEMON2200             OBJECT IDENTIFIER ::= { hwProducts 66 }
        s3552F-SI               OBJECT IDENTIFIER ::= { hwProducts 67 }
        s3552F-EI               OBJECT IDENTIFIER ::= { hwProducts 68 }
        e026                    OBJECT IDENTIFIER ::= { hwProducts 69 }
        e026-SI                 OBJECT IDENTIFIER ::= { hwProducts 70 }
        e050                    OBJECT IDENTIFIER ::= { hwProducts 71 }
        ua5000ipm               OBJECT IDENTIFIER ::= { hwProducts 72 }
        rm9000                  OBJECT IDENTIFIER ::= { hwProducts 73 }
        hwIMAPNorthbound        OBJECT IDENTIFIER ::= { hwProducts 74 }
        hwBITS                  OBJECT IDENTIFIER ::= { hwProducts 75 }
        hwPv8                   OBJECT IDENTIFIER ::= { hwProducts 76 }
        eudemon500              OBJECT IDENTIFIER ::= { hwProducts 77 }
        ua5000IpmB              OBJECT IDENTIFIER ::= { hwProducts 78 }
        ua5000ApmB              OBJECT IDENTIFIER ::= { hwProducts 79 }
        ma5600                  OBJECT IDENTIFIER ::= { hwProducts 80 }
        softx3000UC             OBJECT IDENTIFIER ::= { hwProducts 81 }
        hwOSTA                  OBJECT IDENTIFIER ::= { hwProducts 82 }
        sECPATH1800F            OBJECT IDENTIFIER ::= { hwProducts 83 }
        eudemon2300             OBJECT IDENTIFIER ::= { hwProducts 84 }
        mA5100V600              OBJECT IDENTIFIER ::= { hwProducts 85 }
        mA5605                  OBJECT IDENTIFIER ::= { hwProducts 86 }
        
        carrierSwitch           OBJECT IDENTIFIER ::= { hwProducts 87 }
            cX200A              OBJECT IDENTIFIER ::= { carrierSwitch 1 }
            cX200B              OBJECT IDENTIFIER ::= { carrierSwitch 2 }
            cX300A              OBJECT IDENTIFIER ::= { carrierSwitch 3 }
            cX300B              OBJECT IDENTIFIER ::= { carrierSwitch 4 }
            cX500A              OBJECT IDENTIFIER ::= { carrierSwitch 5 }

        nE20E                   OBJECT IDENTIFIER ::= { hwProducts 88 }
            nE20E-4             OBJECT IDENTIFIER ::= { nE20E 1 }
            nE20E-8             OBJECT IDENTIFIER ::= { nE20E 2 }

        mE60             OBJECT IDENTIFIER ::= { hwProducts 89}



        huaweiExperimental OBJECT IDENTIFIER    ::= { huawei 4 }
        huaweiMgmt OBJECT IDENTIFIER            ::= { huawei 5 }
            hwAcl OBJECT IDENTIFIER             ::= { huaweiMgmt 1 }
            hwAaa OBJECT IDENTIFIER             ::= { huaweiMgmt 2 }
            hwLam OBJECT IDENTIFIER             ::= { huaweiMgmt 3 }
            hwPortal OBJECT IDENTIFIER          ::= { huaweiMgmt 4 }
            hwRadius OBJECT IDENTIFIER          ::= { huaweiMgmt 5 }
            hwVlan OBJECT IDENTIFIER            ::= { huaweiMgmt 6 }
            
            hwDhcp OBJECT IDENTIFIER            ::= { huaweiMgmt 7 }
                hwDHCPRelayMib OBJECT IDENTIFIER    ::= { hwDhcp 1 }
                hwDHCPServerMib OBJECT IDENTIFIER   ::= { hwDhcp 2 }

            hwVprn OBJECT IDENTIFIER            ::= { huaweiMgmt 8 }
            hwFr OBJECT IDENTIFIER              ::= { huaweiMgmt 9 }
            hwAtmCmRm OBJECT IDENTIFIER         ::= { huaweiMgmt 10 }
            hwCes OBJECT IDENTIFIER             ::= { huaweiMgmt 11 }
            
            hwMpls OBJECT IDENTIFIER            ::= { huaweiMgmt 12 }
                hwMplsLsr OBJECT IDENTIFIER     ::= { hwMpls 1 }
                hwMplsLdp OBJECT IDENTIFIER     ::= { hwMpls 2 }
                hwMplsVpn OBJECT IDENTIFIER     ::= { hwMpls 3 }
                hwMplsFtn OBJECT IDENTIFIER     ::= { hwMpls 4 }
                hwMplsVpls OBJECT IDENTIFIER    ::= { hwMpls 5 }
                hwMplsLsp  OBJECT IDENTIFIER    ::= { hwMpls 6 }
                hwMplsOam  OBJECT IDENTIFIER    ::= { hwMpls 7 }

            hwRouteManagement OBJECT IDENTIFIER ::= { huaweiMgmt 13 }
                hwRouteManagementUrm OBJECT IDENTIFIER  ::= { hwRouteManagement 1 }
                hwRouteManagementMrm OBJECT IDENTIFIER  ::= { hwRouteManagement 2 }
                hwRouteManagementRpm OBJECT IDENTIFIER  ::= { hwRouteManagement 3 }

            hwEthernetPort OBJECT IDENTIFIER    ::= { huaweiMgmt 14 }
            hwVTP OBJECT IDENTIFIER             ::= { huaweiMgmt 15 }
            hwMam OBJECT IDENTIFIER             ::= { huaweiMgmt 16 }
            hwArpProxy OBJECT IDENTIFIER        ::= { huaweiMgmt 17 }
            hwDhcpProxy OBJECT IDENTIFIER       ::= { huaweiMgmt 18 }
            hwIgspSnooping OBJECT IDENTIFIER    ::= { huaweiMgmt 19 }
            hwGarpExt OBJECT IDENTIFIER         ::= { huaweiMgmt 20 }
            hwRstpExt OBJECT IDENTIFIER         ::= { huaweiMgmt 21 }
            hwPae8021xExt OBJECT IDENTIFIER     ::= { huaweiMgmt 22 }
            hwNat OBJECT IDENTIFIER             ::= { huaweiMgmt 23 }
            hwVlanProtocol OBJECT IDENTIFIER    ::= { huaweiMgmt 24 }
            hwDatacomm OBJECT IDENTIFIER        ::= { huaweiMgmt 25 }
            hwImps     OBJECT IDENTIFIER        ::= { huaweiMgmt 26 }

        huaweiUtility OBJECT IDENTIFIER         ::= { huawei 6 }
            hwEnvironment OBJECT IDENTIFIER     ::= { huaweiUtility 1 }
            hwPower OBJECT IDENTIFIER           ::= { huaweiUtility 2 }
            hwDev OBJECT IDENTIFIER             ::= { huaweiUtility 3 }
            hwNtp OBJECT IDENTIFIER             ::= { huaweiUtility 4 }
            hwMem OBJECT IDENTIFIER             ::= { huaweiUtility 5 }
            hwLoadBackup OBJECT IDENTIFIER      ::= { huaweiUtility 6 }
            hwHgmp OBJECT IDENTIFIER            ::= { huaweiUtility 7 }
            hwIppool OBJECT IDENTIFIER          ::= { huaweiUtility 8 }
            huaweiFlashManMIB OBJECT IDENTIFIER ::= { huaweiUtility 9 }
            hwConfig OBJECT IDENTIFIER          ::= { huaweiUtility 10 }
            hwAtmOam OBJECT IDENTIFIER          ::= { huaweiUtility 11 }
            hwAtmPos OBJECT IDENTIFIER          ::= { huaweiUtility 12 }
            hwHSL OBJECT IDENTIFIER             ::= { huaweiUtility 13 }
            hwMTA OBJECT IDENTIFIER             ::= { huaweiUtility 14 }
            hwSPC OBJECT IDENTIFIER             ::= { huaweiUtility 15 }
            hwV5 OBJECT IDENTIFIER              ::= { huaweiUtility 16 }
            hwIma OBJECT IDENTIFIER             ::= { huaweiUtility 17 }
            hwUcl OBJECT IDENTIFIER             ::= { huaweiUtility 18 }
            hwAtmSvc OBJECT IDENTIFIER          ::= { huaweiUtility 19 }
            hwVPRing OBJECT IDENTIFIER          ::= { huaweiUtility 20 }
            
            hwTest OBJECT IDENTIFIER            ::= { huaweiUtility 21 }
                hwTestCommon OBJECT IDENTIFIER  ::= { hwTest 1 }
                hwNTest OBJECT IDENTIFIER       ::= { hwTest 2 }
                hwBtest OBJECT IDENTIFIER       ::= { hwTest 3 }

            hwSwitchOver OBJECT IDENTIFIER      ::= { huaweiUtility 22 }
            hwVfb OBJECT IDENTIFIER             ::= { huaweiUtility 23 }
            hwClk OBJECT IDENTIFIER             ::= { huaweiUtility 25 }
            hwCdi OBJECT IDENTIFIER             ::= { huaweiUtility 26 }
            hwAti OBJECT IDENTIFIER             ::= { huaweiUtility 27 }
            hwDslamNtv OBJECT IDENTIFIER        ::= { huaweiUtility 28 }
            hwServerMon OBJECT IDENTIFIER       ::= { huaweiUtility 29 }
            hwSyntrap OBJECT IDENTIFIER         ::= { huaweiUtility 30}
            hwAdsl OBJECT IDENTIFIER            ::= { huaweiUtility 31 }
            hwVdsl OBJECT IDENTIFIER            ::= { huaweiUtility 32 }
            hwHdsl OBJECT IDENTIFIER            ::= { huaweiUtility 33 }
            hwDeha OBJECT IDENTIFIER            ::= { huaweiUtility 34 }
            hwSyslog OBJECT IDENTIFIER          ::= { huaweiUtility 35 }
            hwVoip OBJECT IDENTIFIER            ::= { huaweiUtility 36 }
            hwVrp OBJECT IDENTIFIER             ::= { huaweiUtility 37 }
            hwMus OBJECT IDENTIFIER             ::= { huaweiUtility 38 }
            hwDns OBJECT IDENTIFIER             ::= { huaweiUtility 39 }
            hwNetTest OBJECT IDENTIFIER         ::= { huaweiUtility 40 }
            hwMs OBJECT IDENTIFIER              ::= { huaweiUtility 41 }
            hwPITP OBJECT IDENTIFIER            ::= { huaweiUtility 42 }
            hwDslamMacPool OBJECT IDENTIFIER    ::= { huaweiUtility 43 }
            hwDslamPPPoA OBJECT IDENTIFIER      ::= { huaweiUtility 44 }
            hwDslamPvcProtocol OBJECT IDENTIFIER    ::= { huaweiUtility 45 }
            hwDslamIpoa OBJECT IDENTIFIER       ::= { huaweiUtility 46 }
END
