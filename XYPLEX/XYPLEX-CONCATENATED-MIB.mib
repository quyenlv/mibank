-- A concatinated XYPLEX MIB
-- It contains the following MIBs:

--   A copy of MIB-II from RFC-1213 with the EGP group removed.

--   Converted Xyplex Systems MIB
--     the 18 February 1992 version, Xyplex Document Number 420-0545-B

--   Converted Xyplex Bootstrap Clients MIB
--     the 22 May 1991 version, Xyplex Document Number 420-0537-A

--   Converted Xyplex Bootstrap Servers MIB
--     the 11 March 1992 version, Xyplex Document Number 420-0538-B

--   Converted Xyplex Character Stream Devices MIB
--     the 18 October 1991 version, Xyplex Document Number 420-0539-A

--   Converted Xyplex Decnet MIB
--     the 22 May 1991 version, Xyplex Document Number 420-0546-A

--   Converted Xyplex Ethernet Interfaces MIB
--     the 23 May 1991 version, Xyplex Document Number 420-0547-A

--   Converted Xyplex Internet Systems MIB
--     the 26 February 1992 version, Xyplex Document Number 420-0542-B
--     NOTE: The following objects that are not implemented
--           by the terminal server were removed from the MIB:
--           all under xEgp, all under ospf, all under routerIp,
--           all under routerUdp, and all under routerPolicy.

--   Converted Xyplex LAT MIB
--     the 18 October 1991 version, Xyplex Document Number 420-0543-A

--   Converted Xyplex Parameter Clients MIB
--     the 14 February 1992 version, Xyplex Document Number 420-0544-A

--   Converted IETF Internet Draft CHARACTER MIB
--     the 21 Oct 91 version 

--   Converted IETF Internet Draft RS-232-LIKE MIB
--     the 19 Mar 91 version


   XYPLEX-CONCATENATED-MIB DEFINITIONS ::= BEGIN
         IMPORTS
               enterprises, Counter, Gauge, TimeTicks,
               IpAddress, experimental, NetworkAddress,
               mgmt
                  FROM RFC1155-SMI
               OBJECT-TYPE
                  FROM RFC-1212
               TRAP-TYPE
                  FROM RFC-1215;

-- MIB-II from RFC 1213 with the EGP Group removed

          --  MIB-II (same prefix as MIB-I)

          mib-2      OBJECT IDENTIFIER ::= { mgmt 1 }

          -- textual conventions

          DisplayString ::=
              OCTET STRING
          -- This data type is used to model textual information taken
          -- from the NVT ASCII character set.  By convention, objects
          -- with this syntax are declared as having
          --
          --      SIZE (0..255)

          PhysAddress ::=
              OCTET STRING
          -- This data type is used to model media addresses.  For many
          -- types of media, this will be in a binary representation.
          -- For example, an ethernet address would be represented as
          -- a string of 6 octets.


          -- groups in MIB-II

          system       OBJECT IDENTIFIER ::= { mib-2 1 }

          interfaces   OBJECT IDENTIFIER ::= { mib-2 2 }

          at           OBJECT IDENTIFIER ::= { mib-2 3 }

          ip           OBJECT IDENTIFIER ::= { mib-2 4 }

          icmp         OBJECT IDENTIFIER ::= { mib-2 5 }

          tcp          OBJECT IDENTIFIER ::= { mib-2 6 }

          udp          OBJECT IDENTIFIER ::= { mib-2 7 }

          egp          OBJECT IDENTIFIER ::= { mib-2 8 }

          -- historical
          -- cmot      OBJECT IDENTIFIER ::= { mib-2 9 }

          transmission OBJECT IDENTIFIER ::= { mib-2 10 }

          snmp         OBJECT IDENTIFIER ::= { mib-2 11 }


          -- the System group

          -- Implementation of the System group is mandatory for all
          -- systems.  If an agent is not configured to have a value
          -- for any of these variables, a string of length 0 is
          -- returned.

          sysDescr OBJECT-TYPE
              SYNTAX  DisplayString (SIZE (0..255))
              ACCESS  read-only
              STATUS  mandatory
              DESCRIPTION
                      "A textual description of the entity.  This value
                      should include the full name and version
                      identification of the system's hardware type,
                      software operating-system, and networking
                      software.  It is mandatory that this only contain
                      printable ASCII characters."
              ::= { system 1 }

          sysObjectID OBJECT-TYPE
              SYNTAX  OBJECT IDENTIFIER
              ACCESS  read-only
              STATUS  mandatory
              DESCRIPTION
                      "The vendor's authoritative identification of the
                      network management subsystem contained in the
                      entity.  This value is allocated within the SMI
                      enterprises subtree (1.3.6.1.4.1) and provides an
                      easy and unambiguous means for determining `what
                      kind of box' is being managed.  For example, if
                      vendor `Flintstones, Inc.' was assigned the
                      subtree 1.3.6.1.4.1.4242, it could assign the
                      identifier 1.3.6.1.4.1.4242.1.1 to its `Fred
                      Router'."
              ::= { system 2 }

          sysUpTime OBJECT-TYPE
              SYNTAX  TimeTicks
              ACCESS  read-only
              STATUS  mandatory
              DESCRIPTION
                      "The time (in hundredths of a second) since the
                      network management portion of the system was last
                      re-initialized."
              ::= { system 3 }

          sysContact OBJECT-TYPE
              SYNTAX  DisplayString (SIZE (0..255))
              ACCESS  read-write
              STATUS  mandatory
              DESCRIPTION
                      "The textual identification of the contact person
                      for this managed node, together with information
                      on how to contact this person."
              ::= { system 4 }

          sysName OBJECT-TYPE
              SYNTAX  DisplayString (SIZE (0..255))
              ACCESS  read-write
              STATUS  mandatory
              DESCRIPTION
                      "An administratively-assigned name for this
                      managed node.  By convention, this is the node's
                      fully-qualified domain name."
              ::= { system 5 }

          sysLocation OBJECT-TYPE
              SYNTAX  DisplayString (SIZE (0..255))
              ACCESS  read-write
              STATUS  mandatory
              DESCRIPTION
                      "The physical location of this node (e.g.,
                      `telephone closet, 3rd floor')."
              ::= { system 6 }

          sysServices OBJECT-TYPE
              SYNTAX  INTEGER (0..127)
              ACCESS  read-only
              STATUS  mandatory
              DESCRIPTION
                      "A value which indicates the set of services that
                      this entity primarily offers.

                      The value is a sum.  This sum initially takes the
                      value zero, Then, for each layer, L, in the range
                      1 through 7, that this node performs transactions
                      for, 2 raised to (L - 1) is added to the sum.  For
                      example, a node which performs primarily routing
                      functions would have a value of 4 (2^(3-1)).  In
                      contrast, a node which is a host offering
                      application services would have a value of 72
                      (2^(4-1) + 2^(7-1)).  Note that in the context of
                      the Internet suite of protocols, values should be
                      calculated accordingly:

                           layer  functionality
                               1  physical (e.g., repeaters)
                               2  datalink/subnetwork (e.g., bridges)
                               3  internet (e.g., IP gateways)
                               4  end-to-end  (e.g., IP hosts)
                               7  applications (e.g., mail relays)

                      For systems including OSI protocols, layers 5 and
                      6 may also be counted."
              ::= { system 7 }

          -- the Interfaces group

          -- Implementation of the Interfaces group is mandatory for
          -- all systems.

          ifNumber OBJECT-TYPE
              SYNTAX  INTEGER
              ACCESS  read-only
              STATUS  mandatory
              DESCRIPTION
                      "The number of network interfaces (regardless of
                      their current state) present on this system."
              ::= { interfaces 1 }


          -- the Interfaces table

          -- The Interfaces table contains information on the entity's
          -- interfaces.  Each interface is thought of as being
          -- attached to a `subnetwork'.  Note that this term should
          -- not be confused with `subnet' which refers to an
          -- addressing partitioning scheme used in the Internet suite
          -- of protocols.

          ifTable OBJECT-TYPE
              SYNTAX  SEQUENCE OF IfEntry
              ACCESS  not-accessible
              STATUS  mandatory
              DESCRIPTION
                      "A list of interface entries.  The number of
                      entries is given by the value of ifNumber."
              ::= { interfaces 2 }

          ifEntry OBJECT-TYPE
              SYNTAX  IfEntry
              ACCESS  not-accessible
              STATUS  mandatory
              DESCRIPTION
                      "An interface entry containing objects at the
                      subnetwork layer and below for a particular
                      interface."
              INDEX   { ifIndex }
              ::= { ifTable 1 }

          IfEntry ::=
              SEQUENCE {
                  ifIndex
                      INTEGER,
                  ifDescr
                      DisplayString,
                  ifType
                      INTEGER,
                  ifMtu
                      INTEGER,
                  ifSpeed
                      Gauge,
                  ifPhysAddress
                      PhysAddress,
                  ifAdminStatus
                      INTEGER,
                  ifOperStatus
                      INTEGER,
                  ifLastChange
                      TimeTicks,
                  ifInOctets
                      Counter,
                  ifInUcastPkts
                      Counter,
                  ifInNUcastPkts
                      Counter,
                  ifInDiscards
                      Counter,
                  ifInErrors
                      Counter,
                  ifInUnknownProtos
                      Counter,
                  ifOutOctets
                      Counter,
                  ifOutUcastPkts
                      Counter,
                  ifOutNUcastPkts
                      Counter,
                  ifOutDiscards
                      Counter,
                  ifOutErrors
                      Counter,
                  ifOutQLen
                      Gauge,
                  ifSpecific
                      OBJECT IDENTIFIER
              }

          ifIndex OBJECT-TYPE
              SYNTAX  INTEGER
              ACCESS  read-only
              STATUS  mandatory
              DESCRIPTION
                      "A unique value for each interface.  Its value
                      ranges between 1 and the value of ifNumber.  The
                      value for each interface must remain constant at
                      least from one re-initialization of the entity's
                      network management system to the next re-
                      initialization."
              ::= { ifEntry 1 }

          ifDescr OBJECT-TYPE
              SYNTAX  DisplayString (SIZE (0..255))
              ACCESS  read-only
              STATUS  mandatory
              DESCRIPTION
                      "A textual string containing information about the
                      interface.  This string should include the name of
                      the manufacturer, the product name and the version
                      of the hardware interface."
              ::= { ifEntry 2 }

          ifType OBJECT-TYPE
              SYNTAX  INTEGER {
                          other(1),          -- none of the following
                          regular1822(2),
                          hdh1822(3),
                          ddn-x25(4),
                          rfc877-x25(5),
                          ethernet-csmacd(6),
                          iso88023-csmacd(7),
                          iso88024-tokenBus(8),
                          iso88025-tokenRing(9),
                          iso88026-man(10),
                          starLan(11),
                          proteon-10Mbit(12),
                          proteon-80Mbit(13),
                          hyperchannel(14),
                          fddi(15),
                          lapb(16),
                          sdlc(17),
                          ds1(18),           -- T-1
                          e1(19),            -- european equiv. of T-1
                          basicISDN(20),
                          primaryISDN(21),   -- proprietary serial
                          propPointToPointSerial(22),
                          ppp(23),
                          softwareLoopback(24),
                          eon(25),            -- CLNP over IP [11]
                          ethernet-3Mbit(26),
                          nsip(27),           -- XNS over IP
                          slip(28),           -- generic SLIP
                          ultra(29),          -- ULTRA technologies
                          ds3(30),            -- T-3
                          sip(31),            -- SMDS
                          frame-relay(32)
                      }
              ACCESS  read-only
              STATUS  mandatory
              DESCRIPTION
                      "The type of interface, distinguished according to
                      the physical/link protocol(s) immediately `below'
                      the network layer in the protocol stack."
              ::= { ifEntry 3 }

          ifMtu OBJECT-TYPE
              SYNTAX  INTEGER
              ACCESS  read-only
              STATUS  mandatory
              DESCRIPTION
                      "The size of the largest datagram which can be
                      sent/received on the interface, specified in
                      octets.  For interfaces that are used for
                      transmitting network datagrams, this is the size
                      of the largest network datagram that can be sent
                      on the interface."
              ::= { ifEntry 4 }

          ifSpeed OBJECT-TYPE
              SYNTAX  Gauge
              ACCESS  read-only
              STATUS  mandatory
              DESCRIPTION
                      "An estimate of the interface's current bandwidth
                      in bits per second.  For interfaces which do not
                      vary in bandwidth or for those where no accurate
                      estimation can be made, this object should contain
                      the nominal bandwidth."
              ::= { ifEntry 5 }

          ifPhysAddress OBJECT-TYPE
              SYNTAX  PhysAddress
              ACCESS  read-only
              STATUS  mandatory
              DESCRIPTION
                      "The interface's address at the protocol layer
                      immediately `below' the network layer in the
                      protocol stack.  For interfaces which do not have
                      such an address (e.g., a serial line), this object
                      should contain an octet string of zero length."
              ::= { ifEntry 6 }

          ifAdminStatus OBJECT-TYPE
              SYNTAX  INTEGER {
                          up(1),       -- ready to pass packets
                          down(2),
                          testing(3)   -- in some test mode
                      }
              ACCESS  read-write
              STATUS  mandatory
              DESCRIPTION
                      "The desired state of the interface.  The
                      testing(3) state indicates that no operational
                      packets can be passed."
              ::= { ifEntry 7 }

          ifOperStatus OBJECT-TYPE
              SYNTAX  INTEGER {
                          up(1),       -- ready to pass packets
                          down(2),
                          testing(3)   -- in some test mode
                      }
              ACCESS  read-only
              STATUS  mandatory
              DESCRIPTION
                      "The current operational state of the interface.
                      The testing(3) state indicates that no operational
                      packets can be passed."
              ::= { ifEntry 8 }

          ifLastChange OBJECT-TYPE
              SYNTAX  TimeTicks
              ACCESS  read-only
              STATUS  mandatory
              DESCRIPTION
                      "The value of sysUpTime at the time the interface
                      entered its current operational state.  If the
                      current state was entered prior to the last re-
                      initialization of the local network management
                      subsystem, then this object contains a zero
                      value."
              ::= { ifEntry 9 }

          ifInOctets OBJECT-TYPE
              SYNTAX  Counter
              ACCESS  read-only
              STATUS  mandatory
              DESCRIPTION
                      "The total number of octets received on the
                      interface, including framing characters."
              ::= { ifEntry 10 }

          ifInUcastPkts OBJECT-TYPE
              SYNTAX  Counter
              ACCESS  read-only
              STATUS  mandatory
              DESCRIPTION
                      "The number of subnetwork-unicast packets
                      delivered to a higher-layer protocol."
              ::= { ifEntry 11 }

          ifInNUcastPkts OBJECT-TYPE
              SYNTAX  Counter
              ACCESS  read-only
              STATUS  mandatory
              DESCRIPTION
                      "The number of non-unicast (i.e., subnetwork-
                      broadcast or subnetwork-multicast) packets
                      delivered to a higher-layer protocol."
              ::= { ifEntry 12 }

          ifInDiscards OBJECT-TYPE
              SYNTAX  Counter
              ACCESS  read-only
              STATUS  mandatory
              DESCRIPTION
                      "The number of inbound packets which were chosen
                      to be discarded even though no errors had been
                      detected to prevent their being deliverable to a
                      higher-layer protocol.  One possible reason for
                      discarding such a packet could be to free up
                      buffer space."
              ::= { ifEntry 13 }

          ifInErrors OBJECT-TYPE
              SYNTAX  Counter
              ACCESS  read-only
              STATUS  mandatory
              DESCRIPTION
                      "The number of inbound packets that contained
                      errors preventing them from being deliverable to a
                      higher-layer protocol."
              ::= { ifEntry 14 }

          ifInUnknownProtos OBJECT-TYPE
              SYNTAX  Counter
              ACCESS  read-only
              STATUS  mandatory
              DESCRIPTION
                      "The number of packets received via the interface
                      which were discarded because of an unknown or
                      unsupported protocol."
              ::= { ifEntry 15 }

          ifOutOctets OBJECT-TYPE
              SYNTAX  Counter
              ACCESS  read-only
              STATUS  mandatory
              DESCRIPTION
                      "The total number of octets transmitted out of the
                      interface, including framing characters."
              ::= { ifEntry 16 }

          ifOutUcastPkts OBJECT-TYPE
              SYNTAX  Counter
              ACCESS  read-only
              STATUS  mandatory
              DESCRIPTION
                      "The total number of packets that higher-level
                      protocols requested be transmitted to a
                      subnetwork-unicast address, including those that
                      were discarded or not sent."
              ::= { ifEntry 17 }

          ifOutNUcastPkts OBJECT-TYPE
              SYNTAX  Counter
              ACCESS  read-only
              STATUS  mandatory
              DESCRIPTION
                      "The total number of packets that higher-level
                      protocols requested be transmitted to a non-
                      unicast (i.e., a subnetwork-broadcast or
                      subnetwork-multicast) address, including those
                      that were discarded or not sent."
              ::= { ifEntry 18 }

          ifOutDiscards OBJECT-TYPE
              SYNTAX  Counter
              ACCESS  read-only
              STATUS  mandatory
              DESCRIPTION
                      "The number of outbound packets which were chosen
                      to be discarded even though no errors had been
                      detected to prevent their being transmitted.  One
                      possible reason for discarding such a packet could
                      be to free up buffer space."
              ::= { ifEntry 19 }

          ifOutErrors OBJECT-TYPE
              SYNTAX  Counter
              ACCESS  read-only
              STATUS  mandatory
              DESCRIPTION
                      "The number of outbound packets that could not be
                      transmitted because of errors."
              ::= { ifEntry 20 }

          ifOutQLen OBJECT-TYPE
              SYNTAX  Gauge
              ACCESS  read-only
              STATUS  mandatory
              DESCRIPTION
                      "The length of the output packet queue (in
                      packets)."
              ::= { ifEntry 21 }

          ifSpecific OBJECT-TYPE
              SYNTAX  OBJECT IDENTIFIER
              ACCESS  read-only
              STATUS  mandatory
              DESCRIPTION
                      "A reference to MIB definitions specific to the
                      particular media being used to realize the
                      interface.  For example, if the interface is
                      realized by an ethernet, then the value of this
                      object refers to a document defining objects
                      specific to ethernet.  If this information is not
                      present, its value should be set to the OBJECT
                      IDENTIFIER { 0 0 }, which is a syntatically valid
                      object identifier, and any conformant
                      implementation of ASN.1 and BER must be able to
                      generate and recognize this value."
              ::= { ifEntry 22 }


          -- the Address Translation group

          -- Implementation of the Address Translation group is
          -- mandatory for all systems.  Note however that this group
          -- is deprecated by MIB-II. That is, it is being included
          -- solely for compatibility with MIB-I nodes, and will most
          -- likely be excluded from MIB-III nodes.  From MIB-II and
          -- onwards, each network protocol group contains its own
          -- address translation tables.

          -- The Address Translation group contains one table which is
          -- the union across all interfaces of the translation tables
          -- for converting a NetworkAddress (e.g., an IP address) into
          -- a subnetwork-specific address.  For lack of a better term,
          -- this document refers to such a subnetwork-specific address
          -- as a `physical' address.

          -- Examples of such translation tables are: for broadcast
          -- media where ARP is in use, the translation table is
          -- equivalent to the ARP cache; or, on an X.25 network where
          -- non-algorithmic translation to X.121 addresses is
          -- required, the translation table contains the
          -- NetworkAddress to X.121 address equivalences.

          atTable OBJECT-TYPE
              SYNTAX  SEQUENCE OF AtEntry
              ACCESS  not-accessible
              STATUS  deprecated
              DESCRIPTION
                      "The Address Translation tables contain the
                      NetworkAddress to `physical' address equivalences.
                      Some interfaces do not use translation tables for
                      determining address equivalences (e.g., DDN-X.25
                      has an algorithmic method); if all interfaces are
                      of this type, then the Address Translation table
                      is empty, i.e., has zero entries."
              ::= { at 1 }

          atEntry OBJECT-TYPE
              SYNTAX  AtEntry
              ACCESS  not-accessible
              STATUS  deprecated
              DESCRIPTION
                      "Each entry contains one NetworkAddress to
                      `physical' address equivalence."
              INDEX   { atIfIndex,
                        atNetAddress }
              ::= { atTable 1 }

          AtEntry ::=
              SEQUENCE {
                  atIfIndex
                      INTEGER,
                  atPhysAddress
                      PhysAddress,
                  atNetAddress
                      NetworkAddress
              }

          atIfIndex OBJECT-TYPE
              SYNTAX  INTEGER
              ACCESS  read-write
              STATUS  deprecated
              DESCRIPTION
                      "The interface on which this entry's equivalence
                      is effective.  The interface identified by a
                      particular value of this index is the same
                      interface as identified by the same value of
                      ifIndex."
              ::= { atEntry 1 }

          atPhysAddress OBJECT-TYPE
              SYNTAX  PhysAddress
              ACCESS  read-write
              STATUS  deprecated
              DESCRIPTION
                      "The media-dependent `physical' address.

                      Setting this object to a null string (one of zero
                      length) has the effect of invaliding the
                      corresponding entry in the atTable object.  That
                      is, it effectively dissasociates the interface
                      identified with said entry from the mapping
                      identified with said entry.  It is an
                      implementation-specific matter as to whether the
                      agent removes an invalidated entry from the table.
                      Accordingly, management stations must be prepared
                      to receive tabular information from agents that
                      corresponds to entries not currently in use.
                      Proper interpretation of such entries requires
                      examination of the relevant atPhysAddress object."
              ::= { atEntry 2 }

          atNetAddress OBJECT-TYPE
              SYNTAX  NetworkAddress
              ACCESS  read-write
              STATUS  deprecated
              DESCRIPTION
                      "The NetworkAddress (e.g., the IP address)
                      corresponding to the media-dependent `physical'
                      address."
              ::= { atEntry 3 }


          -- the IP group

          -- Implementation of the IP group is mandatory for all
          -- systems.

          ipForwarding OBJECT-TYPE
              SYNTAX  INTEGER {
                          forwarding(1),    -- acting as a gateway
                          not-forwarding(2) -- NOT acting as a gateway
                      }
              ACCESS  read-write
              STATUS  mandatory
              DESCRIPTION
                      "The indication of whether this entity is acting
                      as an IP gateway in respect to the forwarding of
                      datagrams received by, but not addressed to, this
                      entity.  IP gateways forward datagrams.  IP hosts
                      do not (except those source-routed via the host).

                      Note that for some managed nodes, this object may
                      take on only a subset of the values possible.
                      Accordingly, it is appropriate for an agent to
                      return a `badValue' response if a management
                      station attempts to change this object to an
                      inappropriate value."
              ::= { ip 1 }

          ipDefaultTTL OBJECT-TYPE
              SYNTAX  INTEGER
              ACCESS  read-write
              STATUS  mandatory
              DESCRIPTION
                      "The default value inserted into the Time-To-Live
                      field of the IP header of datagrams originated at
                      this entity, whenever a TTL value is not supplied
                      by the transport layer protocol."
              ::= { ip 2 }

          ipInReceives OBJECT-TYPE
              SYNTAX  Counter
              ACCESS  read-only
              STATUS  mandatory
              DESCRIPTION
                      "The total number of input datagrams received from
                      interfaces, including those received in error."
              ::= { ip 3 }

          ipInHdrErrors OBJECT-TYPE
              SYNTAX  Counter
              ACCESS  read-only
              STATUS  mandatory
              DESCRIPTION
                      "The number of input datagrams discarded due to
                      errors in their IP headers, including bad
                      checksums, version number mismatch, other format
                      errors, time-to-live exceeded, errors discovered
                      in processing their IP options, etc."
              ::= { ip 4 }

          ipInAddrErrors OBJECT-TYPE
              SYNTAX  Counter
              ACCESS  read-only
              STATUS  mandatory
              DESCRIPTION
                      "The number of input datagrams discarded because
                      the IP address in their IP header's destination
                      field was not a valid address to be received at
                      this entity.  This count includes invalid
                      addresses (e.g., 0.0.0.0) and addresses of
                      unsupported Classes (e.g., Class E).  For entities
                      which are not IP Gateways and therefore do not
                      forward datagrams, this counter includes datagrams
                      discarded because the destination address was not
                      a local address."
              ::= { ip 5 }

          ipForwDatagrams OBJECT-TYPE
              SYNTAX  Counter
              ACCESS  read-only
              STATUS  mandatory
              DESCRIPTION
                      "The number of input datagrams for which this
                      entity was not their final IP destination, as a
                      result of which an attempt was made to find a
                      route to forward them to that final destination.
                      In entities which do not act as IP Gateways, this
                      counter will include only those packets which were
                      Source-Routed via this entity, and the Source-
                      Route option processing was successful."
              ::= { ip 6 }

          ipInUnknownProtos OBJECT-TYPE
              SYNTAX  Counter
              ACCESS  read-only
              STATUS  mandatory
              DESCRIPTION
                      "The number of locally-addressed datagrams
                      received successfully but discarded because of an
                      unknown or unsupported protocol."
              ::= { ip 7 }

          ipInDiscards OBJECT-TYPE
              SYNTAX  Counter
              ACCESS  read-only
              STATUS  mandatory
              DESCRIPTION
                      "The number of input IP datagrams for which no
                      problems were encountered to prevent their
                      continued processing, but which were discarded
                      (e.g., for lack of buffer space).  Note that this
                      counter does not include any datagrams discarded
                      while awaiting re-assembly."
              ::= { ip 8 }

          ipInDelivers OBJECT-TYPE
              SYNTAX  Counter
              ACCESS  read-only
              STATUS  mandatory
              DESCRIPTION
                      "The total number of input datagrams successfully
                      delivered to IP user-protocols (including ICMP)."
              ::= { ip 9 }

          ipOutRequests OBJECT-TYPE
              SYNTAX  Counter
              ACCESS  read-only
              STATUS  mandatory
              DESCRIPTION
                      "The total number of IP datagrams which local IP
                      user-protocols (including ICMP) supplied to IP in
                      requests for transmission.  Note that this counter
                      does not include any datagrams counted in
                      ipForwDatagrams."
              ::= { ip 10 }

          ipOutDiscards OBJECT-TYPE
              SYNTAX  Counter
              ACCESS  read-only
              STATUS  mandatory
              DESCRIPTION
                      "The number of output IP datagrams for which no
                      problem was encountered to prevent their
                      transmission to their destination, but which were
                      discarded (e.g., for lack of buffer space).  Note
                      that this counter would include datagrams counted
                      in ipForwDatagrams if any such packets met this
                      (discretionary) discard criterion."
              ::= { ip 11 }

          ipOutNoRoutes OBJECT-TYPE
              SYNTAX  Counter
              ACCESS  read-only
              STATUS  mandatory
              DESCRIPTION
                      "The number of IP datagrams discarded because no
                      route could be found to transmit them to their
                      destination.  Note that this counter includes any
                      packets counted in ipForwDatagrams which meet this
                      `no-route' criterion.  Note that this includes any
                      datagarms which a host cannot route because all of
                      its default gateways are down."
              ::= { ip 12 }

          ipReasmTimeout OBJECT-TYPE
              SYNTAX  INTEGER
              ACCESS  read-only
              STATUS  mandatory
              DESCRIPTION
                      "The maximum number of seconds which received
                      fragments are held while they are awaiting
                      reassembly at this entity."
              ::= { ip 13 }

          ipReasmReqds OBJECT-TYPE
              SYNTAX  Counter
              ACCESS  read-only
              STATUS  mandatory
              DESCRIPTION
                      "The number of IP fragments received which needed
                      to be reassembled at this entity."
              ::= { ip 14 }

          ipReasmOKs OBJECT-TYPE
              SYNTAX  Counter
              ACCESS  read-only
              STATUS  mandatory
              DESCRIPTION
                      "The number of IP datagrams successfully re-
                      assembled."
              ::= { ip 15 }

          ipReasmFails OBJECT-TYPE
              SYNTAX  Counter
              ACCESS  read-only
              STATUS  mandatory
              DESCRIPTION
                      "The number of failures detected by the IP re-
                      assembly algorithm (for whatever reason: timed
                      out, errors, etc).  Note that this is not
                      necessarily a count of discarded IP fragments
                      since some algorithms (notably the algorithm in
                      RFC 815) can lose track of the number of fragments
                      by combining them as they are received."
              ::= { ip 16 }

          ipFragOKs OBJECT-TYPE
              SYNTAX  Counter
              ACCESS  read-only
              STATUS  mandatory
              DESCRIPTION
                      "The number of IP datagrams that have been
                      successfully fragmented at this entity."
              ::= { ip 17 }

          ipFragFails OBJECT-TYPE
              SYNTAX  Counter
              ACCESS  read-only
              STATUS  mandatory
              DESCRIPTION
                      "The number of IP datagrams that have been
                      discarded because they needed to be fragmented at
                      this entity but could not be, e.g., because their
                      Don't Fragment flag was set."
              ::= { ip 18 }

          ipFragCreates OBJECT-TYPE
              SYNTAX  Counter
              ACCESS  read-only
              STATUS  mandatory
              DESCRIPTION
                      "The number of IP datagram fragments that have
                      been generated as a result of fragmentation at
                      this entity."
              ::= { ip 19 }

          -- the IP address table

          -- The IP address table contains this entity's IP addressing
          -- information.

          ipAddrTable OBJECT-TYPE
              SYNTAX  SEQUENCE OF IpAddrEntry
              ACCESS  not-accessible
              STATUS  mandatory
              DESCRIPTION
                      "The table of addressing information relevant to
                      this entity's IP addresses."
              ::= { ip 20 }

          ipAddrEntry OBJECT-TYPE
              SYNTAX  IpAddrEntry
              ACCESS  not-accessible
              STATUS  mandatory
              DESCRIPTION
                      "The addressing information for one of this
                      entity's IP addresses."
              INDEX   { ipAdEntAddr }
              ::= { ipAddrTable 1 }

          IpAddrEntry ::=
              SEQUENCE {
                  ipAdEntAddr
                      IpAddress,
                  ipAdEntIfIndex
                      INTEGER,
                  ipAdEntNetMask
                      IpAddress,
                  ipAdEntBcastAddr
                      INTEGER,
                  ipAdEntReasmMaxSize
                      INTEGER (0..65535)
              }

          ipAdEntAddr OBJECT-TYPE
              SYNTAX  IpAddress
              ACCESS  read-only
              STATUS  mandatory
              DESCRIPTION
                      "The IP address to which this entry's addressing
                      information pertains."
              ::= { ipAddrEntry 1 }

          ipAdEntIfIndex OBJECT-TYPE
              SYNTAX  INTEGER
              ACCESS  read-only
              STATUS  mandatory
              DESCRIPTION
                      "The index value which uniquely identifies the
                      interface to which this entry is applicable.  The
                      interface identified by a particular value of this
                      index is the same interface as identified by the
                      same value of ifIndex."
              ::= { ipAddrEntry 2 }

          ipAdEntNetMask OBJECT-TYPE
              SYNTAX  IpAddress
              ACCESS  read-only
              STATUS  mandatory
              DESCRIPTION
                      "The subnet mask associated with the IP address of
                      this entry.  The value of the mask is an IP
                      address with all the network bits set to 1 and all
                      the hosts bits set to 0."
              ::= { ipAddrEntry 3 }

          ipAdEntBcastAddr OBJECT-TYPE
              SYNTAX  INTEGER
              ACCESS  read-only
              STATUS  mandatory
              DESCRIPTION
                      "The value of the least-significant bit in the IP
                      broadcast address used for sending datagrams on
                      the (logical) interface associated with the IP
                      address of this entry.  For example, when the
                      Internet standard all-ones broadcast address is
                      used, the value will be 1.  This value applies to
                      both the subnet and network broadcasts addresses
                      used by the entity on this (logical) interface."
              ::= { ipAddrEntry 4 }

          ipAdEntReasmMaxSize OBJECT-TYPE
              SYNTAX  INTEGER (0..65535)
              ACCESS  read-only
              STATUS  mandatory
              DESCRIPTION
                      "The size of the largest IP datagram which this
                      entity can re-assemble from incoming IP fragmented
                      datagrams received on this interface."
              ::= { ipAddrEntry 5 }

          -- the IP routing table

          -- The IP routing table contains an entry for each route
          -- presently known to this entity.

          ipRouteTable OBJECT-TYPE
              SYNTAX  SEQUENCE OF IpRouteEntry
              ACCESS  not-accessible
              STATUS  mandatory
              DESCRIPTION
                      "This entity's IP Routing table."
              ::= { ip 21 }

          ipRouteEntry OBJECT-TYPE
              SYNTAX  IpRouteEntry
              ACCESS  not-accessible
              STATUS  mandatory
              DESCRIPTION
                      "A route to a particular destination."
              INDEX   { ipRouteDest }
              ::= { ipRouteTable 1 }

          IpRouteEntry ::=
              SEQUENCE {
                  ipRouteDest
                      IpAddress,
                  ipRouteIfIndex
                      INTEGER,
                  ipRouteMetric1
                      INTEGER,
                  ipRouteMetric2
                      INTEGER,
                  ipRouteMetric3
                      INTEGER,
                  ipRouteMetric4
                      INTEGER,
                  ipRouteNextHop
                      IpAddress,
                  ipRouteType
                      INTEGER,
                  ipRouteProto
                      INTEGER,
                  ipRouteAge
                      INTEGER,
                  ipRouteMask
                      IpAddress,
                  ipRouteMetric5
                      INTEGER,
                  ipRouteInfo
                      OBJECT IDENTIFIER
              }

          ipRouteDest OBJECT-TYPE
              SYNTAX  IpAddress
              ACCESS  read-write
              STATUS  mandatory
              DESCRIPTION
                      "The destination IP address of this route.  An
                      entry with a value of 0.0.0.0 is considered a
                      default route.  Multiple routes to a single
                      destination can appear in the table, but access to
                      such multiple entries is dependent on the table-
                      access mechanisms defined by the network
                      management protocol in use."
              ::= { ipRouteEntry 1 }

          ipRouteIfIndex OBJECT-TYPE
              SYNTAX  INTEGER
              ACCESS  read-write
              STATUS  mandatory
              DESCRIPTION
                      "The index value which uniquely identifies the
                      local interface through which the next hop of this
                      route should be reached.  The interface identified
                      by a particular value of this index is the same
                      interface as identified by the same value of
                      ifIndex."
              ::= { ipRouteEntry 2 }

          ipRouteMetric1 OBJECT-TYPE
              SYNTAX  INTEGER
              ACCESS  read-write
              STATUS  mandatory
              DESCRIPTION
                      "The primary routing metric for this route.  The
                      semantics of this metric are determined by the
                      routing-protocol specified in the route's
                      ipRouteProto value.  If this metric is not used,
                      its value should be set to -1."
              ::= { ipRouteEntry 3 }

          ipRouteMetric2 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 4 }

          ipRouteMetric3 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 5 }

          ipRouteMetric4 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 6 }

          ipRouteNextHop OBJECT-TYPE
              SYNTAX  IpAddress
              ACCESS  read-write
              STATUS  mandatory
              DESCRIPTION
                      "The IP address of the next hop of this route.
                      (In the case of a route bound to an interface
                      which is realized via a broadcast media, the value
                      of this field is the agent's IP address on that
                      interface.)"
              ::= { ipRouteEntry 7 }

          ipRouteType OBJECT-TYPE
              SYNTAX  INTEGER {
                          other(1),        -- none of the following

                          invalid(2),      -- an invalidated route

                                           -- route to directly
                          direct(3),       -- connected (sub-)network

                                           -- route to a non-local
                          indirect(4)      -- host/network/sub-network
                      }
              ACCESS  read-write
              STATUS  mandatory
              DESCRIPTION
                      "The type of route.  Note that the values
                      direct(3) and indirect(4) refer to the notion of
                      direct and indirect routing in the IP
                      architecture.

                      Setting this object to the value invalid(2) has
                      the effect of invalidating the corresponding entry
                      in the ipRouteTable object.  That is, it
                      effectively dissasociates the destination
                      identified with said entry from the route
                      identified with said entry.  It is an
                      implementation-specific matter as to whether the
                      agent removes an invalidated entry from the table.
                      Accordingly, management stations must be prepared
                      to receive tabular information from agents that
                      corresponds to entries not currently in use.
                      Proper interpretation of such entries requires
                      examination of the relevant ipRouteType object."
              ::= { ipRouteEntry 8 }

          ipRouteProto OBJECT-TYPE
              SYNTAX  INTEGER {
                          other(1),       -- none of the following

                                          -- non-protocol information,
                                          -- e.g., manually configured
                          local(2),       -- entries

                                          -- set via a network
                          netmgmt(3),     -- management protocol

                                          -- obtained via ICMP,
                          icmp(4),        -- e.g., Redirect

                                          -- the remaining values are
                                          -- all gateway routing
                                          -- protocols
                          egp(5),
                          ggp(6),
                          hello(7),
                          rip(8),
                          is-is(9),
                          es-is(10),
                          ciscoIgrp(11),
                          bbnSpfIgp(12),
                          ospf(13),
                          bgp(14)
                      }
              ACCESS  read-only
              STATUS  mandatory
              DESCRIPTION
                      "The routing mechanism via which this route was
                      learned.  Inclusion of values for gateway routing
                      protocols is not intended to imply that hosts
                      should support those protocols."
              ::= { ipRouteEntry 9 }

          ipRouteAge OBJECT-TYPE
              SYNTAX  INTEGER
              ACCESS  read-write
              STATUS  mandatory
              DESCRIPTION
                      "The number of seconds since this route was last
                      updated or otherwise determined to be correct.
                      Note that no semantics of `too old' can be implied
                      except through knowledge of the routing protocol
                      by which the route was learned."
              ::= { ipRouteEntry 10 }

          ipRouteMask OBJECT-TYPE
              SYNTAX  IpAddress
              ACCESS  read-write
              STATUS  mandatory
              DESCRIPTION
                      "Indicate the mask to be logical-ANDed with the
                      destination address before being compared to the
                      value in the ipRouteDest field.  For those systems
                      that do not support arbitrary subnet masks, an
                      agent constructs the value of the ipRouteMask by
                      determining whether the value of the correspondent
                      ipRouteDest field belong to a class-A, B, or C
                      network, and then using one of:

                           mask           network
                           255.0.0.0      class-A
                           255.255.0.0    class-B
                           255.255.255.0  class-C

                      If the value of the ipRouteDest is 0.0.0.0 (a
                      default route), then the mask value is also
                      0.0.0.0.  It should be noted that all IP routing
                      subsystems implicitly use this mechanism."
              ::= { ipRouteEntry 11 }

          ipRouteMetric5 OBJECT-TYPE
              SYNTAX  INTEGER
              ACCESS  read-write
              STATUS  mandatory
              DESCRIPTION
                      "An alternate routing metric for this route.  The
                      semantics of this metric are determined by the
                      routing-protocol specified in the route's
                      ipRouteProto value.  If this metric is not used,
                      its value should be set to -1."
              ::= { ipRouteEntry 12 }

          ipRouteInfo OBJECT-TYPE
              SYNTAX  OBJECT IDENTIFIER
              ACCESS  read-only
              STATUS  mandatory
              DESCRIPTION
                      "A reference to MIB definitions specific to the
                      particular routing protocol which is responsible
                      for this route, as determined by the value
                      specified in the route's ipRouteProto value.  If
                      this information is not present, its value should
                      be set to the OBJECT IDENTIFIER { 0 0 }, which is
                      a syntatically valid object identifier, and any
                      conformant implementation of ASN.1 and BER must be
                      able to generate and recognize this value."
              ::= { ipRouteEntry 13 }


          -- the IP Address Translation table

          -- The IP address translation table contain the IpAddress to
          -- `physical' address equivalences.  Some interfaces do not
          -- use translation tables for determining address
          -- equivalences (e.g., DDN-X.25 has an algorithmic method);
          -- if all interfaces are of this type, then the Address
          -- Translation table is empty, i.e., has zero entries.

          ipNetToMediaTable OBJECT-TYPE
              SYNTAX  SEQUENCE OF IpNetToMediaEntry
              ACCESS  not-accessible
              STATUS  mandatory
              DESCRIPTION
                      "The IP Address Translation table used for mapping
                      from IP addresses to physical addresses."
              ::= { ip 22 }

          ipNetToMediaEntry OBJECT-TYPE
              SYNTAX  IpNetToMediaEntry
              ACCESS  not-accessible
              STATUS  mandatory
              DESCRIPTION
                      "Each entry contains one IpAddress to `physical'
                      address equivalence."
              INDEX   { ipNetToMediaIfIndex,
                        ipNetToMediaNetAddress }
              ::= { ipNetToMediaTable 1 }

          IpNetToMediaEntry ::=
              SEQUENCE {
                  ipNetToMediaIfIndex
                      INTEGER,
                  ipNetToMediaPhysAddress
                      PhysAddress,
                  ipNetToMediaNetAddress
                      IpAddress,
                  ipNetToMediaType
                      INTEGER
              }

          ipNetToMediaIfIndex OBJECT-TYPE
              SYNTAX  INTEGER
              ACCESS  read-write
              STATUS  mandatory
              DESCRIPTION
                      "The interface on which this entry's equivalence
                      is effective.  The interface identified by a
                      particular value of this index is the same
                      interface as identified by the same value of
                      ifIndex."
              ::= { ipNetToMediaEntry 1 }

          ipNetToMediaPhysAddress OBJECT-TYPE
              SYNTAX  PhysAddress
              ACCESS  read-write
              STATUS  mandatory
              DESCRIPTION
                      "The media-dependent `physical' address."
              ::= { ipNetToMediaEntry 2 }

          ipNetToMediaNetAddress OBJECT-TYPE
              SYNTAX  IpAddress
              ACCESS  read-write
              STATUS  mandatory
              DESCRIPTION
                      "The IpAddress corresponding to the media-
                      dependent `physical' address."
              ::= { ipNetToMediaEntry 3 }

          ipNetToMediaType OBJECT-TYPE
              SYNTAX  INTEGER {
                          other(1),        -- none of the following
                          invalid(2),      -- an invalidated mapping
                          dynamic(3),
                          static(4)
                      }
              ACCESS  read-write
              STATUS  mandatory
              DESCRIPTION
                      "The type of mapping.

                      Setting this object to the value invalid(2) has
                      the effect of invalidating the corresponding entry
                      in the ipNetToMediaTable.  That is, it effectively
                      dissasociates the interface identified with said
                      entry from the mapping identified with said entry.
                      It is an implementation-specific matter as to
                      whether the agent removes an invalidated entry
                      from the table.  Accordingly, management stations
                      must be prepared to receive tabular information
                      from agents that corresponds to entries not
                      currently in use.  Proper interpretation of such
                      entries requires examination of the relevant
                      ipNetToMediaType object."
              ::= { ipNetToMediaEntry 4 }


          -- additional IP objects

          ipRoutingDiscards OBJECT-TYPE
              SYNTAX  Counter
              ACCESS  read-only
              STATUS  mandatory
              DESCRIPTION
                      "The number of routing entries which were chosen
                      to be discarded even though they are valid.  One
                      possible reason for discarding such an entry could
                      be to free-up buffer space for other routing
                      entries."
              ::= { ip 23 }


          -- the ICMP group

          -- Implementation of the ICMP group is mandatory for all
          -- systems.

          icmpInMsgs OBJECT-TYPE
              SYNTAX  Counter
              ACCESS  read-only
              STATUS  mandatory
              DESCRIPTION
                      "The total number of ICMP messages which the
                      entity received.  Note that this counter includes
                      all those counted by icmpInErrors."
              ::= { icmp 1 }

          icmpInErrors OBJECT-TYPE
              SYNTAX  Counter
              ACCESS  read-only
              STATUS  mandatory
              DESCRIPTION
                      "The number of ICMP messages which the entity
                      received but determined as having ICMP-specific
                      errors (bad ICMP checksums, bad length, etc.)."
              ::= { icmp 2 }

          icmpInDestUnreachs OBJECT-TYPE
              SYNTAX  Counter
              ACCESS  read-only
              STATUS  mandatory
              DESCRIPTION
                      "The number of ICMP Destination Unreachable
                      messages received."
              ::= { icmp 3 }

          icmpInTimeExcds OBJECT-TYPE
              SYNTAX  Counter
              ACCESS  read-only
              STATUS  mandatory
              DESCRIPTION
                      "The number of ICMP Time Exceeded messages
                      received."
              ::= { icmp 4 }

          icmpInParmProbs OBJECT-TYPE
              SYNTAX  Counter
              ACCESS  read-only
              STATUS  mandatory
              DESCRIPTION
                      "The number of ICMP Parameter Problem messages
                      received."
              ::= { icmp 5 }

          icmpInSrcQuenchs OBJECT-TYPE
              SYNTAX  Counter
              ACCESS  read-only
              STATUS  mandatory
              DESCRIPTION
                      "The number of ICMP Source Quench messages
                      received."
              ::= { icmp 6 }

          icmpInRedirects OBJECT-TYPE
              SYNTAX  Counter
              ACCESS  read-only
              STATUS  mandatory
              DESCRIPTION
                      "The number of ICMP Redirect messages received."
              ::= { icmp 7 }

          icmpInEchos OBJECT-TYPE
              SYNTAX  Counter
              ACCESS  read-only
              STATUS  mandatory
              DESCRIPTION
                      "The number of ICMP Echo (request) messages
                      received."
              ::= { icmp 8 }

          icmpInEchoReps OBJECT-TYPE
              SYNTAX  Counter
              ACCESS  read-only
              STATUS  mandatory
              DESCRIPTION
                      "The number of ICMP Echo Reply messages received."
              ::= { icmp 9 }

          icmpInTimestamps OBJECT-TYPE
              SYNTAX  Counter
              ACCESS  read-only
              STATUS  mandatory
              DESCRIPTION
                      "The number of ICMP Timestamp (request) messages
                      received."
              ::= { icmp 10 }

          icmpInTimestampReps OBJECT-TYPE
              SYNTAX  Counter
              ACCESS  read-only
              STATUS  mandatory
              DESCRIPTION
                      "The number of ICMP Timestamp Reply messages
                      received."
              ::= { icmp 11 }

          icmpInAddrMasks OBJECT-TYPE
              SYNTAX  Counter
              ACCESS  read-only
              STATUS  mandatory
              DESCRIPTION
                      "The number of ICMP Address Mask Request messages
                      received."
              ::= { icmp 12 }

          icmpInAddrMaskReps OBJECT-TYPE
              SYNTAX  Counter
              ACCESS  read-only
              STATUS  mandatory
              DESCRIPTION
                      "The number of ICMP Address Mask Reply messages
                      received."
              ::= { icmp 13 }

          icmpOutMsgs OBJECT-TYPE
              SYNTAX  Counter
              ACCESS  read-only
              STATUS  mandatory
              DESCRIPTION
                      "The total number of ICMP messages which this
                      entity attempted to send.  Note that this counter
                      includes all those counted by icmpOutErrors."
              ::= { icmp 14 }

          icmpOutErrors OBJECT-TYPE
              SYNTAX  Counter
              ACCESS  read-only
              STATUS  mandatory
              DESCRIPTION
                      "The number of ICMP messages which this entity did
                      not send due to problems discovered within ICMP
                      such as a lack of buffers.  This value should not
                      include errors discovered outside the ICMP layer
                      such as the inability of IP to route the resultant
                      datagram.  In some implementations there may be no
                      types of error which contribute to this counter's
                      value."
              ::= { icmp 15 }

          icmpOutDestUnreachs OBJECT-TYPE
              SYNTAX  Counter
              ACCESS  read-only
              STATUS  mandatory
              DESCRIPTION
                      "The number of ICMP Destination Unreachable
                      messages sent."
              ::= { icmp 16 }

          icmpOutTimeExcds OBJECT-TYPE
              SYNTAX  Counter
              ACCESS  read-only
              STATUS  mandatory
              DESCRIPTION
                      "The number of ICMP Time Exceeded messages sent."
              ::= { icmp 17 }

          icmpOutParmProbs OBJECT-TYPE
              SYNTAX  Counter
              ACCESS  read-only
              STATUS  mandatory
              DESCRIPTION
                      "The number of ICMP Parameter Problem messages
                      sent."
              ::= { icmp 18 }

          icmpOutSrcQuenchs OBJECT-TYPE
              SYNTAX  Counter
              ACCESS  read-only
              STATUS  mandatory
              DESCRIPTION
                      "The number of ICMP Source Quench messages sent."
              ::= { icmp 19 }

          icmpOutRedirects OBJECT-TYPE
              SYNTAX  Counter
              ACCESS  read-only
              STATUS  mandatory
              DESCRIPTION
                      "The number of ICMP Redirect messages sent.  For a
                      host, this object will always be zero, since hosts
                      do not send redirects."
              ::= { icmp 20 }

          icmpOutEchos OBJECT-TYPE
              SYNTAX  Counter
              ACCESS  read-only
              STATUS  mandatory
              DESCRIPTION
                      "The number of ICMP Echo (request) messages sent."
              ::= { icmp 21 }

          icmpOutEchoReps OBJECT-TYPE
              SYNTAX  Counter
              ACCESS  read-only
              STATUS  mandatory
              DESCRIPTION
                      "The number of ICMP Echo Reply messages sent."
              ::= { icmp 22 }

          icmpOutTimestamps OBJECT-TYPE
              SYNTAX  Counter
              ACCESS  read-only
              STATUS  mandatory
              DESCRIPTION
                      "The number of ICMP Timestamp (request) messages
                      sent."
              ::= { icmp 23 }

          icmpOutTimestampReps OBJECT-TYPE
              SYNTAX  Counter
              ACCESS  read-only
              STATUS  mandatory
              DESCRIPTION
                      "The number of ICMP Timestamp Reply messages
                      sent."
              ::= { icmp 24 }

          icmpOutAddrMasks OBJECT-TYPE
              SYNTAX  Counter
              ACCESS  read-only
              STATUS  mandatory
              DESCRIPTION
                      "The number of ICMP Address Mask Request messages
                      sent."
              ::= { icmp 25 }

          icmpOutAddrMaskReps OBJECT-TYPE
              SYNTAX  Counter
              ACCESS  read-only
              STATUS  mandatory
              DESCRIPTION
                      "The number of ICMP Address Mask Reply messages
                      sent."
              ::= { icmp 26 }


          -- the TCP group

          -- Implementation of the TCP group is mandatory for all
          -- systems that implement the TCP.

          -- Note that instances of object types that represent
          -- information about a particular TCP connection are
          -- transient; they persist only as long as the connection
          -- in question.

          tcpRtoAlgorithm OBJECT-TYPE
              SYNTAX  INTEGER {
                          other(1),    -- none of the following
                          constant(2), -- a constant rto
                          rsre(3),     -- MIL-STD-1778, Appendix B
                          vanj(4)      -- Van Jacobson's algorithm [10]
                      }
              ACCESS  read-only
              STATUS  mandatory
              DESCRIPTION
                      "The algorithm used to determine the timeout value
                      used for retransmitting unacknowledged octets."
              ::= { tcp 1 }

          tcpRtoMin OBJECT-TYPE
              SYNTAX  INTEGER
              ACCESS  read-only
              STATUS  mandatory
              DESCRIPTION
                      "The minimum value permitted by a TCP
                      implementation for the retransmission timeout,
                      measured in milliseconds.  More refined semantics
                      for objects of this type depend upon the algorithm
                      used to determine the retransmission timeout.  In
                      particular, when the timeout algorithm is rsre(3),
                      an object of this type has the semantics of the
                      LBOUND quantity described in RFC 793."
              ::= { tcp 2 }


          tcpRtoMax OBJECT-TYPE
              SYNTAX  INTEGER
              ACCESS  read-only
              STATUS  mandatory
              DESCRIPTION
                      "The maximum value permitted by a TCP
                      implementation for the retransmission timeout,
                      measured in milliseconds.  More refined semantics
                      for objects of this type depend upon the algorithm
                      used to determine the retransmission timeout.  In
                      particular, when the timeout algorithm is rsre(3),
                      an object of this type has the semantics of the
                      UBOUND quantity described in RFC 793."
              ::= { tcp 3 }

          tcpMaxConn OBJECT-TYPE
              SYNTAX  INTEGER
              ACCESS  read-only
              STATUS  mandatory
              DESCRIPTION
                      "The limit on the total number of TCP connections
                      the entity can support.  In entities where the
                      maximum number of connections is dynamic, this
                      object should contain the value -1."
              ::= { tcp 4 }

          tcpActiveOpens OBJECT-TYPE
              SYNTAX  Counter
              ACCESS  read-only
              STATUS  mandatory
              DESCRIPTION
                      "The number of times TCP connections have made a
                      direct transition to the SYN-SENT state from the
                      CLOSED state."
              ::= { tcp 5 }

          tcpPassiveOpens OBJECT-TYPE
              SYNTAX  Counter
              ACCESS  read-only
              STATUS  mandatory
              DESCRIPTION
                      "The number of times TCP connections have made a
                      direct transition to the SYN-RCVD state from the
                      LISTEN state."
              ::= { tcp 6 }

          tcpAttemptFails OBJECT-TYPE
              SYNTAX  Counter
              ACCESS  read-only
              STATUS  mandatory
              DESCRIPTION
                      "The number of times TCP connections have made a
                      direct transition to the CLOSED state from either
                      the SYN-SENT state or the SYN-RCVD state, plus the
                      number of times TCP connections have made a direct
                      transition to the LISTEN state from the SYN-RCVD
                      state."
              ::= { tcp 7 }

          tcpEstabResets OBJECT-TYPE
              SYNTAX  Counter
              ACCESS  read-only
              STATUS  mandatory
              DESCRIPTION
                      "The number of times TCP connections have made a
                      direct transition to the CLOSED state from either
                      the ESTABLISHED state or the CLOSE-WAIT state."
              ::= { tcp 8 }

          tcpCurrEstab OBJECT-TYPE
              SYNTAX  Gauge
              ACCESS  read-only
              STATUS  mandatory
              DESCRIPTION
                      "The number of TCP connections for which the
                      current state is either ESTABLISHED or CLOSE-
                      WAIT."
              ::= { tcp 9 }

          tcpInSegs OBJECT-TYPE
              SYNTAX  Counter
              ACCESS  read-only
              STATUS  mandatory
              DESCRIPTION
                      "The total number of segments received, including
                      those received in error.  This count includes
                      segments received on currently established
                      connections."
              ::= { tcp 10 }

          tcpOutSegs OBJECT-TYPE
              SYNTAX  Counter
              ACCESS  read-only
              STATUS  mandatory
              DESCRIPTION
                      "The total number of segments sent, including
                      those on current connections but excluding those
                      containing only retransmitted octets."
              ::= { tcp 11 }

          tcpRetransSegs OBJECT-TYPE
              SYNTAX  Counter
              ACCESS  read-only
              STATUS  mandatory
              DESCRIPTION
                      "The total number of segments retransmitted - that
                      is, the number of TCP segments transmitted
                      containing one or more previously transmitted
                      octets."
              ::= { tcp 12 }


          -- the TCP Connection table

          -- The TCP connection table contains information about this
          -- entity's existing TCP connections.

          tcpConnTable OBJECT-TYPE
              SYNTAX  SEQUENCE OF TcpConnEntry
              ACCESS  not-accessible
              STATUS  mandatory
              DESCRIPTION
                      "A table containing TCP connection-specific
                      information."
              ::= { tcp 13 }

          tcpConnEntry OBJECT-TYPE
              SYNTAX  TcpConnEntry
              ACCESS  not-accessible
              STATUS  mandatory
              DESCRIPTION
                      "Information about a particular current TCP
                      connection.  An object of this type is transient,
                      in that it ceases to exist when (or soon after)
                      the connection makes the transition to the CLOSED
                      state."
              INDEX   { tcpConnLocalAddress,
                        tcpConnLocalPort,
                        tcpConnRemAddress,
                        tcpConnRemPort }
              ::= { tcpConnTable 1 }

          TcpConnEntry ::=
              SEQUENCE {
                  tcpConnState
                      INTEGER,
                  tcpConnLocalAddress
                      IpAddress,
                  tcpConnLocalPort
                      INTEGER (0..65535),
                  tcpConnRemAddress
                      IpAddress,
                  tcpConnRemPort
                      INTEGER (0..65535)
              }

          tcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11),
                          deleteTCB(12)
                      }
              ACCESS  read-write
              STATUS  mandatory
              DESCRIPTION
                      "The state of this TCP connection.

                      The only value which may be set by a management
                      station is deleteTCB(12).  Accordingly, it is
                      appropriate for an agent to return a `badValue'
                      response if a management station attempts to set
                      this object to any other value.

                      If a management station sets this object to the
                      value deleteTCB(12), then this has the effect of
                      deleting the TCB (as defined in RFC 793) of the
                      corresponding connection on the managed node,
                      resulting in immediate termination of the
                      connection.

                      As an implementation-specific option, a RST
                      segment may be sent from the managed node to the
                      other TCP endpoint (note however that RST segments
                      are not sent reliably)."
              ::= { tcpConnEntry 1 }

          tcpConnLocalAddress OBJECT-TYPE
              SYNTAX  IpAddress
              ACCESS  read-only
              STATUS  mandatory
              DESCRIPTION
                      "The local IP address for this TCP connection.  In
                      the case of a connection in the listen state which
                      is willing to accept connections for any IP
                      interface associated with the node, the value
                      0.0.0.0 is used."
              ::= { tcpConnEntry 2 }

          tcpConnLocalPort OBJECT-TYPE
              SYNTAX  INTEGER (0..65535)
              ACCESS  read-only
              STATUS  mandatory
              DESCRIPTION
                      "The local port number for this TCP connection."
              ::= { tcpConnEntry 3 }

          tcpConnRemAddress OBJECT-TYPE
              SYNTAX  IpAddress
              ACCESS  read-only
              STATUS  mandatory
              DESCRIPTION
                      "The remote IP address for this TCP connection."
              ::= { tcpConnEntry 4 }

          tcpConnRemPort OBJECT-TYPE
              SYNTAX  INTEGER (0..65535)
              ACCESS  read-only
              STATUS  mandatory
              DESCRIPTION
                      "The remote port number for this TCP connection."
              ::= { tcpConnEntry 5 }


          -- additional TCP objects

          tcpInErrs OBJECT-TYPE
              SYNTAX  Counter
              ACCESS  read-only
              STATUS  mandatory
              DESCRIPTION
                      "The total number of segments received in error
                      (e.g., bad TCP checksums)."
              ::= { tcp 14 }

          tcpOutRsts OBJECT-TYPE
              SYNTAX  Counter
              ACCESS  read-only
              STATUS  mandatory
              DESCRIPTION
                      "The number of TCP segments sent containing the
                      RST flag."
              ::= { tcp 15 }


          -- the UDP group

          -- Implementation of the UDP group is mandatory for all
          -- systems which implement the UDP.

          udpInDatagrams OBJECT-TYPE
              SYNTAX  Counter
              ACCESS  read-only
              STATUS  mandatory
              DESCRIPTION
                      "The total number of UDP datagrams delivered to
                      UDP users."
              ::= { udp 1 }

          udpNoPorts OBJECT-TYPE
              SYNTAX  Counter
              ACCESS  read-only
              STATUS  mandatory
              DESCRIPTION
                      "The total number of received UDP datagrams for
                      which there was no application at the destination
                      port."
              ::= { udp 2 }

          udpInErrors OBJECT-TYPE
              SYNTAX  Counter
              ACCESS  read-only
              STATUS  mandatory
              DESCRIPTION
                      "The number of received UDP datagrams that could
                      not be delivered for reasons other than the lack
                      of an application at the destination port."
              ::= { udp 3 }

          udpOutDatagrams OBJECT-TYPE
              SYNTAX  Counter
              ACCESS  read-only
              STATUS  mandatory
              DESCRIPTION
                      "The total number of UDP datagrams sent from this
                      entity."
              ::= { udp 4 }


          -- the UDP Listener table

          -- The UDP listener table contains information about this
          -- entity's UDP end-points on which a local application is
          -- currently accepting datagrams.

          udpTable OBJECT-TYPE
              SYNTAX  SEQUENCE OF UdpEntry
              ACCESS  not-accessible
              STATUS  mandatory
              DESCRIPTION
                      "A table containing UDP listener information."
              ::= { udp 5 }

          udpEntry OBJECT-TYPE
              SYNTAX  UdpEntry
              ACCESS  not-accessible
              STATUS  mandatory
              DESCRIPTION
                      "Information about a particular current UDP
                      listener."
              INDEX   { udpLocalAddress, udpLocalPort }
              ::= { udpTable 1 }

          UdpEntry ::=
              SEQUENCE {
                  udpLocalAddress
                      IpAddress,
                  udpLocalPort
                      INTEGER (0..65535)
              }

          udpLocalAddress OBJECT-TYPE
              SYNTAX  IpAddress
              ACCESS  read-only
              STATUS  mandatory
              DESCRIPTION
                      "The local IP address for this UDP listener.  In
                      the case of a UDP listener which is willing to
                      accept datagrams for any IP interface associated
                      with the node, the value 0.0.0.0 is used."
              ::= { udpEntry 1 }

          udpLocalPort OBJECT-TYPE
              SYNTAX  INTEGER (0..65535)
              ACCESS  read-only
              STATUS  mandatory
              DESCRIPTION
                      "The local port number for this UDP listener."
              ::= { udpEntry 2 }


          -- the EGP group

          -- Implementation of the EGP group is mandatory for all
          -- systems which implement the EGP.

          snmpInPkts OBJECT-TYPE
              SYNTAX  Counter
              ACCESS  read-only
              STATUS  mandatory
              DESCRIPTION
                      "The total number of Messages delivered to the
                      SNMP entity from the transport service."
              ::= { snmp 1 }

          snmpOutPkts OBJECT-TYPE
              SYNTAX  Counter
              ACCESS  read-only
              STATUS  mandatory
              DESCRIPTION
                      "The total number of SNMP Messages which were
                      passed from the SNMP protocol entity to the
                      transport service."
              ::= { snmp 2 }

          snmpInBadVersions OBJECT-TYPE
              SYNTAX  Counter
              ACCESS  read-only
              STATUS  mandatory
              DESCRIPTION
                      "The total number of SNMP Messages which were
                      delivered to the SNMP protocol entity and were for
                      an unsupported SNMP version."
              ::= { snmp 3 }

          snmpInBadCommunityNames OBJECT-TYPE
              SYNTAX  Counter
              ACCESS  read-only
              STATUS  mandatory
              DESCRIPTION
                      "The total number of SNMP Messages delivered to
                      the SNMP protocol entity which used a SNMP
                      community name not known to said entity."
              ::= { snmp 4 }

          snmpInBadCommunityUses OBJECT-TYPE
              SYNTAX  Counter
              ACCESS  read-only
              STATUS  mandatory
              DESCRIPTION
                      "The total number of SNMP Messages delivered to
                      the SNMP protocol entity which represented an SNMP
                      operation which was not allowed by the SNMP
                      community named in the Message."
              ::= { snmp 5 }

          snmpInASNParseErrs OBJECT-TYPE
              SYNTAX  Counter
              ACCESS  read-only
              STATUS  mandatory
              DESCRIPTION
                      "The total number of ASN.1 or BER errors
                      encountered by the SNMP protocol entity when
                      decoding received SNMP Messages."
              ::= { snmp 6 }

          -- { snmp 7 } is not used

          snmpInTooBigs OBJECT-TYPE
              SYNTAX  Counter
              ACCESS  read-only
              STATUS  mandatory
              DESCRIPTION
                      "The total number of SNMP PDUs which were
                      delivered to the SNMP protocol entity and for
                      which the value of the error-status field is
                      `tooBig'."
              ::= { snmp 8 }

          snmpInNoSuchNames OBJECT-TYPE
              SYNTAX  Counter
              ACCESS  read-only
              STATUS  mandatory
              DESCRIPTION
                      "The total number of SNMP PDUs which were
                      delivered to the SNMP protocol entity and for
                      which the value of the error-status field is
                      `noSuchName'."
              ::= { snmp 9 }

          snmpInBadValues OBJECT-TYPE
              SYNTAX  Counter
              ACCESS  read-only
              STATUS  mandatory
              DESCRIPTION
                      "The total number of SNMP PDUs which were
                      delivered to the SNMP protocol entity and for
                      which the value of the error-status field is
                      `badValue'."
              ::= { snmp 10 }

          snmpInReadOnlys OBJECT-TYPE
              SYNTAX  Counter
              ACCESS  read-only
              STATUS  mandatory
              DESCRIPTION
                      "The total number valid SNMP PDUs which were
                      delivered to the SNMP protocol entity and for
                      which the value of the error-status field is
                      `readOnly'.  It should be noted that it is a
                      protocol error to generate an SNMP PDU which
                      contains the value `readOnly' in the error-status
                      field, as such this object is provided as a means
                      of detecting incorrect implementations of the
                      SNMP."
              ::= { snmp 11 }

          snmpInGenErrs OBJECT-TYPE
              SYNTAX  Counter
              ACCESS  read-only
              STATUS  mandatory
              DESCRIPTION
                      "The total number of SNMP PDUs which were
                      delivered to the SNMP protocol entity and for
                      which the value of the error-status field is
                      `genErr'."
              ::= { snmp 12 }

          snmpInTotalReqVars OBJECT-TYPE
              SYNTAX  Counter
              ACCESS  read-only
              STATUS  mandatory
              DESCRIPTION
                      "The total number of MIB objects which have been
                      retrieved successfully by the SNMP protocol entity
                      as the result of receiving valid SNMP Get-Request
                      and Get-Next PDUs."
              ::= { snmp 13 }

          snmpInTotalSetVars OBJECT-TYPE
              SYNTAX  Counter
              ACCESS  read-only
              STATUS  mandatory
              DESCRIPTION
                      "The total number of MIB objects which have been
                      altered successfully by the SNMP protocol entity
                      as the result of receiving valid SNMP Set-Request
                      PDUs."
              ::= { snmp 14 }

          snmpInGetRequests OBJECT-TYPE
              SYNTAX  Counter
              ACCESS  read-only
              STATUS  mandatory
              DESCRIPTION
                      "The total number of SNMP Get-Request PDUs which
                      have been accepted and processed by the SNMP
                      protocol entity."
              ::= { snmp 15 }

          snmpInGetNexts OBJECT-TYPE
              SYNTAX  Counter
              ACCESS  read-only
              STATUS  mandatory
              DESCRIPTION
                      "The total number of SNMP Get-Next PDUs which have
                      been accepted and processed by the SNMP protocol
                      entity."
              ::= { snmp 16 }

          snmpInSetRequests OBJECT-TYPE
              SYNTAX  Counter
              ACCESS  read-only
              STATUS  mandatory
              DESCRIPTION
                      "The total number of SNMP Set-Request PDUs which
                      have been accepted and processed by the SNMP
                      protocol entity."
              ::= { snmp 17 }

          snmpInGetResponses OBJECT-TYPE
              SYNTAX  Counter
              ACCESS  read-only
              STATUS  mandatory
              DESCRIPTION
                      "The total number of SNMP Get-Response PDUs which
                      have been accepted and processed by the SNMP
                      protocol entity."
              ::= { snmp 18 }

          snmpInTraps OBJECT-TYPE
              SYNTAX  Counter
              ACCESS  read-only
              STATUS  mandatory
              DESCRIPTION
                      "The total number of SNMP Trap PDUs which have
                      been accepted and processed by the SNMP protocol
                      entity."
              ::= { snmp 19 }

          snmpOutTooBigs OBJECT-TYPE
              SYNTAX  Counter
              ACCESS  read-only
              STATUS  mandatory
              DESCRIPTION
                      "The total number of SNMP PDUs which were
                      generated by the SNMP protocol entity and for
                      which the value of the error-status field is
                      `tooBig.'"
              ::= { snmp 20 }

          snmpOutNoSuchNames OBJECT-TYPE
              SYNTAX  Counter
              ACCESS  read-only
              STATUS  mandatory
              DESCRIPTION
                      "The total number of SNMP PDUs which were
                      generated by the SNMP protocol entity and for
                      which the value of the error-status is
                      `noSuchName'."
              ::= { snmp 21 }

          snmpOutBadValues OBJECT-TYPE
              SYNTAX  Counter
              ACCESS  read-only
              STATUS  mandatory
              DESCRIPTION
                      "The total number of SNMP PDUs which were
                      generated by the SNMP protocol entity and for
                      which the value of the error-status field is
                      `badValue'."
              ::= { snmp 22 }

          -- { snmp 23 } is not used

          snmpOutGenErrs OBJECT-TYPE
              SYNTAX  Counter
              ACCESS  read-only
              STATUS  mandatory
              DESCRIPTION
                      "The total number of SNMP PDUs which were
                      generated by the SNMP protocol entity and for
                      which the value of the error-status field is
                      `genErr'."
              ::= { snmp 24 }

          snmpOutGetRequests OBJECT-TYPE
              SYNTAX  Counter
              ACCESS  read-only
              STATUS  mandatory
              DESCRIPTION
                      "The total number of SNMP Get-Request PDUs which
                      have been generated by the SNMP protocol entity."
              ::= { snmp 25 }

          snmpOutGetNexts OBJECT-TYPE
              SYNTAX  Counter
              ACCESS  read-only
              STATUS  mandatory
              DESCRIPTION
                      "The total number of SNMP Get-Next PDUs which have
                      been generated by the SNMP protocol entity."
              ::= { snmp 26 }

          snmpOutSetRequests OBJECT-TYPE
              SYNTAX  Counter
              ACCESS  read-only
              STATUS  mandatory
              DESCRIPTION
                      "The total number of SNMP Set-Request PDUs which
                      have been generated by the SNMP protocol entity."
              ::= { snmp 27 }

          snmpOutGetResponses OBJECT-TYPE
              SYNTAX  Counter
              ACCESS  read-only
              STATUS  mandatory
              DESCRIPTION
                      "The total number of SNMP Get-Response PDUs which
                      have been generated by the SNMP protocol entity."
              ::= { snmp 28 }

          snmpOutTraps OBJECT-TYPE
              SYNTAX  Counter
              ACCESS  read-only
              STATUS  mandatory
              DESCRIPTION
                      "The total number of SNMP Trap PDUs which have
                      been generated by the SNMP protocol entity."
              ::= { snmp 29 }

          snmpEnableAuthenTraps OBJECT-TYPE
              SYNTAX  INTEGER { enabled(1), disabled(2) }
              ACCESS  read-write
              STATUS  mandatory
              DESCRIPTION
                      "Indicates whether the SNMP agent process is
                      permitted to generate authentication-failure
                      traps.  The value of this object overrides any
                      configuration information; as such, it provides a
                      means whereby all authentication-failure traps may
                      be disabled.

                      Note that it is strongly recommended that this
                      object be stored in non-volatile memory so that it
                      remains constant between re-initializations of the
                      network management system."
              ::= { snmp 30 }


-- end of MIB-2 objects


-- Xyplex System MIB


            xyplex          OBJECT IDENTIFIER ::= { enterprises 33 }


            xSystem         OBJECT IDENTIFIER ::= { xyplex 1 }

            -- This is a MIB module for all Xyplex systems
            -- Textual Conventions
            DateTime ::=
                OCTET STRING (SIZE (8))
            -- This data type is used throughout the Xyplex private MIB
            -- to model an absolute date and time.
            -- In order, the octets contain the following information:
            -- century, year within century (0..99), month (1..12),
            -- day (1..31), hour (0..23), minute (0..59),
            -- second (0..59), hundredth (0..99).  If the century
            -- value is zero, the date and time are unknown, and the
            -- other values are meaningless.

            AddressType ::=
                INTEGER  { unknown(1), other(2), local(3),
                           ip(4), ethernet(5) }
            -- This data type is used throughout the Xyplex private MIB
            -- to indicate the type of an address stored in a related
            -- octet string.


            -- the System group
            -- Implementation of this group is mandatory for all Xyplex
            -- systems.

            sysIdent OBJECT-TYPE
                SYNTAX DisplayString (SIZE (0..50))
                ACCESS read-write
                STATUS mandatory
                DESCRIPTION
                    "An identification string for local and remote 
                    displays.  Corresponds directly to SERVER 
                    IDENTIFICATION and the value labeled 
                    'Identification:' on the SERVER CHARACTERISTICS 
                    display."
                ::= { xSystem 1 }


            sysDefineMode OBJECT-TYPE
                SYNTAX INTEGER { permOnly(1), operAndPerm(2) }
                ACCESS read-write
                STATUS mandatory
                DESCRIPTION
                    "The system's operation with regard to DEFINE 
                    commands.  'permOnly' indicates that DEFINE commands 
                    modify only the permanent data base.  'operAndPerm' 
                    indicates that DEFINE commands modify both 
                    operational and permanent data bases, unless 
                    specifically documented to the contrary.  
                    Corresponds to SERVER CHANGE and the presence of the 
                    label CHANGE in the SERVER CHARACTERISTICS 
                    display."
                ::= { xSystem 2 }


            sysDateTime OBJECT-TYPE
                SYNTAX DateTime
                ACCESS read-write
                STATUS mandatory
                DESCRIPTION
                    "The system's current local date and time.  
                    Corresponds directly to SERVER DATE and SERVER TIME 
                    and the value in various displays."
                ::= { xSystem 3 }


            sysTimeZone OBJECT-TYPE
                SYNTAX OCTET STRING (SIZE (2))
                ACCESS read-write
                STATUS mandatory
                DESCRIPTION
                    "The adjustment to apply to a universal (Greenwich) 
                    time received when down-line loaded, comprising two 
                    octets.  The first octet is the number of hours west 
                    of universal, the second is the number of minutes.  
                    Corresponds directly to SERVER TIMEZONE and the 
                    value labeled 'Timezone:' in the SERVER 
                    CHARACTERISTICS display."
                ::= { xSystem 4 }


            sysLoadSoftware OBJECT-TYPE
                SYNTAX DisplayString (SIZE (0..15))
                ACCESS read-write
                STATUS mandatory
                DESCRIPTION
                    "The software file name to request for down-line 
                    load of the server.  Corresponds directly to SERVER 
                    SOFTWARE, and the value labeled 'Software:' in the 
                    SERVER CHARACTERISTICS display."
                ::= { xSystem 5 }


            sysDump OBJECT-TYPE
                SYNTAX INTEGER { disabled(1), enabled(2) }
                ACCESS read-write
                STATUS mandatory
                DESCRIPTION
                    "Control for dumping the system's memory when the 
                    system crashes.  Corresponds directly to SERVER DUMP 
                    and the presence of 'Dump' under the label 'Enabled 
                    Characteristics' in the SERVER CHARACTERISTICS 
                    display."
                ::= { xSystem 6 }


            sysMaintenancePassword OBJECT-TYPE
                SYNTAX OCTET STRING (SIZE (0..8))
                ACCESS read-write
                STATUS mandatory
                DESCRIPTION
                    "The password a management system must supply to 
                    force the system to reboot or use the system's 
                    remote console via the Maintenance Operation 
                    Protocol (MOP).  Corresponds directly to SERVER 
                    MAINTENANCE PASSWORD.

                    When setting this value, the management system must 
                    supply eight octets, filling with zeros from the 
                    first octet.  That is, the value '1ab42' would be 
                    expressed as '0.0.0.0.0.1.ab.42'.  Setting the value 
                    to zero disables the password check.

                    When returning this value, the agent always returns 
                    a zero length OCTET STRING."
                ::= { xSystem 7 }


            sysLocalName OBJECT-TYPE
                SYNTAX DisplayString (SIZE (0..16))
                ACCESS read-write
                STATUS mandatory
                DESCRIPTION
                    "The system's local name.  Corresponds directly to 
                    SERVER NAME and the value labeled 'Name:' in the 
                    SERVER CHARACTERISTICS display."
                ::= { xSystem 8 }


            sysSoftwareVersionType OBJECT-TYPE
                SYNTAX INTEGER { alpha(1), beta(2),
                                 production(3), special(4) }
                ACCESS read-only
                STATUS mandatory
                DESCRIPTION
                    "The software version variant running in the system.  
                    Corresponds to the letter in the software version in 
                    the SERVER CHARACTERISTICS display.

                    alpha         'A':   alpha test
                    beta          'B':   beta test
                    production    null:  normal, production software
                    special       'S':   special, custom software
                    "
                ::= { xSystem 9 }


            sysSoftwareVersion OBJECT-TYPE
                SYNTAX OCTET STRING (SIZE (4))
                ACCESS read-only
                STATUS mandatory
                DESCRIPTION
                    "The software version running in the system.  In 
                    order, the octets contain major version, minor 
                    version, ECO, and pre-release number.  Corresponds 
                    to the numbers in the software version in the SERVER 
                    CHARACTERISTICS display.
            For example, the version display for 
                    sysSoftwareVersionType 'production' and 
                    sysSoftwareVersion '2.2.0.0' is 'V2.2'.

                    The version display for sysSoftwareVersionType 
                    'beta' and sysSoftwareVersion '3.1.0.4' is 
                    'V3.1B4'."
                ::= { xSystem 10 }


            sysRomVersion OBJECT-TYPE
                SYNTAX INTEGER
                ACCESS read-only
                STATUS mandatory
                DESCRIPTION
                    "The firmware version of the bootstrap ROM installed 
                    in the system.  Corresponds directly to the value 
                    labeled 'Rom' in the SERVER CHARACTERISTICS 
                    display."
                ::= { xSystem 11 }


            sysHardwareType OBJECT-TYPE
                SYNTAX INTEGER
                ACCESS read-only
                STATUS mandatory
                DESCRIPTION
                    "The type of hardware on which the system is 
                    running, with values as defined in Xyplex Assigned 
                    Numbers, Xyplex document number 420-0497.  
                    Corresponds directly to the value labeled 'Hardware 
                    Type:' in the UNIT display."
                ::= { xSystem 12 }


            sysHardwareVersion OBJECT-TYPE
                SYNTAX INTEGER
                ACCESS read-only
                STATUS mandatory
                DESCRIPTION
                    "This version of hardware on which the system is 
                    running.  Corresponds directly to part of the value 
                    labeled 'HW' in the SERVER CHARACTERISTICS 
                    display."
                ::= { xSystem 13 }


            sysChassisType OBJECT-TYPE
                SYNTAX INTEGER { mx45xx(1), other(2), lanbusII(3) }
                ACCESS read-only
                STATUS mandatory
                DESCRIPTION
                    "The type of chassis in which the system is running.  
                    Corresponds directly to part of the value labeled 
                    'HW' in the SERVER CHARACTERISTICS display."
                ::= { xSystem 14 }


            sysChassisVersion OBJECT-TYPE
                SYNTAX INTEGER
                ACCESS read-only
                STATUS mandatory
                DESCRIPTION
                    "This version of chassis in which the system is 
                    running.  Corresponds directly to part of the value 
                    labeled 'HW' in the SERVER CHARACTERISTICS 
                    display."
                ::= { xSystem 15 }


            sysCrash OBJECT-TYPE
                SYNTAX INTEGER { ready(1), execute(2) }
                ACCESS read-write
                STATUS mandatory
                DESCRIPTION
                    "Control to cause this system to crash.  In response 
                    to a get-request or get-next-request, the agent 
                    always returns 'ready' for this value.  Setting the 
                    value to 'ready' has no effect.  Setting it to 
                    'execute' causes an immediate crash.  Corresponds to 
                    the CRASH command."
            ::= { xSystem 16 }


            sysInitialize OBJECT-TYPE
                SYNTAX INTEGER { ready(1), conditionalExecute(2),
                                 unconditionalExecute(3), cancel(4) }
                ACCESS read-write
                STATUS mandatory
                DESCRIPTION
                    "Control to cause this system to reset its software 
                    to initial load values, typically by reloading.  
                    When executing an initialize command, the system 
                    observes the value of sysInitializeDelay as supplied 
                    anywhere in the same set request with sysInitialize.  
                    If this value is not included in the set request, 
                    the system uses its default value.
            In response to a get-request or get-next-request, 
                    the agent always returns 'ready' for this value.  
                    Setting the value to 'ready' has no effect.  Setting 
                    it to 'conditionalExecute' causes initialization if 
                    the overall system state is acceptible (such as not 
                    needing to store permanent parameters).  Setting it 
                    to 'unconditionalExecute' causes initialization 
                    regardless of the overall system state.  Setting it 
                    to 'cancel' aborts an initialization that has not 
                    yet started.  According to standard SNMP operation, 
                    if the system is not in a proper state to accept a 
                    given set request for this value, it returns the 
                    standard SNMP error 'badValue'.

                    Corresponds to the INITIALIZE command."
                ::= { xSystem 17 }


            sysInitializeDelay OBJECT-TYPE
                SYNTAX INTEGER (0..32768)
                ACCESS read-write
                STATUS mandatory
                DESCRIPTION
                    "The number of minutes to delay before beginning the 
                    system initialization process as executed with 
                    sysInitialize.

                    This value cannot be set outside a set-request that 
                    contains the value 'execute' for sysInitialize.  If 
                    not included in such a set, the default value is 1.

                    Corresponds to the INITIALIZE command's DELAY 
                    parameter and to the value labeled 'Minutes to 
                    shutdown:' in the SYSTEM STATUS display."
                ::= { xSystem 18 }


            sysZeroAll OBJECT-TYPE
                SYNTAX INTEGER { ready(1), execute(2) }
                ACCESS read-write
                STATUS mandatory
                DESCRIPTION
                    "Control to zero all counters.  In response to a 
                    get-request or get-next-request, the agent always 
                    returns 'ready' for this value.  Setting the value 
                    to 'ready' has no effect.  Setting it to 'execute' 
                    causes all the system's counters to be zeroed.  
                    Corresponds to the ZERO ALL command."
                ::= { xSystem 19 }


            sysZeroBase OBJECT-TYPE
                SYNTAX INTEGER { ready(1), execute(2) }
                ACCESS read-write
                STATUS mandatory
                DESCRIPTION
                    "Control to zero all base counters.  In response to 
                    a get-request or get-next-request, the agent always 
                    returns 'ready' for this value.  Setting the value 
                    to 'ready' has no effect.  Setting it to 'execute' 
                    causes all the system's base counters to be zeroed.  
                    Examples of counters that are zeroed are the SNMP 
                    counters or the counters from the SYSTEM COUNTERS 
                    display.  Examples of counters that are not zeroed 
                    are Ethernet interface counters or port counters.  
                    Corresponds to the ZERO SYSTEM command."
                ::= { xSystem 20 }


            sysZeroBaseTime OBJECT-TYPE
                SYNTAX TimeTicks
                ACCESS read-only
                STATUS mandatory
                DESCRIPTION
                    "The number hundredths of a second since the most 
                    recent zeroing of the base counters, such as through 
                    execution of sysZeroAll or sysZeroBase.  Corresponds 
                    directly to the value labeled 'Seconds Since 
                    Zeroed:' in the SERVER COUNTERS display."
                ::= { xSystem 21 }


            sysLoaderName OBJECT-TYPE
                SYNTAX DisplayString (SIZE (0..40))
                ACCESS read-only
                STATUS mandatory
                DESCRIPTION
                    "The name of the system that provided this system's 
                    running software.  Corresponds directly to the value 
                    labeled 'Primary Host:' in the SERVER STATUS 
                    display."
                ::= { xSystem 22 }


            sysLoaderAddressType OBJECT-TYPE
                SYNTAX AddressType
                ACCESS read-only
                STATUS mandatory
                DESCRIPTION
                    "The type of network address contained in 
                    sysLoaderAddress.  'unknown' means no address has 
                    been defined.  'other' means no other type value 
                    applies.  'local' means there is no address and this 
                    system's software was loaded from local storage.  
                    'ip' is an Internet IP address.  'ethernet' is an 
                    802.3 MAC address.  Corresponds indirectly to the 
                    value labeled 'Load Address:' in the SERVER STATUS 
                    display."
                ::= { xSystem 23 }


            sysLoaderAddress OBJECT-TYPE
                SYNTAX OCTET STRING
                ACCESS read-only
                STATUS mandatory
                DESCRIPTION
                    "The network address of the system that provided 
                    this system's running software.  Corresponds 
                    directly to the value labeled 'Load Address:' in the 
                    SERVER STATUS display."
                ::= { xSystem 24 }


            sysDumperAddressType OBJECT-TYPE
                SYNTAX AddressType
                ACCESS read-only
                STATUS mandatory
                DESCRIPTION
                    "The type of network address contained in 
                    sysDumperAddress.  'unknown' means no address has 
                    been defined.  'other' means no other type value 
                    applies.  'local' means there is no address and this 
                    system's was dumped to local storage.  'ip' is an 
                    Internet IP address.  'ethernet' is an 802.3 MAC 
                    address.  Corresponds indirectly to the value 
                    labeled 'Dump Address:' in the SERVER STATUS 
                    display."
                ::= { xSystem 25 }


            sysDumperAddress OBJECT-TYPE
                SYNTAX OCTET STRING
                ACCESS read-only
                STATUS mandatory
                DESCRIPTION
                    "The network address of the system that most 
                    recently accepted a crash dump from this system.  
                    Corresponds directly to the value labeled 'Dump 
                    Address:' in the SERVER STATUS display."
                ::= { xSystem 26 }


            sysResourceLacks OBJECT-TYPE
                SYNTAX Counter
                ACCESS read-only
                STATUS mandatory
                DESCRIPTION
                    "The number of times a local resource allocation 
                    failed, for example due to lack of dynamic memory.  
                    Corresponds directly to the value labeled 'Resource 
                    Errors:' in the SERVER STATUS display."
                ::= { xSystem 27 }


            sysChassisState OBJECT-TYPE
                SYNTAX INTEGER { notApplicable(1), noFault(2), fault(3) }
                ACCESS read-only
                STATUS mandatory
                DESCRIPTION
                    "For chassis-based systems, the state of the overall 
                    chassis.  'notApplicable' indicates the system is 
                    not chassis based.  'noFault' indicates no current 
                    chassis problem.  'fault' indicates a current 
                    chassis problem such as a card or power supply 
                    failure.  Corresponds directly to the value labeled 
                    'Crate Current State: in the SERVER ALTERNATE STATUS 
                    display."
                ::= { xSystem 28 }


            sysChassisFaultTransitions OBJECT-TYPE
                SYNTAX Counter
                ACCESS read-only
                STATUS mandatory
                DESCRIPTION
                    "The number of times this system has seen 
                    sysChassisState switch from 'noFault' to 'fault' or 
                    from 'fault' to 'noFault'.  Corresponds directly to 
                    the value labeled 'Crate Transition Count: in the 
                    SERVER ALTERNATE STATUS display."
                ::= { xSystem 29 }


            sysResourceNumber OBJECT-TYPE
                SYNTAX INTEGER
                ACCESS read-only
                STATUS mandatory
                DESCRIPTION
                    "The number of resource entries in the Resource 
                    table."
                ::= { xSystem 30 }


            sysFeatureNumber OBJECT-TYPE
                SYNTAX INTEGER
                ACCESS read-only
                STATUS mandatory
                DESCRIPTION
                    "The number of feature entries in the Feature 
                    table."
                ::= { xSystem 31 }

            -- more base objects following tables
            -- the Resource table

            resTable OBJECT-TYPE
                SYNTAX SEQUENCE OF ResEntry
                ACCESS not-accessible
                STATUS mandatory
                DESCRIPTION
                    "A list of resource entries.  The number of entries 
                    is given by the value of sysResourceNumber."
                ::= { xSystem 32 }


            resEntry OBJECT-TYPE
                SYNTAX ResEntry
                ACCESS not-accessible
                STATUS mandatory
                DESCRIPTION
                    "Status values for a system resource."
                INDEX { resType }
                ::= { resTable 1 }

            ResEntry ::=
                SEQUENCE {
                    resType
                        INTEGER,
                    resCurrent
                        Gauge,
                    resWorst
                        Gauge,
                    resAdminMaximum
                        INTEGER,
                    resLacks
                        Counter,
                    resLackTime
                        DateTime,
                    resOperMaximum
                        INTEGER
                }

            resType OBJECT-TYPE
                SYNTAX INTEGER { cpuPercent(1), memoryPercent(2),
                                 process(3), timer(4), packetBuffer(5),
                                 ipcMessage(6), textPool(7),
                                 freeMemory(8), globalMemoryPercent(9),
                                 phivDecnetRouteCache(10),
                                 ipFilterCache(11), ipRouteCache(12),
                                 ipxRouteCache(13), ipPolicyTable(14),
                                 ipFilterTable(15) }
                ACCESS read-only
                STATUS mandatory
                DESCRIPTION
                    "Identification of a resource type.  Typically 
                    corresponds directly to a label such as 'Processes:' 
                    in the SERVER ALTERNATE STATUS display."
                ::= { resEntry 1 }


            resCurrent OBJECT-TYPE
                SYNTAX Gauge
                ACCESS read-only
                STATUS mandatory
                DESCRIPTION
                    "The number of resources currently in use on the 
                    system.  Typically corresponds directly to a value 
                    labeled 'Cur' in the SERVER ALTERNATE STATUS 
                    display."
                ::= { resEntry 2 }


            resWorst OBJECT-TYPE
                SYNTAX Gauge
                ACCESS read-only
                STATUS mandatory
                DESCRIPTION
                    "The highest or lowest value of resCurrent since 
                    system initialization.  Typically corresponds 
                    directly to a value labeled 'High' or 'Low' in the 
                    SERVER ALTERNATE STATUS display."
                ::= { resEntry 3 }


            resAdminMaximum OBJECT-TYPE
                SYNTAX INTEGER
                ACCESS read-write
                STATUS mandatory
                DESCRIPTION
                    "The desired maximum possible number of resources in 
                    the system.  In many cases, ACCESS to this object 
                    for a particular resType is read-only.  Typically 
                    corresponds directly to a value labeled 'Max' in the 
                    SERVER ALTERNATE STATUS display for desired, 
                    administrative values.  When the desired change 
                    takes effect is implementation specific, ranging 
                    from immediately to the next system 
                    initialization."
                ::= { resEntry 4 }


            resLacks OBJECT-TYPE
                SYNTAX Counter
                ACCESS read-only
                STATUS mandatory
                DESCRIPTION
                    "The number of times since system initialization 
                    that the system could not obtain the resource 
                    because none were available.  Typically corresponds 
                    directly to a value labeled 'Failure' in the SERVER 
                    ALTERNATE STATUS display.

                    If such failures do not apply to the particular 
                    resource, such as 'cpuPercent', the agent returns 
                    zero for this object."
                ::= { resEntry 5 }


            resLackTime OBJECT-TYPE
                SYNTAX DateTime
                ACCESS read-only
                STATUS mandatory
                DESCRIPTION
                    "The local system date and time when resLack last 
                    increased.  Typically corresponds directly to a 
                    value labeled 'Last Occurred' in the SERVER 
                    ALTERNATE STATUS display.

                    If such failures do not apply to the particular 
                    resource, such as 'cpuPercent', the agent returns 
                    all zeroes (unknown) for this object."
            ::= { resEntry 6 }


            resOperMaximum OBJECT-TYPE
                SYNTAX INTEGER
                ACCESS read-only
                STATUS mandatory
                DESCRIPTION
                    "The current maximum possible number of resources in 
                    the system.  Typically corresponds directly to a 
                    value labeled 'Max' in the SERVER ALTERNATE STATUS 
                    display for current operational values.  This value 
                    is based on current or previous value of 
                    resAdminMaximum."
                ::= { resEntry 7 }

            -- the Feature table

            featTable OBJECT-TYPE
                SYNTAX SEQUENCE OF FeatEntry
                ACCESS not-accessible
                STATUS mandatory
                DESCRIPTION
                    "A list of feature entries.  The number of entries 
                    is given by the value of sysFeatureNumber."
                ::= { xSystem 33 }


            featEntry OBJECT-TYPE
                SYNTAX FeatEntry
                ACCESS not-accessible
                STATUS mandatory
                DESCRIPTION
                    "Status values for a system feature."
                INDEX { featType }
                ::= { featTable 1 }

            FeatEntry ::=
                SEQUENCE {
                    featType
                        INTEGER,
                    featStatus
                        INTEGER
                }

            featType OBJECT-TYPE
                SYNTAX INTEGER { help(1), snmp(2), xremote(3),
                                 tn3270(4), menu(5), multisessions(6),
                                 lat(7), eventLog(8),
                                 internetSecurity(9), slip(10),
                                 scriptServer(11), kerberos(12),
                                 telnet(13), rlogin(14) }
                ACCESS read-only
                STATUS mandatory
                DESCRIPTION
                    "Identification of a feature type.  Corresponds to a 
                    SERVER feature keyword."
                ::= { featEntry 1 }


            featStatus OBJECT-TYPE
                SYNTAX INTEGER { disabled(1), enabled(2) }
                ACCESS read-write
                STATUS mandatory
                DESCRIPTION
                    "The status of the feature as of the next system 
                    initialization.  Corresponds to the presence of the 
                    feature's lable following the label 'Enabled 
                    Feature(s): in the UNIT display."
                ::= { featEntry 2 }

            -- the Boot Control group
            -- The Boot Control group contains parameters to control
            -- how a system loads and dumps its runtime software and
            -- parameters.  Typically these parameters are kept for
            -- and used by system initialization firmware.
            -- This group is mandatory for systems that offer runtime
            -- control of these parameters, and omitted in systems
            -- that do not.

            bootControl OBJECT IDENTIFIER ::= { xSystem 34 }


            bootControlLoadInternetFile OBJECT-TYPE
                SYNTAX DisplayString (SIZE (0..64))
                ACCESS read-write
                STATUS mandatory
                DESCRIPTION
                    "The filename to request when loading an image via 
                    TFTP.  Corresponds directly to SERVER INTERNET LOAD 
                    FILE and the value labeled 'Internet Load File:' in 
                    the SERVER BOOT CHARACTERISTICS display."
                ::= { bootControl 1 }


            bootControlLoadInternetServer OBJECT-TYPE
                SYNTAX IpAddress
                ACCESS read-write
                STATUS mandatory
                DESCRIPTION
                    "The internet address of the server to use when 
                    loading an image via TFTP.  Corresponds directly to 
                    SERVER INTERNET LOAD HOST and the value labeled 
                    'Internet Load Host:' in the SERVER BOOT 
                    CHARACTERISTICS display."
                ::= { bootControl 2 }


            bootControlLoadInternetGateway OBJECT-TYPE
                SYNTAX IpAddress
                ACCESS read-write
                STATUS mandatory
                DESCRIPTION
                    "The internet address of the gateway to use when 
                    loading an image via TFTP.  Corresponds directly to 
                    SERVER INTERNET LOAD GATEWAY and the value labeled 
                    'Internet Load Gateway:' in the SERVER BOOT 
                    CHARACTERISTICS display."
                ::= { bootControl 3 }


            bootControlLoadBootpTftp OBJECT-TYPE
                SYNTAX INTEGER { disabled(1), enabled(2) }
                ACCESS read-write
                STATUS mandatory
                DESCRIPTION
                    "Control for loading via the combination of BOOTP 
                    and TFTP.  Corresponds to SERVER LOAD PROTOCOL 
                    BOOTPTFTP and the presence of 'BOOTP/TFTP/' 
                    following the label 'Load Protocols Enabled:' in the 
                    SERVER BOOT CHARACTERISTICS display."
                ::= { bootControl 4 }


            bootControlLoadTftpDirect OBJECT-TYPE
                SYNTAX INTEGER { disabled(1), enabled(2) }
                ACCESS read-write
                STATUS mandatory
                DESCRIPTION
                    "Control for loading via directed TFTP.  Corresponds 
                    to SERVER LOAD PROTOCOL TFTPDIRECT and the presence 
                    of 'TFTPDIRECT' following the label 'Load Protocols 
                    Enabled:' in the SERVER BOOT CHARACTERISTICS 
                    display."
                ::= { bootControl 5 }


            bootControlLoadLocal OBJECT-TYPE
                SYNTAX INTEGER { disabled(1), enabled(2) }
                ACCESS read-write
                STATUS mandatory
                DESCRIPTION
                    "Control for loading from a local medium.  
                    Corresponds to SERVER LOAD PROTOCOL LOCAL and the 
                    presence of 'LOCAL' following the label 'Load 
                    Protocols Enabled:' in the SERVER BOOT 
                    CHARACTERISTICS display."
                ::= { bootControl 6 }


            bootControlLoadMop OBJECT-TYPE
                SYNTAX INTEGER { disabled(1), enabled(2) }
                ACCESS read-write
                STATUS mandatory
                DESCRIPTION
                    "Control for loading via DEC MOP.  Corresponds to 
                    SERVER LOAD PROTOCOL MOP and the presence of 'MOP' 
                    following the label 'Load Protocols Enabled:' in the 
                    SERVER BOOT CHARACTERISTICS display."
                ::= { bootControl 7 }


            bootControlLoadProprietary OBJECT-TYPE
                SYNTAX INTEGER { disabled(1), enabled(2) }
                ACCESS read-write
                STATUS mandatory
                DESCRIPTION
                    "Control for loading via Xyplex-proprietary extended 
                    MOP.  Corresponds to SERVER LOAD PROTOCOL 
                    PROPRIETARY and the presence of 'Proprietary' 
                    following the label 'Load Protocols Enabled:' in the 
                    SERVER BOOT CHARACTERISTICS display."
                ::= { bootControl 8 }


            bootControlLoadRarpTftp OBJECT-TYPE
                SYNTAX INTEGER { disabled(1), enabled(2) }
                ACCESS read-write
                STATUS mandatory
                DESCRIPTION
                    "Control for loading via the combination of RARP and 
                    TFTP.  Corresponds to SERVER LOAD PROTOCOL RARPTFTP 
                    and the presence of 'RARP/TFTP' following the label 
                    'Load Protocols Enabled:' in the SERVER BOOT 
                    CHARACTERISTICS display."
                ::= { bootControl 9 }


            bootControlDumpBootpTftp OBJECT-TYPE
                SYNTAX INTEGER { disabled(1), enabled(2) }
                ACCESS read-write
                STATUS mandatory
                DESCRIPTION
                    "Control for dumping via the combination of BOOTP 
                    and TFTP.  Corresponds to SERVER DUMP PROTOCOL 
                    BOOTPTFTP and the presence of 'BOOTP/TFTP' following 
                    the label 'Dump Protocols Enabled:' in the SERVER 
                    BOOT CHARACTERISTICS display."
                ::= { bootControl 10 }


            bootControlDumpLocal OBJECT-TYPE
                SYNTAX INTEGER { disabled(1), enabled(2) }
                ACCESS read-write
                STATUS mandatory
                DESCRIPTION
                    "Control for dumping to a local medium.  Corresponds 
                    to SERVER DUMP PROTOCOL LOCAL and the presence of 
                    'Local' following the label 'Dump Protocols 
                    Enabled:' in the SERVER BOOT CHARACTERISTICS 
                    display."
                ::= { bootControl 11 }


            bootControlDumpMop OBJECT-TYPE
                SYNTAX INTEGER { disabled(1), enabled(2) }
                ACCESS read-write
                STATUS mandatory
                DESCRIPTION
                    "Control for dumping via DEC MOP.  Corresponds to 
                    SERVER DUMP PROTOCOL MOP and the presence of 'MOP' 
                    following the label 'Dump Protocols Enabled:' in the 
                    SERVER BOOT CHARACTERISTICS display."
                ::= { bootControl 12 }


            bootControlDumpProprietary OBJECT-TYPE
                SYNTAX INTEGER { disabled(1), enabled(2) }
                ACCESS read-write
                STATUS mandatory
                DESCRIPTION
                    "Control for dumping via Xyplex-proprietary extended 
                    MOP.  Corresponds to SERVER DUMP PROTOCOL 
                    PROPRIETARY and the presence of 'Proprietary' 
                    following the label 'Dump Protocols Enabled:' in the 
                    SERVER BOOT CHARACTERISTICS display."
                ::= { bootControl 13 }


            bootControlDumpRarpTftp OBJECT-TYPE
                SYNTAX INTEGER { disabled(1), enabled(2) }
                ACCESS read-write
                STATUS mandatory
                DESCRIPTION
                    "Control for dumping via the combination of RARP and 
                    TFTP.  Corresponds to SERVER DUMP PROTOCOL RARPTFTP 
                    and the presence of 'RARP/TFTP' following the label 
                    'Dump Protocols Enabled:' in the SERVER BOOT 
                    CHARACTERISTICS display."
                ::= { bootControl 14 }


            bootControlParamBootpTftp OBJECT-TYPE
                SYNTAX INTEGER { disabled(1), enabled(2) }
                ACCESS read-write
                STATUS mandatory
                DESCRIPTION
                    "Control for loading parameters via the combination 
                    of BOOTP and TFTP.  Corresponds to SERVER PARAMETER 
                    PROTOCOL MOP and the presence of 'BOOTP/TFTP' 
                    following the label 'Parameter Protocols Enabled:' 
                    in the SERVER BOOT CHARACTERISTICS display."
                ::= { bootControl 15 }


            bootControlParamLocal OBJECT-TYPE
                SYNTAX INTEGER { disabled(1), enabled(2) }
                ACCESS read-write
                STATUS mandatory
                DESCRIPTION
                    "Control for loading parameters from a local medium.  
                    Corresponds to SERVER PARAMETER PROTOCOL LOCAL and 
                    the presence of 'LOCAL' following the label 
                    'Parameter Protocols Enabled:' in the SERVER BOOT 
                    CHARACTERISTICS display."
                ::= { bootControl 16 }


            bootControlParamMop OBJECT-TYPE
                SYNTAX INTEGER { disabled(1), enabled(2) }
                ACCESS read-write
                STATUS mandatory
                DESCRIPTION
                    "Control for loading parameters via DEC MOP.  
                    Corresponds to SERVER PARAMETER PROTOCOL MOP and the 
                    presence of 'MOP' following the label 'Parameter 
                    Protocols Enabled:' in the SERVER BOOT 
                    CHARACTERISTICS display."
                ::= { bootControl 17 }


            bootControlParamProprietary OBJECT-TYPE
                SYNTAX INTEGER { disabled(1), enabled(2) }
                ACCESS read-write
                STATUS mandatory
                DESCRIPTION
                    "Control for loading parameters via 
                    Xyplex-proprietary extended MOP.  Corresponds to 
                    SERVER PARAMETER PROTOCOL PROPRIETARY and the 
                    presence of 'Proprietary' following the label 
                    'Parameter Protocols Enabled:' in the SERVER BOOT 
                    CHARACTERISTICS display."
                ::= { bootControl 18 }


            bootControlParamRarpTftp OBJECT-TYPE
                SYNTAX INTEGER { disabled(1), enabled(2) }
                ACCESS read-write
                STATUS mandatory
                DESCRIPTION
                    "Control for loading parameters via the combination 
                    of RARP and TFTP.  Corresponds to SERVER PARAMETER 
                    PROTOCOL RARPTFTP and the presence of 'RARP/TFTP' 
                    following the label 'Parameter Protocols Enabled:' 
                    in the SERVER BOOT CHARACTERISTICS display."
                ::= { bootControl 19 }

            -- the System group, basic parameters continued

            sysInstalledMemory OBJECT-TYPE
                SYNTAX Gauge
                ACCESS read-only
                STATUS mandatory
                DESCRIPTION
                    "The total number of bytes of main memory installed 
                    in the system.  Corresponds directly to the value 
                    labeled 'Installed' on the SERVER ALTERNATE STATUS 
                    display."
                ::= { xSystem 35 }

            -- System traps
            resourceLack TRAP-TYPE
                ENTERPRISE xSystem
                VARIABLES {
                    resType
                    }
                DESCRIPTION
                    "Indication that the system incremented the 
                    corresponding value of resLacks."
                ::= 1

-- End of Xyplex System MIB

-- Xyplex Bootstrap Clients MIB

            bootClient      OBJECT IDENTIFIER ::= { xyplex 12 }

            --  This MIB module uses the extended OBJECT-TYPE macro as
            --  defined in [9]
            --  this is the MIB module for clients of Xyplex bootstrap
            --  service
            -- the Bootstrap Client group
            -- Implementation of this group is mandatory for all Xyplex
            -- systems that use the Xyplex bootstrap service

            bootClientStatus OBJECT-TYPE
                SYNTAX DisplayString (SIZE (0..1400))
                ACCESS read-only
                STATUS mandatory
                DESCRIPTION
                    "The overall status of the bootstrapping operation, 
                    including, for example, what is presently happening 
                    and error information."
                ::= { bootClient 1 }


-- End Xyplex Bootstrap Clients MIB


-- Xyplex Bootstrap Servers MIB


            bootServer      OBJECT IDENTIFIER ::= { xyplex 6 }

            -- Xyplex Character subgroups

            bsBasic         OBJECT IDENTIFIER ::= { bootServer 1 }


            dump            OBJECT IDENTIFIER ::= { bootServer 2 }


            load            OBJECT IDENTIFIER ::= { bootServer 3 }


            param           OBJECT IDENTIFIER ::= { bootServer 4 }

            --  This MIB module uses the extended OBJECT-TYPE macro as
            --  defined in [9]
            --  this is the MIB module for providers of Xyplex
            --  bootstrap service
            -- the Bootstrap Server Basic group
            -- Implementation of this group is mandatory for all Xyplex
            -- systems that provide the Xyplex bootstrap service

            basicLogLimit OBJECT-TYPE
                SYNTAX INTEGER (1..100)
                ACCESS read-write
                STATUS mandatory
                DESCRIPTION
                    "Maximum allowed number of kilobytes for recording 
                    events.  Corresponds directly to MANAGER LOG FILE 
                    SIZE and the value labeled 'Log File Size:' in the 
                    MANAGER CHARACTERISTICS display."
                ::= { bsBasic 1 }


            basicActiveLimit OBJECT-TYPE
                SYNTAX INTEGER (0..32)
                ACCESS read-write
                STATUS mandatory
                DESCRIPTION
                    "Maximum allowed number of simultaneous service 
                    dialogs.  Corresponds directly to MANAGER 
                    SIMULTANEOUS and the value labeled 'Maximum 
                    simultaneous requests:' in the MANAGER 
                    CHARACTERISTICS display."
                ::= { bsBasic 2 }


            basicActiveNumber OBJECT-TYPE
                SYNTAX Gauge
                ACCESS read-only
                STATUS mandatory
                DESCRIPTION
                    "Number of active service dialogs.  Corresponds 
                    indirectly to the list of active clients in the 
                    MANAGER STATUS display."
                ::= { bsBasic 3 }


            basicClientNumber OBJECT-TYPE
                SYNTAX Gauge
                ACCESS read-only
                STATUS mandatory
                DESCRIPTION
                    "Number of defined clients.  Corresponds indirectly 
                    to the list of defined clients in the MANAGER LOCAL, 
                    MANAGER GLOBAL, and MANAGER NODE displays."
                ::= { bsBasic 4 }


            basicOffersSent OBJECT-TYPE
                SYNTAX Counter
                ACCESS read-only
                STATUS mandatory
                DESCRIPTION
                    "Total number of service offers sent in response to 
                    client requests.  Corresponds directly to the value 
                    labeled 'Total service offers sent:' in the MANAGER 
                    STATUS display."
                ::= { bsBasic 5 }


            basicEventTotal OBJECT-TYPE
                SYNTAX Gauge
                ACCESS read-only
                STATUS mandatory
                DESCRIPTION
                    "Total number of events that have been written to 
                    the event log since it was last purged.  This may be 
                    less than the number currently in the log.  
                    Corresponds directly to the value labeled 'Total 
                    Messages Logged:' in the MANAGER EVENTS display."
                ::= { bsBasic 6 }


            basicEventPurge OBJECT-TYPE
                SYNTAX INTEGER { ready(1), execute(2) }
                ACCESS read-write
                STATUS mandatory
                DESCRIPTION
                    "Control to cause emptying the event log.  In 
                    response to a get-request or get-next-request, the 
                    agent always returns 'ready' for this value.  
                    Setting the value to 'ready' has no effect.  Setting 
                    it to 'execute' causes the event log to immediately 
                    become empty.  Corresponds directly to the PURGE 
                    MANAGER LOG FILE command."
                ::= { bsBasic 7 }

            -- The Active table

            activeTable OBJECT-TYPE
                SYNTAX SEQUENCE OF ActiveEntry
                ACCESS not-accessible
                STATUS mandatory
                DESCRIPTION
                    "A list of active client dialog entries.  The number 
                    of entries is given by basicActiveNumber."
                ::= { bsBasic 8 }


            activeEntry OBJECT-TYPE
                SYNTAX ActiveEntry
                ACCESS not-accessible
                STATUS mandatory
                DESCRIPTION
                    "Parameter values for an active client dialog 
                    entry."
                INDEX { activeIdentificationType, activeIdentification }
                ::= { activeTable 1 }

            ActiveEntry ::=
                SEQUENCE {
                    activeIdentificationType
                        AddressType,
                    activeIdentification
                        OCTET STRING,
                    activeFunction
                        INTEGER,
                    activeSoftwareVersionType
                        INTEGER,
                    activeSoftwareVersion
                        OCTET STRING,
                    activeParameterVersion
                        INTEGER,
                    activeCurrentSequence
                        INTEGER,
                    activeBytesRemaining
                        INTEGER,
                    activeFile
                        DisplayString,
                    activeStatus
                        INTEGER,
                    activeState
                        INTEGER
                }

            activeIdentificationType OBJECT-TYPE
                SYNTAX AddressType
                ACCESS read-only
                STATUS mandatory
                DESCRIPTION
                    "The type of identification value in 
                    activeIdentification.  Corresponds indirectly to the 
                    value labeled 'EthernetAddress' in the MANAGER 
                    STATUS display."
                ::= { activeEntry 1 }


            activeIdentification OBJECT-TYPE
                SYNTAX OCTET STRING (SIZE (1..6))
                ACCESS read-only
                STATUS mandatory
                DESCRIPTION
                    "Identification of the active partner.  Corresponds 
                    directly to the value labeled 'EthernetAddress' in 
                    the MANAGER STATUS display."
                ::= { activeEntry 2 }


            activeFunction OBJECT-TYPE
                SYNTAX INTEGER { parameterStore(1), load(2), dump(3),
                                 imageUpdate(4) }
                ACCESS read-only
                STATUS mandatory
                DESCRIPTION
                    "The function the server is performing with the 
                    partner.  Corresponds directly to the value labeled 
                    'Function' in the MANAGER STATUS display."
                ::= { activeEntry 3 }


            activeSoftwareVersionType OBJECT-TYPE
                SYNTAX INTEGER { alpha(1), beta(2),
                                 production(3), special(4),
                                 notApplicable(5) }
                ACCESS read-only
                STATUS mandatory
                DESCRIPTION
                    "If activeFunction is 'load', the software version 
                    being sent to the client, otherwise 'notApplicable'.  
                    Corresponds to the letter in the software version 
                    labeled 'Version' in the MANAGER STATUS display.

                    alpha         'A':   alpha test
            beta          'B':   beta test
                    production    null:  normal, production software
                    special       'S':   special, custom software
                    "
                ::= { activeEntry 4 }


            activeSoftwareVersion OBJECT-TYPE
                SYNTAX OCTET STRING (SIZE (0..4))
                ACCESS read-only
                STATUS mandatory
                DESCRIPTION
                    "If activeFunction is 'load', the 4-byte software 
                    version being sent to the client, otherwise zero 
                    length.  In order, the octets contain major version, 
                    minor version, ECO, and pre-release number.  
                    Corresponds to the numbers in the software version 
                    labeled 'Version' in the MANAGER STATUS display.

                    For example, the version display for 
                    activeSoftwareVersionType 'production' and 
                    activeSoftwareVersion '2.2.0.0' is 'V2.2'.

                    The version display for activeSoftwareVersionType 
                    'beta' and activeSoftwareVersion '3.1.0.4' is 
                    'V3.1B4'."
                ::= { activeEntry 5 }


            activeParameterVersion OBJECT-TYPE
                SYNTAX INTEGER
                ACCESS read-only
                STATUS mandatory
                DESCRIPTION
                    "If activeFunction is 'parameterStore', the 
                    parameter version being stored by the client, 
                    otherwise zero.  Corresponds directly to the value 
                    labeled 'Version' in the MANAGER STATUS display."
                ::= { activeEntry 6 }


            activeCurrentSequence OBJECT-TYPE
                SYNTAX INTEGER
                ACCESS read-only
                STATUS mandatory
                DESCRIPTION
                    "The current dialog sequence number.  Corresponds 
                    directly to the value labeled 'Seq' in the MANAGER 
                    STATUS display."
                ::= { activeEntry 7 }


            activeBytesRemaining OBJECT-TYPE
                SYNTAX INTEGER
                ACCESS read-only
                STATUS mandatory
                DESCRIPTION
                    "The number of bytes remaining to be transferred in 
                    the dialog.  Corresponds directly to the value 
                    labeled 'Left' in the MANAGER STATUS display."
                ::= { activeEntry 8 }


            activeFile OBJECT-TYPE
                SYNTAX DisplayString (SIZE (1..16))
                ACCESS read-only
                STATUS mandatory
                DESCRIPTION
                    "The name of the file being used in the dialog.  
                    Corresponds directly to the value labeled 'File' in 
                    the MANAGER STATUS display."
                ::= { activeEntry 9 }


            activeStatus OBJECT-TYPE
                SYNTAX INTEGER { none(1),
                                 fileTooLarge(2),
                                 notImageFile(3),
                                 notExecutableFile(4),
                                 badFileData(5),
                                 deviceWriteProtected(6),
                                 operationTimeout(7),
                                 remoteFileNotFound(8),
                                 remoteFileAccessViolation(9),
                                 protocolError(10),
                                 fileSystemError(11),
                                 temporaryResourceConflict(12),
                                 success(13) }
                ACCESS read-only
                STATUS mandatory
                DESCRIPTION
                    "The final status of the most recent attempt to get 
                    an image.  Corresponds directly to the value labeled 
                    'Get Status:' in the DEVICE STATUS display."
                ::= { activeEntry 10 }


            activeState OBJECT-TYPE
                SYNTAX INTEGER { idle(1),
                                 internal1(2),
                                 internal2(3),
                                 openPartner(4),
                                 openFile(5),
                                 receivePartner(6),
                                 writeFile(7),
                                 closePartner(8),
                                 closeFile(9),
                                 cleanup(10),
                                 done(11),
                                 error(12) }
                ACCESS read-only
                STATUS mandatory
                DESCRIPTION
                    "The dynamic state of an active attempt to get an 
                    image.  Corresponds directly to the value labeled 
                    'Get State:' in the DEVICE STATUS display."
                ::= { activeEntry 11 }

            -- The Client table

            clientTable OBJECT-TYPE
                SYNTAX SEQUENCE OF ClientEntry
                ACCESS not-accessible
                STATUS mandatory
                DESCRIPTION
                    "A list of client data base entries.  The number of 
                    entries is given by basicClientNumber."
                ::= { bsBasic 9 }


            clientEntry OBJECT-TYPE
                SYNTAX ClientEntry
                ACCESS not-accessible
                STATUS mandatory
                DESCRIPTION
                    "Parameter values for a client data base entry."
                INDEX { clientIdentificationType, clientIdentification }
                ::= { clientTable 1 }

            ClientEntry ::=
                SEQUENCE {
                    clientIdentificationType
                        AddressType,
                    clientIdentification
                        OCTET STRING,
                    clientEntryStatus
                        INTEGER,
                    clientName
                        DisplayString,
                    clientLoadFile
                        DisplayString,
                    clientDiagnosticFile
                        DisplayString,
                    clientLoadService
                        INTEGER,
                    clientDumpService
                        INTEGER
                }

            clientIdentificationType OBJECT-TYPE
                SYNTAX AddressType
                ACCESS read-write
                STATUS mandatory
                DESCRIPTION
                    "The type of identification value in 
                    clientIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 1 }


            clientIdentification OBJECT-TYPE
                SYNTAX OCTET STRING (SIZE (1..6))
                ACCESS read-write
                STATUS mandatory
                DESCRIPTION
                    "Identification of the client, either a hardware 
                    type or an Ethernet address, depending on 
                    clientIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { clientEntry 2 }


            clientEntryStatus OBJECT-TYPE
                SYNTAX INTEGER { invalid(1), valid(2) }
                ACCESS read-write
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { clientEntry 3 }


            clientName OBJECT-TYPE
                SYNTAX DisplayString (SIZE (0..16))
                ACCESS read-write
                STATUS mandatory
                DESCRIPTION
                    "A name that may be used to identify the client.  
                    Corresponds directly to the value labeled 'Name' in 
                    the MANAGER NODE display."
                DEFVAL { "" }
                ::= { clientEntry 4 }


            clientLoadFile OBJECT-TYPE
                SYNTAX DisplayString (SIZE (0..16))
                ACCESS read-write
                STATUS mandatory
                DESCRIPTION
                    "The file with the client's load image.  Corresponds 
                    directly to the value labeled 'Load File' in the 
                    MANAGER LOCAL, MANAGER GLOBAL, and MANAGER NODE 
                    displays."
                DEFVAL { "" }
                ::= { clientEntry 5 }


            clientDiagnosticFile OBJECT-TYPE
                SYNTAX DisplayString (SIZE (0..16))
                ACCESS read-write
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { clientEntry 6 }


            clientLoadService OBJECT-TYPE
                SYNTAX INTEGER { disabled(1), enabled(2) }
                ACCESS read-write
                STATUS mandatory
                DESCRIPTION
                    "Control for allowing load service for the client.  
                    Corresponds directly to the value labeled 'Load' in 
                    the MANAGER LOCAL, MANAGER GLOBAL, and MANAGER NODE 
                    displays."
                DEFVAL { enabled }
                ::= { clientEntry 7 }


            clientDumpService OBJECT-TYPE
                SYNTAX INTEGER { disabled(1), enabled(2) }
                ACCESS read-write
                STATUS mandatory
                DESCRIPTION
                    "Control for allowing dump service for the client.  
                    Corresponds directly to the value labeled 'Dump' in 
                    the MANAGER LOCAL, MANAGER GLOBAL, and MANAGER NODE 
                    displays."
                DEFVAL { disabled }
                ::= { clientEntry 8 }

            -- The Named Client table
            -- This table is strict subset of the Client table, being
            -- the same information in the same form with client name
            -- as the table index instead of client identification.
            -- It does not contain clients that have no name.

            namedTable OBJECT-TYPE
                SYNTAX SEQUENCE OF NamedEntry
                ACCESS not-accessible
                STATUS mandatory
                DESCRIPTION
                    "A list of named client data base entries.  The 
                    number of entries is given by basicClientNumber."
                ::= { bsBasic 10 }


            namedEntry OBJECT-TYPE
                SYNTAX NamedEntry
                ACCESS not-accessible
                STATUS mandatory
                DESCRIPTION
                    "Parameter values for a named client data base 
                    entry."
                INDEX { namedName }
                ::= { namedTable 1 }

            NamedEntry ::=
                SEQUENCE {
                    namedIdentificationType
                        AddressType,
                    namedIdentification
                        OCTET STRING,
                    namedEntryStatus
                        INTEGER,
                    namedName
                        DisplayString,
                    namedLoadFile
                        DisplayString,
                    namedDiagnosticFile
                        DisplayString,
                    namedLoadService
                        INTEGER,
                    namedDumpService
                        INTEGER
                }

            namedIdentificationType OBJECT-TYPE
                SYNTAX AddressType
                ACCESS read-write
                STATUS mandatory
                DESCRIPTION
                    "The type of identification value in 
                    namedIdentification.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 1 }


            namedIdentification OBJECT-TYPE
                SYNTAX OCTET STRING (SIZE (1..6))
                ACCESS read-write
                STATUS mandatory
                DESCRIPTION
                    "Identification of the client, either a hardware 
                    type or an Ethernet address, depending on 
                    namedIdentificationType.  Corresponds directly to 
                    MANAGER NODE, MANAGER GLOBAL, and MANAGER LOCAL, and  
                    the value labeled 'Ethernet Address' in the MANAGER 
                    NODE display or 'Ethernet Address', 'Device', and 
                    'Global Devices' or 'Local Devices' in the MANAGER 
                    GLOBAL and LOCAL displays."
                ::= { namedEntry 2 }


            namedEntryStatus OBJECT-TYPE
                SYNTAX INTEGER { invalid(1), valid(2) }
                ACCESS read-write
                STATUS mandatory
                DESCRIPTION
                    "The status of the entry.  Set to 'invalid' to 
                    remove the entry, which corresponds directly to the 
                    PURGE LOCAL, PURGE GLOBAL, and PURGE NODE commands.  
                    Actual removal of the entry is implementation 
                    specific."
                DEFVAL { valid }
                ::= { namedEntry 3 }


            namedName OBJECT-TYPE
                SYNTAX DisplayString (SIZE (0..16))
                ACCESS read-write
                STATUS mandatory
                DESCRIPTION
                    "A name that may be used to identify the client.  
                    Corresponds directly to the value labeled 'Name' in 
                    the MANAGER NODE display."
--                DEFVAL { "" }
                ::= { namedEntry 4 }


            namedLoadFile OBJECT-TYPE
                SYNTAX DisplayString (SIZE (0..16))
                ACCESS read-write
                STATUS mandatory
                DESCRIPTION
                    "The file with the client's load image.  Corresponds 
                    directly to the value labeled 'Load File' in the 
                    MANAGER LOCAL, MANAGER GLOBAL, and MANAGER NODE 
                    displays."
                DEFVAL { "" }
                ::= { namedEntry 5 }


            namedDiagnosticFile OBJECT-TYPE
                SYNTAX DisplayString (SIZE (0..16))
                ACCESS read-write
                STATUS mandatory
                DESCRIPTION
                    "The file with the client's diagnostic test image.  
                    Corresponds directly to the value labeled 'Diag 
                    File' in the MANAGER LOCAL, MANAGER GLOBAL, and 
                    MANAGER NODE displays."
                DEFVAL { "" }
                ::= { namedEntry 6 }


            namedLoadService OBJECT-TYPE
                SYNTAX INTEGER { disabled(1), enabled(2) }
                ACCESS read-write
                STATUS mandatory
                DESCRIPTION
                    "Control for allowing load service for the client.  
                    Corresponds directly to the value labeled 'Load' in 
                    the MANAGER LOCAL, MANAGER GLOBAL, and MANAGER NODE 
                    displays."
                DEFVAL { enabled }
                ::= { namedEntry 7 }


            namedDumpService OBJECT-TYPE
                SYNTAX INTEGER { disabled(1), enabled(2) }
                ACCESS read-write
                STATUS mandatory
                DESCRIPTION
                    "Control for allowing dump service for the client.  
                    Corresponds directly to the value labeled 'Dump' in 
                    the MANAGER LOCAL, MANAGER GLOBAL, and MANAGER NODE 
                    displays."
                DEFVAL { disabled }
                ::= { namedEntry 8 }

            -- The Event table

            eventTable OBJECT-TYPE
                SYNTAX SEQUENCE OF EventEntry
                ACCESS not-accessible
                STATUS mandatory
                DESCRIPTION
                    "A list of event entries.  The number of entries is 
                    given by basicEventNumber."
                ::= { bsBasic 11 }


            eventEntry OBJECT-TYPE
                SYNTAX EventEntry
                ACCESS not-accessible
                STATUS mandatory
                DESCRIPTION
                    "Parameter values for a event entry."
                INDEX { eventIndex }
                ::= { eventTable 1 }

            EventEntry ::=
                SEQUENCE {
                    eventIndex
                        INTEGER,
                    eventText
                        DisplayString
                }

            eventIndex OBJECT-TYPE
                SYNTAX INTEGER
                ACCESS read-only
                STATUS mandatory
                DESCRIPTION
                    "In identification number for an event.  The value 1 
                    indicates the oldest event in the file, with 
                    subsequent numbers indicating sequential events.  
                    The event text for a given number may change as a 
                    circular event log wraps over its beginning.  
                    Corresponds directly to the relative position of an 
                    event in the MANAGER EVENTS display."
                ::= { eventEntry 1 }


            eventText OBJECT-TYPE
                SYNTAX DisplayString (SIZE (1..255))
                ACCESS read-only
                STATUS mandatory
                DESCRIPTION
                    "The text of the event, including date, time and 
                    other information.  Corresponds directly to the 
                    individual event text in the MANAGER EVENTS 
                    display."
                ::= { eventEntry 2 }

            -- The Device table

            basicDeviceNumber OBJECT-TYPE
                SYNTAX INTEGER
                ACCESS read-only
                STATUS mandatory
                DESCRIPTION
                    "The system's number of mass-storage devices."
                ::= { bsBasic 12 }


            deviceTable OBJECT-TYPE
                SYNTAX SEQUENCE OF DeviceEntry
                ACCESS not-accessible
                STATUS mandatory
                DESCRIPTION
                    "A list of device entries.  The number of entries is 
                    given by basicDeviceNumber."
                ::= { bsBasic 13 }


            deviceEntry OBJECT-TYPE
                SYNTAX DeviceEntry
                ACCESS not-accessible
                STATUS mandatory
                DESCRIPTION
                    "Parameter values for a device entry."
                INDEX { deviceIndex }
                ::= { deviceTable 1 }

            DeviceEntry ::=
                SEQUENCE {
                    deviceIndex
                        INTEGER,
                    deviceName
                        DisplayString,
                    deviceDescr
                        DisplayString,
                    deviceOperation
                        INTEGER,
                    deviceFormat
                        INTEGER,
                    deviceProtection
                        INTEGER,
                    deviceFormatMedium
                        INTEGER,
                    deviceGetFile
                        INTEGER,
                    deviceGetFileHostIdentificationType
                        AddressType,
                    deviceGetFileHostIdentification
                        OCTET STRING,
                    deviceGetFileName
                        DisplayString
                }

            deviceIndex OBJECT-TYPE
                SYNTAX INTEGER
                ACCESS read-only
                STATUS mandatory
                DESCRIPTION
                    "In identification number for a device, in the range 
                    1 to basicDeviceNumber"
                ::= { deviceEntry 1 }


            deviceName OBJECT-TYPE
                SYNTAX DisplayString (SIZE (0..16))
                ACCESS read-only
                STATUS mandatory
                DESCRIPTION
                    "A name by which the device is known in other 
                    displays, such as 'C1' or 'D2'."
                ::= { deviceEntry 2 }


            deviceDescr OBJECT-TYPE
                SYNTAX DisplayString (SIZE (0..80))
                ACCESS read-only
                STATUS mandatory
                DESCRIPTION
                    "Details of the device type, including, for example, 
                    size, manufacturer, Flash versus RAM, and such.  
                    Corresponds directly to the value labeled 'Device 
                    Type: in the MANAGER DEVICE STATUS display."
                ::= { deviceEntry 3 }


            deviceOperation OBJECT-TYPE
                SYNTAX INTEGER { read(1), write(2), format(3), idle(4) }
                ACCESS read-only
                STATUS mandatory
                DESCRIPTION
                    "Current operational state of the device.  
                    Corresponds directly the value labeled 'Device 
                    Operation:' in the MANAGER DEVICE STATUS display."
                ::= { deviceEntry 4 }


            deviceFormat OBJECT-TYPE
                SYNTAX INTEGER { unformatted(1), formatted(2),
                                 unknown(3) }
                ACCESS read-only
                STATUS mandatory
                DESCRIPTION
                    "Formatting status of the device.  Corresponds 
                    directly the presence of one of the value labels 
                    under the label 'Device Status:' in the MANAGER 
                    DEVICE STATUS display."
                ::= { deviceEntry 5 }


            deviceProtection OBJECT-TYPE
                SYNTAX INTEGER { write-enabled(1), write-protected(2),
                                 unknown(3) }
                ACCESS read-only
                STATUS mandatory
                DESCRIPTION
                    "Write-protect status of the device.  Corresponds 
                    directly the presence of one of the value labels 
                    under the label 'Device Status:' in the MANAGER 
                    DEVICE STATUS display."
                ::= { deviceEntry 6 }


            deviceFormatMedium OBJECT-TYPE
                SYNTAX INTEGER { ready(1), execute(2) }
                ACCESS read-write
                STATUS mandatory
                DESCRIPTION
                    "Control to cause formatting of the medium in the 
                    device.  In response to a get-request or 
                    get-next-request, the agent always returns 'ready' 
                    for this value.  Setting the value to 'ready' has no 
                    effect.  Setting it to 'execute' causes the device 
                    to be formatted.  Corresponds directly to the FORMAT 
                    DEVICE command."
                ::= { deviceEntry 7 }


            deviceGetFile OBJECT-TYPE
                SYNTAX INTEGER { ready(1), execute(2) }
                ACCESS read-write
                STATUS mandatory
                DESCRIPTION
                    "Control to cause getting a file to the device from 
                    a remote host system.  In response to a get-request 
                    or get-next-request, the agent always returns 
                    'ready' for this value.  Setting the value to 
                    'ready' has no effect.  Setting it to 'execute' 
                    causes the get to be attempted.  Corresponds 
                    directly to the GET DEVICE command.

                    When set to 'execute', the objects 
                    deviceGetFileHostIdentificationType, 
                    deviceGetFileHostIdentification, and 
                    deviceGetFileName must be somewhere in the same set 
                    request message."
                ::= { deviceEntry 8 }


            deviceGetFileHostIdentificationType OBJECT-TYPE
                SYNTAX AddressType
                ACCESS read-write
                STATUS mandatory
                DESCRIPTION
                    "The type of identification value in 
                    deviceIdentification.  Corresponds indirectly to 
                    ADDRESS in the GET DEVICE command.

                    This object may not be set outside the context of 
                    setting deviceGetFile to 'execute'.  In response to 
                    a get-request or get-next-request, the value of this 
                    object is 'undefined'."
                ::= { deviceEntry 9 }


            deviceGetFileHostIdentification OBJECT-TYPE
                SYNTAX OCTET STRING (SIZE (1..6))
                ACCESS read-write
                STATUS mandatory
                DESCRIPTION
                    "Identification of the host to get the file from, 
                    with type depending on deviceIdentificationType.  
                    Corresponds directly to ADDRESS in the GET DEVICE 
                    command.

                    This object may not be set outside the context of 
                    setting deviceGetFile to 'execute'.  In response to 
                    a get-request or get-next-request, the value of this 
                    object is zero length."
                ::= { deviceEntry 10 }


            deviceGetFileName OBJECT-TYPE
                SYNTAX DisplayString (SIZE (1..64))
                ACCESS read-write
                STATUS mandatory
                DESCRIPTION
                    "The name of the file to get.  Corresponds directly 
                    to LOAD FILE in the GET DEVICE command.

                    This object may not be set outside the context of 
                    setting deviceGetFile to 'execute'.  In response to 
                    a get-request or get-next-request, the value of this 
                    object is zero length."
                ::= { deviceEntry 11 }

            -- the Bootstrap Server Dump group
            -- Implementation of this group is mandatory for all Xyplex
            -- systems that provide the Xyplex bootstrap dump service

            dumpService OBJECT-TYPE
                SYNTAX INTEGER { disabled(1), enabled(2) }
                ACCESS read-write
                STATUS mandatory
                DESCRIPTION
                    "Control for allowing dump service for any client.  
                    Corresponds directly to DUMP and the value labeled 
                    'Dump:' in the MANAGER CHARACTERISTICS display."
                ::= { dump 1 }


            dumpDrive OBJECT-TYPE
                SYNTAX INTEGER (1..2)
                ACCESS read-write
                STATUS mandatory
                DESCRIPTION
                    "Identification number of the disk drive where dumps 
                    are stored.  Corresponds directly to DUMP DRIVE and 
                    the value labeled 'Dump Drive:' in the MANAGER 
                    CHARACTERISTICS display."
                ::= { dump 2 }


            dumpMerit OBJECT-TYPE
                SYNTAX INTEGER (0..15)
                ACCESS read-write
                STATUS mandatory
                DESCRIPTION
                    "Relative preference for this dump server over 
                    others.  Corresponds directly to DUMP MERIT and the 
                    value labeled 'Dump Merit:' in the MANAGER 
                    CHARACTERISTICS display."
                ::= { dump 3 }


            dumpSize OBJECT-TYPE
                SYNTAX INTEGER { small(1), full(2) }
                ACCESS read-write
                STATUS mandatory
                DESCRIPTION
                    "Type of dump file to keep.  Corresponds directly to 
                    DUMP SIZE and the value labeled 'Dump Size:' in the 
                    MANAGER CHARACTERISTICS display."
                ::= { dump 4 }


            dumpCompleted OBJECT-TYPE
                SYNTAX Counter
                ACCESS read-only
                STATUS mandatory
                DESCRIPTION
                    "The number of dumps completed since system 
                    initialization.  Corresponds directly to the value 
                    labeled 'Dump Operations Completed:' in the MANAGER 
                    STATUS display."
                ::= { dump 5 }


            dumpActive OBJECT-TYPE
                SYNTAX Gauge
                ACCESS read-only
                STATUS mandatory
                DESCRIPTION
                    "The number of dumps in progress.  Corresponds 
                    directly to the value labeled 'Currently Dumping:' 
                    in the MANAGER STATUS display."
                ::= { dump 6 }


            dumpFileNumber OBJECT-TYPE
                SYNTAX Gauge
                ACCESS read-only
                STATUS mandatory
                DESCRIPTION
                    "The number of dump files currently stored.  
                    Corresponds directly to the value labeled 'Network 
                    dump files' and 'files' in the MANAGER FILES 
                    display."
                ::= { dump 7 }

            -- The Dump File table

            dumpFileTable OBJECT-TYPE
                SYNTAX SEQUENCE OF DumpFileEntry
                ACCESS not-accessible
                STATUS mandatory
                DESCRIPTION
                    "A list of dump file entries.  The number of entries 
                    is given by dumpFileNumber."
                ::= { dump 8 }


            dumpFileEntry OBJECT-TYPE
                SYNTAX DumpFileEntry
                ACCESS not-accessible
                STATUS mandatory
                DESCRIPTION
                    "Parameter values for a dump file entry."
                INDEX { dumpFileIdentificationType,
                        dumpFileIdentification }
                ::= { dumpFileTable 1 }

            DumpFileEntry ::=
                SEQUENCE {
                    dumpFileIdentificationType
                        AddressType,
                    dumpFileIdentification
                        OCTET STRING,
                    dumpFileEntryStatus
                        INTEGER,
                    dumpFileCreation
                        DateTime,
                    dumpFileSize
                        INTEGER
                }

            dumpFileIdentificationType OBJECT-TYPE
                SYNTAX AddressType
                ACCESS read-only
                STATUS mandatory
                DESCRIPTION
                    "The type of identification value in 
                    dumpFileIdentification.  Corresponds indirectly to a 
                    file name part in the section labeled 'Network dump 
                    files' in the MANAGER FILES display."
                ::= { dumpFileEntry 1 }


            dumpFileIdentification OBJECT-TYPE
                SYNTAX OCTET STRING (SIZE (1..6))
                ACCESS read-only
                STATUS mandatory
                DESCRIPTION
                    "Identification of the dump file, an Ethernet 
                    address, as indicated by dumpFileIdentificationType.  
                    Corresponds indirectly to a file name part in the 
                    section labeled 'Network dump files' in the MANAGER 
                    FILES display."
                ::= { dumpFileEntry 2 }


            dumpFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER DUMP FILES command.  Actual 
                    removal of the entry is implementation specific."
                ::= { dumpFileEntry 3 }


            dumpFileCreation OBJECT-TYPE
                SYNTAX DateTime
                ACCESS read-only
                STATUS mandatory
                DESCRIPTION
                    "The time the dump file was created.  Corresponds 
                    directly to a date and time in the section labeled 
                    'Network dump files' in the MANAGER FILES display."
                ::= { dumpFileEntry 4 }


            dumpFileSize OBJECT-TYPE
                SYNTAX INTEGER
                ACCESS read-only
                STATUS mandatory
                DESCRIPTION
                    "The number of bytes stored in the dump file.  
                    Corresponds directly to the value labeled 'bytes' in 
                    the section labeled 'Network dump files' in the 
                    MANAGER FILES display."
                ::= { dumpFileEntry 5 }

            -- the Bootstrap Server Load group
            -- Implementation of this group is mandatory for all Xyplex
            -- systems that provide the Xyplex bootstrap load service

            loadService OBJECT-TYPE
                SYNTAX INTEGER { disabled(1), enabled(2) }
                ACCESS read-write
                STATUS mandatory
                DESCRIPTION
                    "Control for allowing load service for any client.  
                    Corresponds directly to LOAD and the value labeled 
                    'Load:' in the MANAGER CHARACTERISTICS display."
                ::= { load 1 }


            loadMerit OBJECT-TYPE
                SYNTAX INTEGER (0..15)
                ACCESS read-write
                STATUS mandatory
                DESCRIPTION
                    "Relative preference for this load server over 
                    others.  Corresponds directly to LOAD MERIT and the 
                    value labeled 'Load Merit:' in the MANAGER 
                    CHARACTERISTICS display."
                ::= { load 2 }


            loadCompleted OBJECT-TYPE
                SYNTAX Counter
                ACCESS read-only
                STATUS mandatory
                DESCRIPTION
                    "The number of loads completed since system 
                    initialization.  Corresponds directly to the value 
                    labeled 'Load Operations Completed:' in the MANAGER 
                    STATUS display."
                ::= { load 3 }


            loadActive OBJECT-TYPE
                SYNTAX Gauge
                ACCESS read-only
                STATUS mandatory
                DESCRIPTION
                    "The number of loads in progress.  Corresponds 
                    directly to the value labeled 'Currently Loading:' 
                    in the MANAGER STATUS display."
                ::= { load 4 }


            loadFileNumber OBJECT-TYPE
                SYNTAX Gauge
                ACCESS read-only
                STATUS mandatory
                DESCRIPTION
                    "The number of load files currently stored.  
                    Corresponds directly to the value labeled 'Load 
                    image files' and 'files' in the MANAGER FILES 
                    display."
                ::= { load 5 }

            -- The Load File table

            loadFileTable OBJECT-TYPE
                SYNTAX SEQUENCE OF LoadFileEntry
                ACCESS not-accessible
                STATUS mandatory
                DESCRIPTION
                    "A list of load file entries.  The number of entries 
                    is given by loadFileNumber."
                ::= { load 6 }


            loadFileEntry OBJECT-TYPE
                SYNTAX LoadFileEntry
                ACCESS not-accessible
                STATUS mandatory
                DESCRIPTION
                    "Parameter values for a load file entry."
                INDEX { loadFileName }
                ::= { loadFileTable 1 }

            LoadFileEntry ::=
                SEQUENCE {
                    loadFileName
                        DisplayString,
                    loadFileCreation
                        DateTime,
                    loadFileSize
                        INTEGER,
                    loadFileSoftwareVersionType
                        INTEGER,
                    loadFileSoftwareVersion
                        OCTET STRING
                }

            loadFileName OBJECT-TYPE
                SYNTAX DisplayString (SIZE (1..16))
                ACCESS read-only
                STATUS mandatory
                DESCRIPTION
                    "The name of a load file.  Corresponds directly to a 
                    file name part in the section labeled 'Load image 
                    files' in the MANAGER FILES display."
                ::= { loadFileEntry 1 }


            loadFileCreation OBJECT-TYPE
                SYNTAX DateTime
                ACCESS read-only
                STATUS mandatory
                DESCRIPTION
                    "The time the load file was created.  Corresponds 
                    directly to a date and time in the section labeled 
                    'Load image files' in the MANAGER FILES display."
                ::= { loadFileEntry 2 }


            loadFileSize OBJECT-TYPE
                SYNTAX INTEGER
                ACCESS read-only
                STATUS mandatory
                DESCRIPTION
                    "The number of bytes stored in the load file.  
                    Corresponds directly to the value labeled 'bytes' in 
                    the section labeled 'Load image files' in the 
                    MANAGER FILES display."
                ::= { loadFileEntry 3 }


            loadFileSoftwareVersionType OBJECT-TYPE
                SYNTAX INTEGER { alpha(1), beta(2),
                                 production(3), special(4) }
                ACCESS read-only
                STATUS mandatory
                DESCRIPTION
                    "The software version type of the image in the load 
                    file.  Corresponds directly to a software version in 
                    the section labeled 'Load image files' in the 
                    MANAGER FILES display.

                    alpha         'A':   alpha test
                    beta          'B':   beta test
                    production    null:  normal, production software
                    special       'S':   special, custom software
                    "
                ::= { loadFileEntry 4 }


            loadFileSoftwareVersion OBJECT-TYPE
                SYNTAX OCTET STRING (SIZE (0..4))
                ACCESS read-only
                STATUS mandatory
                DESCRIPTION
                    "The software version of the image in the load file.  
                    Corresponds directly to a software version in the 
                    section labeled 'Load image files' in the MANAGER 
                    FILES display.
            For example, the version display for 
                    loadFileSoftwareVersionType 'production' and 
                    loadFileSoftwareVersion '2.2.0.0' is 'V2.2'.

                    The version display for loadFileSoftwareVersionType 
                    'beta' and loadFileSoftwareVersion '3.1.0.4' is 
                    'V3.1B4'."
                ::= { loadFileEntry 5 }

            -- the Bootstrap Server Parameter Storage group
            -- Implementation of this group is mandatory for all Xyplex
            -- systems that provide the Xyplex bootstrap parameter
            -- storage service

            paramService OBJECT-TYPE
                SYNTAX INTEGER { disabled(1), enabled(2) }
                ACCESS read-write
                STATUS mandatory
                DESCRIPTION
                    "Control for allowing parameter storage service for 
                    any client.  Corresponds directly to PARAMETER 
                    SERVICE and the value labeled 'Parameter Service:' 
                    in the MANAGER CHARACTERISTICS display."
                ::= { param 1 }


            paramDefaultService OBJECT-TYPE
                SYNTAX INTEGER { disabled(1), enabled(2) }
                ACCESS read-write
                STATUS mandatory
                DESCRIPTION
                    "Control for allowing default parameter loading 
                    service for any client.  Corresponds directly to 
                    PARAMETER DEFAULT SERVICE and the value labeled 
                    'Parameter Default Service:' in the MANAGER 
                    CHARACTERISTICS display."
                ::= { param 2 }


            paramDrive OBJECT-TYPE
                SYNTAX INTEGER (1..2)
                ACCESS read-write
                STATUS mandatory
                DESCRIPTION
                    "Identification number of the disk drive where 
                    parameters are stored.  Corresponds directly to 
                    PARAMETER DRIVE and the value labeled 'Parameter 
                    Drive:' in the MANAGER CHARACTERISTICS display."
                ::= { param 3 }


            paramActive OBJECT-TYPE
                SYNTAX Gauge
                ACCESS read-only
                STATUS mandatory
                DESCRIPTION
                    "The number of params in progress.  Corresponds 
                    directly to the value labeled 'Currently Paraming:' 
                    in the MANAGER STATUS display."
                ::= { param 4 }


            paramStorageActive OBJECT-TYPE
                SYNTAX Gauge
                ACCESS read-only
                STATUS mandatory
                DESCRIPTION
                    "The number of parameter storage operations in 
                    progress.  Corresponds directly to the value labeled 
                    'Currently saving parameters:' in the MANAGER STATUS 
                    display."
                ::= { param 5 }


            paramFileNumber OBJECT-TYPE
                SYNTAX Gauge
                ACCESS read-only
                STATUS mandatory
                DESCRIPTION
                    "The number of parameter files currently stored.  
                    Corresponds directly to the value labeled 'Parameter 
                    files' and 'files' in the MANAGER FILES display."
                ::= { param 6 }

            -- The Param File table

            paramFileTable OBJECT-TYPE
                SYNTAX SEQUENCE OF ParamFileEntry
                ACCESS not-accessible
                STATUS mandatory
                DESCRIPTION
                    "A list of param file entries.  The number of 
                    entries is given by paramFileNumber."
                ::= { param 7 }


            paramFileEntry OBJECT-TYPE
                SYNTAX ParamFileEntry
                ACCESS not-accessible
                STATUS mandatory
                DESCRIPTION
                    "Parameter values for a param file entry."
                INDEX { paramFileIdentificationType,
                        paramFileIdentification }
                ::= { paramFileTable 1 }

            ParamFileEntry ::=
                SEQUENCE {
                    paramFileIdentificationType
                        AddressType,
                    paramFileIdentification
                        OCTET STRING,
                    paramFileEntryStatus
                        INTEGER,
                    paramFileWrite
                        DateTime,
                    paramFileSize
                        INTEGER,
                    paramFileParameterVersion
                        INTEGER
                }

            paramFileIdentificationType OBJECT-TYPE
                SYNTAX AddressType
                ACCESS read-only
                STATUS mandatory
                DESCRIPTION
                    "The type of identification value in 
                    paramFileIdentification.  Corresponds indirectly to 
                    a file name part in the section labeled 'Parameter 
                    files' in the MANAGER FILES display."
                ::= { paramFileEntry 1 }


            paramFileIdentification OBJECT-TYPE
                SYNTAX OCTET STRING (SIZE (1..6))
                ACCESS read-only
                STATUS mandatory
                DESCRIPTION
                    "Identification of the param file, an Ethernet 
                    address, as indicated by 
                    paramFileIdentificationType.  Corresponds indirectly 
                    to a file name part in the section labeled 
                    'Parameter files' in the MANAGER FILES display."
                ::= { paramFileEntry 2 }


            paramFileEntryStatus OBJECT-TYPE
                SYNTAX INTEGER { invalid(1), valid(2) }
                ACCESS read-write
                STATUS mandatory
                DESCRIPTION
                    "The status of the entry.  Set to 'invalid' to 
                    remove the entry, which corresponds indirectly to 
                    the PURGE MANAGER PARAMETER FILES command.  Actual 
                    removal of the entry is implementation specific."
                ::= { paramFileEntry 3 }


            paramFileWrite OBJECT-TYPE
                SYNTAX DateTime
                ACCESS read-only
                STATUS mandatory
                DESCRIPTION
                    "The time the parameter file was last written.  
                    Corresponds directly to a date and time in the 
                    section labeled 'Parameter files' in the MANAGER 
                    FILES display."
                ::= { paramFileEntry 4 }


            paramFileSize OBJECT-TYPE
                SYNTAX INTEGER
                ACCESS read-only
                STATUS mandatory
                DESCRIPTION
                    "The number of bytes stored in the param file.  
                    Corresponds directly to the value labeled 'bytes' in 
                    the section labeled 'Parameter files' in the MANAGER 
                    FILES display."
                ::= { paramFileEntry 5 }


            paramFileParameterVersion OBJECT-TYPE
                SYNTAX INTEGER
                ACCESS read-only
                STATUS mandatory
                DESCRIPTION
                    "The version number of the parameter data in the 
                    file.  Corresponds directly to the value labeled 
                    'ver' in the section labeled 'Parameter files' in 
                    the MANAGER FILES display."
                ::= { paramFileEntry 6 }

-- end of Bootstrap Servers MIB


-- Xyplex Character Stream Devices MIB


            characterDep    OBJECT IDENTIFIER ::= { xyplex 2 }


            character       OBJECT IDENTIFIER ::= { xyplex 13 }

            -- Xyplex Character subgroups

            basic           OBJECT IDENTIFIER ::= { character 1 }


            queue           OBJECT IDENTIFIER ::= { character 2 }


            menu            OBJECT IDENTIFIER ::= { character 3 }


            netLogin        OBJECT IDENTIFIER ::= { character 4 }


            dial            OBJECT IDENTIFIER ::= { character 5 }


            sessionLog      OBJECT IDENTIFIER ::= { character 6 }

            -- This MIB module uses the extended OBJECT-TYPE macro as
            -- defined in [9]
            -- This is a MIB module for all Xyplex systems that
            -- implement physical or logical character stream devices
            -- the Character Basic group
            -- Implementation of this group is mandatory for all Xyplex
            -- systems that implement physical or logical character
            -- stream devices

            basicBroadcast OBJECT-TYPE
                SYNTAX INTEGER { disabled(1), enabled(2) }
                ACCESS read-write
                STATUS mandatory
                DESCRIPTION
                    "Control for user ability to broadcast messages to 
                    other local ports.  Corresponds directly to SERVER 
                    BROADCAST and the presence of the label 'Broadcast' 
                    following the label 'Enabled Characteristics:' in 
                    the SERVER CHARACTERISTICS display."
                ::= { basic 1 }


            basicErrorReport OBJECT-TYPE
                SYNTAX INTEGER { disabled(1), enabled(2) }
                ACCESS read-write
                STATUS mandatory
                DESCRIPTION
                    "Control for server display of an error when the 
                    user gives an unsupported command.  Corresponds 
                    directly to SERVER REPORT ERRORS and the presence of 
                    the label 'Report Errors' following the label 
                    'Enabled Characteristics:' in the SERVER 
                    CHARACTERISTICS display."
                ::= { basic 2 }


            basicLock OBJECT-TYPE
                SYNTAX INTEGER { disabled(1), enabled(2) }
                ACCESS read-write
                STATUS mandatory
                DESCRIPTION
                    "Control for user ability to use a password to 
                    protect a logged in terminal from other users.  
                    Corresponds directly to SERVER LOCK and the presence 
                    of the label 'Lock' following the label 'Enabled 
                    Characteristics:' in the SERVER CHARACTERISTICS 
                    display."
                ::= { basic 3 }


            basicInactivityTimer OBJECT-TYPE
                SYNTAX INTEGER (1..120)
                ACCESS read-write
                STATUS mandatory
                DESCRIPTION
                    "Number of minutes a terminal may remain logged in 
                    with no sessions, no input or output, and no modem 
                    transitions.  Corresponds directly to SERVER 
                    INACTIVITY TIMER and the value labeled 'Inactivity 
                    Timer:' in the SERVER CHARACTERISTICS display."
                ::= { basic 4 }


            basicPasswordRetryLimit OBJECT-TYPE
                SYNTAX INTEGER (0..250)
                ACCESS read-write
                STATUS mandatory
                DESCRIPTION
                    "Number of times the server allows a user to retry 
                    an incorrect password.  Corresponds directly to 
                    SERVER PASSWORD LIMIT and the value labeled 
                    'Password Limit:' in the SERVER CHARACTERISTICS 
                    display."
                ::= { basic 5 }


            basicPrivilegedPassword OBJECT-TYPE
                SYNTAX DisplayString (SIZE (1..16))
                ACCESS read-write
                STATUS mandatory
                DESCRIPTION
                    "The password a user must enter to become 
                    privileged.
                    For security reasons, reading this object always 
                    returns a zero-length value.  Corresponds directly 
                    to SERVER PRIVILEGED PASSWORD."
                ::= { basic 6 }


            basicLoginPassword OBJECT-TYPE
                SYNTAX DisplayString (SIZE (1..16))
                ACCESS read-write
                STATUS mandatory
                DESCRIPTION
                    "The password a user must enter to be given the 
                    opportunity to log in.  For security reasons, 
                    reading this object always returns a zero-length 
                    value. Corresponds directly to SERVER LOGIN 
                    PASSWORD."
                ::= { basic 7 }


            basicLoginPrompt OBJECT-TYPE
                SYNTAX DisplayString (SIZE (1..8))
                ACCESS read-write
                STATUS mandatory
                DESCRIPTION
                    "The text string the server displays to prompt a 
                    user for the login password.  Corresponds directly 
                    to SERVER LOGIN PROMPT."
                ::= { basic 8 }


            basicWelcome OBJECT-TYPE
                SYNTAX DisplayString (SIZE (0..80))
                ACCESS read-write
                STATUS mandatory
                DESCRIPTION
                    "The text string the server displays before 
                    attempting to log in a user.  Corresponds directly 
                    to SERVER WELCOME and the value labeled 'Welcome:' 
                    in the SERVER CHARACTERISTICS display."
                ::= { basic 9 }


            basicActivePorts OBJECT-TYPE
                SYNTAX Gauge
                ACCESS read-only
                STATUS mandatory
                DESCRIPTION
                    "The number of ports with connected sessions or 
                    logged in users.  Corresponds directly to the value 
                    labeled 'Active Ports:' and 'Cur' in the SERVER 
                    STATUS display."
                ::= { basic 10 }


            basicActivePortsHigh OBJECT-TYPE
                SYNTAX Gauge
                ACCESS read-only
                STATUS mandatory
                DESCRIPTION
                    "The highest value of basicActivePorts since system 
                    initialization.  Corresponds directly to the value 
                    labeled 'Active Ports:' and 'High' in the SERVER 
                    STATUS display."
                ::= { basic 11 }


            basicActiveUsers OBJECT-TYPE
                SYNTAX Gauge
                ACCESS read-only
                STATUS mandatory
                DESCRIPTION
                    "The number of logged in users.  Corresponds 
                    directly to the value labeled 'Active Users:' and 
                    'Cur' in the SERVER STATUS display."
                ::= { basic 12 }


            basicActiveUsersHigh OBJECT-TYPE
                SYNTAX Gauge
                ACCESS read-only
                STATUS mandatory
                DESCRIPTION
                    "The highest value of basicActiveUsers since system 
                    initialization.  Corresponds directly to the value 
                    labeled 'Active Users:' and 'High' in the SERVER 
                    STATUS display."
                ::= { basic 13 }


            basicSessions OBJECT-TYPE
                SYNTAX Gauge
                ACCESS read-only
                STATUS mandatory
                DESCRIPTION
                    "The total number of connected sessions.  
                    Corresponds directly to the value labeled 'Connected 
                    Sessions:' and 'Cur' in the SERVER STATUS display."
                ::= { basic 14 }


            basicSessionsHigh OBJECT-TYPE
                SYNTAX Gauge
                ACCESS read-only
                STATUS mandatory
                DESCRIPTION
                    "The highest value of basicSessions since system 
                    initialization.  Corresponds directly to the value 
                    labeled 'Connected Sessions:' and 'High' in the 
                    SERVER STATUS display."
                ::= { basic 15 }


            basicSessionsLimit OBJECT-TYPE
                SYNTAX INTEGER (-1..64)
                ACCESS read-write
                STATUS mandatory
                DESCRIPTION
                    "The maximum total number of sessions that can 
                    simultaneously be connected to the system.  A value 
                    of -1 indicates no limit up to available dynamic 
                    system memory.  Corresponds directly to SERVER 
                    SESSION LIMIT and the value labeled 'Connected 
                    Sessions:' and 'Max' in the SERVER STATUS display."
                ::= { basic 16 }

            -- Additional Basic group parameters follow the port tables
            -- the Basic Port table

            basicPortTable OBJECT-TYPE
                SYNTAX SEQUENCE OF BasicPortEntry
                ACCESS not-accessible
                STATUS mandatory
                DESCRIPTION
                    "A list of basic character port entries."
                ::= { basic 17 }


            basicPortEntry OBJECT-TYPE
                SYNTAX BasicPortEntry
                ACCESS not-accessible
                STATUS mandatory
                DESCRIPTION
                    "Basic parameter values for a port."
                INDEX { basicPortIndex }
                ::= { basicPortTable 1 }

            BasicPortEntry ::=
                SEQUENCE {
                    basicPortIndex
                        INTEGER,
                    basicPortDefaultDestAction
                        INTEGER,
                    basicPortDefaultDestProtocol
                        INTEGER,
                    basicPortDefaultDestName
                        DisplayString,
                    basicPortDefaultDestLATNodeName
                        DisplayString,
                    basicPortDefaultDestLATPortName
                        DisplayString,
                    basicPortAutoConnect
                        INTEGER,
                    basicPortAutoLogin
                        INTEGER,
                    basicPortBroadcast
                        INTEGER,
                    basicPortConnectResume
                        INTEGER,
                    basicPortDialup
                        INTEGER,
                    basicPortIdleTimeout
                        INTEGER,
                    basicPortInactivityLogout
                        INTEGER,
                    basicPortLossNotification
                        INTEGER,
                    basicPortMessageCodes
                        INTEGER,
                    basicPortMultisessions
                        INTEGER,
                    basicPortDefaultUserName
                        DisplayString,
                    basicPortVerification
                        INTEGER,
                    basicPortDefaultProtocol
                        INTEGER,
                    basicPortLogins
                        Counter,
                    basicPortRemoteSessions
                        Counter,
                    basicPortIdleTimeouts
                        Counter,
                    basicPortStatus
                        INTEGER,
                    basicPortLastInCharacter
                        INTEGER,
                    basicPortLastOutCharacter
                        INTEGER,
                    basicPortActiveUserName
                        DisplayString,
                    basicPortDefaultSessionMode
                        INTEGER,
                    basicPortZero
                        INTEGER,
                    basicPortZeroTime
                        TimeTicks
                }

            basicPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { basicPortEntry 1 }


            basicPortDefaultDestAction OBJECT-TYPE
                SYNTAX INTEGER { dedicated(1), preferred(2) }
                ACCESS read-write
                STATUS mandatory
                DESCRIPTION
                    "The action to take relative to 
                    basicPortDefaultDestName.  Corresponds directly to 
                    PORT DEDICATED/PREFERRED SERVICE and the label 
                    'Dedicated/Preferred Service:' in the PORT 
                    CHARACTERISTICS display."
                ::= { basicPortEntry 2 }


            basicPortDefaultDestProtocol OBJECT-TYPE
                SYNTAX INTEGER { lat(1), telnet(2), any(3) }
                ACCESS read-write
                STATUS mandatory
                DESCRIPTION
                    "The session protocol to use with 
                    basicPortDefaultDestName.  Corresponds directly to 
                    LAT/TELNET PORT DEDICATED/PREFERRED SERVICE."
                ::= { basicPortEntry 3 }


            basicPortDefaultDestName OBJECT-TYPE
                SYNTAX DisplayString (SIZE (0..50))
                ACCESS read-write
                STATUS mandatory
                DESCRIPTION
                    "The default name to use in forming a connection 
                    when no other name is specified.  Corresponds 
                    directly to PORT DEDICATED/PREFERRED SERVICE and the 
                    value labeled 'Dedicated/Preferred Service:' in the 
                    PORT CHARACTERISTICS display.  If the value of 
                    basicPortDefaultDestProtocol is 'telnet', an 
                    Internet port number may be included on the end of 
                    the name, delimited with a colon (':').  If the 
                    value of basicPortDefaultDestProtocol is not 
                    'telnet', then the maximum length is 16."
                ::= { basicPortEntry 4 }


            basicPortDefaultDestLATNodeName OBJECT-TYPE
                SYNTAX DisplayString (SIZE (0..16))
                ACCESS read-write
                STATUS mandatory
                DESCRIPTION
                    "A LAT node name to use with 
                    basicPortDefaultDestName.  Corresponds directly to 
                    PORT DEDICATED/PREFERRED SERVICE NODE and the value 
                    labeled 'Node:' following the label 
                    'Dedicated/Preferred Service:' in the PORT 
                    CHARACTERISTICS display.  This object can have a 
                    non- zero-length value only if the value of 
                    basicPortDefaultDestProtocol is 'lat'."
                ::= { basicPortEntry 5 }


            basicPortDefaultDestLATPortName OBJECT-TYPE
                SYNTAX DisplayString (SIZE (0..16))
                ACCESS read-write
                STATUS mandatory
                DESCRIPTION
                    "A LAT port name to use with 
                    basicPortDefaultDestName.  Corresponds directly to 
                    PORT DEDICATED/PREFERRED SERVICE NODE and the value 
                    labeled 'Node:' following the label 
                    'Dedicated/Preferred Service:' in the PORT 
                    CHARACTERISTICS display.  this object can hav a 
                    non-zero-length value only if the value if 
                    basicPortDefaultDestProtocol is 'lat'"
                ::= { basicPortEntry 6 }


            basicPortAutoConnect OBJECT-TYPE
                SYNTAX INTEGER { disabled(1), enabled(2) }
                ACCESS read-write
                STATUS mandatory
                DESCRIPTION
                    "Control for automatic session connection.  
                    Corresponds directly to PORT AUTOCONNECT and the 
                    presence of the label 'Autoconnect' following the 
                    label 'Enabled Characteristics:' in the PORT 
                    CHARACTERISTICS display."
                ::= { basicPortEntry 7 }


            basicPortAutoLogin OBJECT-TYPE
                SYNTAX INTEGER { disabled(1), enabled(2) }
                ACCESS read-write
                STATUS mandatory
                DESCRIPTION
                    "Control for automatic port login.  Corresponds 
                    directly to PORT AUTODEDICATED and the presence of 
                    the label 'Autodedicated' following the label 
                    'Enabled Characteristics:' in the PORT 
                    CHARACTERISTICS display."
                ::= { basicPortEntry 8 }


            basicPortBroadcast OBJECT-TYPE
                SYNTAX INTEGER { disabled(1), enabled(2) }
                ACCESS read-write
                STATUS mandatory
                DESCRIPTION
                    "Control for display of messages sent by users on 
                    other ports.  Corresponds directly to PORT BROADCAST 
                    and the presence of the label 'Broadcast' following 
                    the label 'Enabled Characteristics:' in the PORT 
                    CHARACTERISTICS display."
                ::= { basicPortEntry 9 }


            basicPortConnectResume OBJECT-TYPE
                SYNTAX INTEGER { disabled(1), enabled(2) }
                ACCESS read-write
                STATUS mandatory
                DESCRIPTION
                    "Control for behavior of a connection attempt to a 
                    destination where the port already has a connection.  
                    'disabled' causes a new connection.  'enabled' 
                    causes the existing connection to become the active 
                    connection.  Corresponds directly to PORT 
                    CONNECTRESUME and the presence of the label 
                    'Connectresume' following the label 'Enabled 
                    Characteristics:' in the PORT CHARACTERISTICS 
                    display."
                ::= { basicPortEntry 10 }


            basicPortDialup OBJECT-TYPE
                SYNTAX INTEGER { disabled(1), enabled(2) }
                ACCESS read-write
                STATUS mandatory
                DESCRIPTION
                    "Defines whether the port should be considered as 
                    connected to a dialup line.  'enabled' means that it 
                    is.  Corresponds directly to PORT DIALUP and the 
                    presence of the label 'Dial Up' following the label 
                    'Enabled Characteristics:' in the PORT 
                    CHARACTERISTICS display."
                ::= { basicPortEntry 11 }


            basicPortIdleTimeout OBJECT-TYPE
                SYNTAX INTEGER (-1..255)
                ACCESS read-write
                STATUS mandatory
                DESCRIPTION
                    "The number of minutes the system will allow a 
                    session to have no activity before automatically 
                    disconnecting it.  A value of -1 indicates no 
                    timeout.  Zero is not a valid value.  Corresponds 
                    directly to PORT IDLE TIMEOUT and the value labeled 
                    'Idle Timeout:' in the PORT ALTERNATE 
                    CHARACTERISTICS display."
                ::= { basicPortEntry 12 }


            basicPortInactivityLogout OBJECT-TYPE
                SYNTAX INTEGER { disabled(1), enabled(2) }
                ACCESS read-write
                STATUS mandatory
                DESCRIPTION
                    "Control for the system automatically logging the 
                    port out when it has no sessions, no local activity, 
                    and no modem signal changes for the time period 
                    specified by basicInactivityTimer.  Corresponds 
                    directly to PORT INACTIVITY LOGOUT and the presence 
                    of the label 'Inactivity Logout' following the label 
                    'Enabled Characteristics:' in the PORT 
                    CHARACTERISTICS display."
                ::= { basicPortEntry 13 }


            basicPortLossNotification OBJECT-TYPE
                SYNTAX INTEGER { disabled(1), enabled(2) }
                ACCESS read-write
                STATUS mandatory
                DESCRIPTION
                    "Control for the system sending a Bell character to 
                    the port when it looses an input character due to an 
                    overrun or data error.  Corresponds directly to PORT 
                    LOSS NOTIFICATION and the presence of the label 
                    'Loss Notification' following the label 'Enabled 
                    Characteristics:' in the PORT CHARACTERISTICS 
                    display."
                ::= { basicPortEntry 14 }


            basicPortMessageCodes OBJECT-TYPE
                SYNTAX INTEGER { disabled(1), enabled(2) }
                ACCESS read-write
                STATUS mandatory
                DESCRIPTION
                    "Control for including error numbers in error 
                    messages displayed on the port.  Corresponds 
                    directly to PORT MESSAGE CODES and the presence of 
                    the label 'Message Codes' following the label 
                    'Enabled Characteristics:' in the PORT 
                    CHARACTERISTICS display."
                ::= { basicPortEntry 15 }


            basicPortMultisessions OBJECT-TYPE
                SYNTAX INTEGER { disabled(1), enabled(2) }
                ACCESS read-write
                STATUS mandatory
                DESCRIPTION
                    "Control for running the multisession line protocol 
                    between the port and the locally-connected terminal.  
                    Corresponds directly to PORT MULTISESSIONS and the 
                    presence of the label 'Multisessions' following the 
                    label 'Enabled Characteristics:' in the PORT 
                    CHARACTERISTICS display."
                ::= { basicPortEntry 16 }


            basicPortDefaultUserName OBJECT-TYPE
                SYNTAX DisplayString (SIZE (0..16))
                ACCESS read-write
                STATUS mandatory
                DESCRIPTION
                    "Default user name to use for automatically logging 
                    in the port.  Corresponds directly to PORT USERNAME 
                    and the value labeled 'Port n:' in the PORT 
                    CHARACTERISTICS display."
                ::= { basicPortEntry 17 }


            basicPortVerification OBJECT-TYPE
                SYNTAX INTEGER { disabled(1), enabled(2) }
                ACCESS read-write
                STATUS mandatory
                DESCRIPTION
                    "Control for display of informational messages on 
                    the port when the user connects, disconnects, or 
                    switches a session.  Corresponds directly to PORT 
                    VERIFICATION and the presence of the label 
                    'Verification' following the label 'Enabled 
                    Characteristics:' in the PORT CHARACTERISTICS 
                    display."
                ::= { basicPortEntry 18 }


            basicPortDefaultProtocol OBJECT-TYPE
                SYNTAX INTEGER { lat(1), telnet(2), any(3) }
                ACCESS read-write
                STATUS mandatory
                DESCRIPTION
                    "The session protocol to use when not otherwise 
                    specified.  Corresponds directly to PORT RESOLVE 
                    SERVICE and the value labeled 'Resolve Service:' in 
                    the PORT ALTERNATE CHARACTERISTICS display."
                ::= { basicPortEntry 19 }


            basicPortLogins OBJECT-TYPE
                SYNTAX Counter
                ACCESS read-only
                STATUS mandatory
                DESCRIPTION
                    "The number of logins on the port since system 
                    initialization.  Corresponds directly to the value 
                    labeled 'Local Accesses:' in the PORT COUNTERS 
                    display."
                ::= { basicPortEntry 20 }


            basicPortRemoteSessions OBJECT-TYPE
                SYNTAX Counter
                ACCESS read-only
                STATUS mandatory
                DESCRIPTION
                    "The number of remotely originating sessions to the 
                    port since system initialization.  Corresponds 
                    directly to the value labeled 'Remote Accesses:' in 
                    the PORT COUNTERS display."
                ::= { basicPortEntry 21 }


            basicPortIdleTimeouts OBJECT-TYPE
                SYNTAX Counter
                ACCESS read-only
                STATUS mandatory
                DESCRIPTION
                    "The number of session disconnects due to expiration 
                    of basicPortIdleTimeout.  Corresponds directly to 
                    the value labeled 'Idle Timeouts:' in the PORT 
                    COUNTERS display."
                ::= { basicPortEntry 22 }


            basicPortStatus OBJECT-TYPE
                SYNTAX INTEGER { idle(1), local(2), waitInput(3),
                                 executingCommand(4), connecting(5),
                                 checkConnect(6), waitOutput(7),
                                 connected(8), disconnecting(9),
                                 disconnect(10), suspended(11),
                                 locked(12), permanent(13),
                                 loginWait(14), retryConnect(15),
                                 connectWait(16), logout(17),
                                 login(18), waitSession(19),
                                 reset(20), testServiceWait(21),
                                 testServiceOut(22), 
            connectPassword(23),
                                 waitLogout(24), waitQueue(25),
                                 cancelQueue(26), autobaud(27),
                                 available(28), checkModem(29),
                                 slip(30), signalWait(31),
                                 scriptSearch(32), scriptLoad(33),
                                 scriptRun(34), dialback1(35),
                                 dialback2(36), dialback3(37),
                                 xremote(38) }
                ACCESS read-only
                STATUS mandatory
                DESCRIPTION
                    "The current operational status of the port.  
                    Corresponds directly to the value labeled 'Status:' 
                    in the PORT STATUS display."
                ::= { basicPortEntry 23 }


            basicPortLastInCharacter OBJECT-TYPE
                SYNTAX INTEGER (0..255)
                ACCESS read-only
                STATUS mandatory
                DESCRIPTION
                    "The character that most recently came into the 
                    port.  Corresponds directly to the value labeled 
                    'Last Char Input:' in the PORT STATUS display."
                ::= { basicPortEntry 24 }


            basicPortLastOutCharacter OBJECT-TYPE
                SYNTAX INTEGER (0..255)
                ACCESS read-only
                STATUS mandatory
                DESCRIPTION
                    "The character that most recently went out of the 
                    port.  Corresponds directly to the value labeled 
                    'Last Char Output:' in the PORT STATUS display."
                ::= { basicPortEntry 25 }


            basicPortActiveUserName OBJECT-TYPE
                SYNTAX DisplayString (SIZE (0..16))
                ACCESS read-only
                STATUS mandatory
                DESCRIPTION
                    "The user name currently logged into the port.  
                    Corresponds directly to the value by the port number 
                    and labeled 'Username' in the USERS display."
                ::= { basicPortEntry 26 }


            basicPortDefaultSessionMode OBJECT-TYPE
                SYNTAX INTEGER { interactive(1), binary(2),
                                 binaryWithFlow(3), transparent(4)  }
                ACCESS read-write
                STATUS mandatory
                DESCRIPTION
                    "Data recognition mode when starting a session, 
            with
                    the following meanings:

                    interactive      locally recognize all controls
                    binary           recognize only session protocol
                                     (corresponds to PASSALL)
                    binaryWithFlow   recognize only XON and XOFF
                                     (corresponds to PASTHRU
                    transparent      recognize no data

                    Corresponds directly to PORT DEFAULT SESSION MODE 
            and
                    the value labeled 'Default Session Mode:' in the 
            PORT
                    ALTERNATE CHARACTERISTICS display."
                ::= { basicPortEntry 27 }


            basicPortZero OBJECT-TYPE
                SYNTAX INTEGER  { ready(1), execute(2) }
                ACCESS read-write
                STATUS mandatory
                DESCRIPTION
                    "Control to zero counters for the port.  In response 
                    to a get-request or get-next-request, the agent 
                    always returns 'ready' for this value.  Setting the 
                    value to 'ready' has no effect.  Setting it to 
                    'execute' causes the port's counters to be zeroed.  
                    Corresponds to the ZERO PORT command."
                ::= { basicPortEntry 28 }


            basicPortZeroTime OBJECT-TYPE
                SYNTAX TimeTicks
                ACCESS read-only
                STATUS mandatory
                DESCRIPTION
                    "The number of hundredths of a second since the most 
                    recent zeroing of the port's counters, such as 
                    through execution of basicPortZero.  Corresponds 
                    directly to the value labeled 'Seconds Since 
                    Zeroed:' in the PORT COUNTERS display."
                ::= { basicPortEntry 29 }

            -- the Basic Serial Port table

            basicSerialPortTable OBJECT-TYPE
                SYNTAX SEQUENCE OF BasicSerialPortEntry
                ACCESS not-accessible
                STATUS mandatory
                DESCRIPTION
                    "A list of basic character serial port entries."
                ::= { basic 18 }


            basicSerialPortEntry OBJECT-TYPE
                SYNTAX BasicSerialPortEntry
                ACCESS not-accessible
                STATUS mandatory
                DESCRIPTION
                    "Basic parameter values for a serial port."
                INDEX { basicSerialPortIndex }
                ::= { basicSerialPortTable 1 }

            BasicSerialPortEntry ::=
                SEQUENCE {
                    basicSerialPortIndex
                        INTEGER,
                    basicSerialPortBreak
                        INTEGER,
                    basicSerialPortInterrupts
                        INTEGER,
                    basicSerialPortNoLoss
                        INTEGER,
                    basicSerialPortPause
                        INTEGER,
                    basicSerialPortPrompt
                        DisplayString,
                    basicSerialPortTerminalType
                        INTEGER,
                    basicSerialPortTypeaheadLimit
                        INTEGER,
                    basicSerialPortBackwardSwitch
                        INTEGER,
                    basicSerialPortForwardSwitch
                        INTEGER,
                    basicSerialPortLocalSwitch
                        INTEGER,
                    basicSerialPortModemControl
                        INTEGER,
                    basicSerialPortSignalCheck
                        INTEGER,
                    basicSerialPortDSRLogout
                        INTEGER,
                    basicSerialPortDSRObserve
                        INTEGER,
                    basicSerialPortDCDTimeout
                        INTEGER,
                    basicSerialPortDTRAssert
                        INTEGER,
                    basicSerialPortLimitedCommands
                        INTEGER,
                    basicSerialPortLimitedView
                        INTEGER,
                    basicSerialPortPassword
                        INTEGER,
                    basicSerialPortLineEditor
                        INTEGER,
                    basicSerialPortLineEditorBackspace
                        INTEGER,
                    basicSerialPortLineEditorBeginning
                        INTEGER,
                    basicSerialPortLineEditorCancel
                        INTEGER,
                    basicSerialPortLineEditorDeleteBeginning
                        INTEGER,
                    basicSerialPortLineEditorDeleteLine
                        INTEGER,
                    basicSerialPortLineEditorEnd
                        INTEGER,
                    basicSerialPortLineEditorForward
                        INTEGER,
                    basicSerialPortLineEditorInsertToggle
                        INTEGER,
                    basicSerialPortLineEditorNextLine
                        INTEGER,
                    basicSerialPortLineEditorPreviousLine
                        INTEGER,
                    basicSerialPortLineEditorQuotingCharacter
                        INTEGER,
                    basicSerialPortLineEditorRedisplay
                        INTEGER
                }

            basicSerialPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { basicSerialPortEntry 1 }


            basicSerialPortBreak OBJECT-TYPE
                SYNTAX INTEGER { ignore(1), localSwitch(2),
                                 sendRemote(3) }
                ACCESS read-write
                STATUS mandatory
                DESCRIPTION
                    "Action to take on a BREAK condition from the port.  
                    Corresponds directly to PORT BREAK and the value 
                    labeled 'Break:' in the PORT CHARACTERISTICS 
                    display."
                ::= { basicSerialPortEntry 2 }


            basicSerialPortInterrupts OBJECT-TYPE
                SYNTAX INTEGER { disabled(1), enabled(2) }
                ACCESS read-write
                STATUS mandatory
                DESCRIPTION
                    "Control for recognizing BREAK or local switch to 
                    interrupt a session.  Corresponds directly to PORT 
                    INTERRUPTS and the presence of the label 
                    'Interrupts' following the label 'Enabled 
                    Characteristics:' in the PORT CHARACTERISTICS 
                    display."
                ::= { basicSerialPortEntry 3 }


            basicSerialPortNoLoss OBJECT-TYPE
                SYNTAX INTEGER { disabled(1), enabled(2) }
                ACCESS read-write
                STATUS mandatory
                DESCRIPTION
                    "Control for storing port input locally in 
                    anticipation of session startup.  Corresponds 
                    directly to PORT NOLOSS and the presence of the 
                    label 'Noloss' following the label 'Enabled 
                    Characteristics:' in the PORT CHARACTERISTICS 
                    display."
                ::= { basicSerialPortEntry 4 }


            basicSerialPortPause OBJECT-TYPE
                SYNTAX INTEGER { disabled(1), enabled(2) }
                ACCESS read-write
                STATUS mandatory
                DESCRIPTION
                    "Control for pausing after each screenful of 
                    locally-originated output to the port.  Corresponds 
                    directly to PORT PAUSE and the presence of the label 
                    'Pause' following the label 'Enabled 
                    Characteristics:' in the PORT CHARACTERISTICS 
                    display."
                ::= { basicSerialPortEntry 5 }


            basicSerialPortPrompt OBJECT-TYPE
                SYNTAX DisplayString (SIZE (1..8))
                ACCESS read-write
                STATUS mandatory
                DESCRIPTION
                    "Prompt for the system to use on the port.  
                    Corresponds directly to PORT PROMPT and the value 
                    labeled 'Prompt:' in the PORT ALTERNATE 
                    CHARACTERISTICS display."
                ::= { basicSerialPortEntry 6 }


            basicSerialPortTerminalType OBJECT-TYPE
                SYNTAX INTEGER { ansi(1), hardcopy(2), softcopy(3) }
                ACCESS read-write
                STATUS mandatory
                DESCRIPTION
                    "Type of terminal attached to the port, for 
                    formatting local output.  Corresponds directly to 
                    PORT TYPE and the value labeled 'Type:' in the PORT 
                    CHARACTERISTICS display."
                ::= { basicSerialPortEntry 7 }


            basicSerialPortTypeaheadLimit OBJECT-TYPE
                SYNTAX INTEGER (80..16384)
                ACCESS read-write
                STATUS mandatory
                DESCRIPTION
                    "Maximum number of input characters to hold pending 
                    tranmission on a session.  Corresponds directly to 
                    PORT TYPEAHEAD SIZE and the value labeled 'Typeahead 
                    Size:' in the PORT ALTERNATE CHARACTERISTICS 
                    display."
                ::= { basicSerialPortEntry 8 }


            basicSerialPortBackwardSwitch OBJECT-TYPE
                SYNTAX INTEGER (0..255)
                ACCESS read-write
                STATUS mandatory
                DESCRIPTION
                    "Character input from the character port to cause a 
                    switch to the previous, lower numbered session.  The 
                    value 0 indicates no character has this effect.  
                    Corresponds directly to PORT BACKWARD SWITCH and the 
                    value labeled 'Backwards Switch:' in the PORT 
                    CHARACTERISTICS display."
                ::= { basicSerialPortEntry 9 }


            basicSerialPortForwardSwitch OBJECT-TYPE
                SYNTAX INTEGER (0..255)
                ACCESS read-write
                STATUS mandatory
                DESCRIPTION
                    "Character input from the character port to cause a 
                    switch to the next, higher numbered session.  The 
                    value 0 indicates no character has this effect.  
                    Corresponds directly to PORT FORWARD SWITCH and the 
                    value labeled 'Forwards Switch:' in the PORT 
                    CHARACTERISTICS display."
                ::= { basicSerialPortEntry 10 }


            basicSerialPortLocalSwitch OBJECT-TYPE
                SYNTAX INTEGER (0..255)
                ACCESS read-write
                STATUS mandatory
                DESCRIPTION
                    "Character input from the character port to cause a 
                    switch to local command mode.  The value 0 indicates 
                    no character has this effect.  Corresponds directly 
                    to PORT LOCAL SWITCH and the value labeled 'Local 
                    Switch:' in the PORT CHARACTERISTICS display."
                ::= { basicSerialPortEntry 11 }


            basicSerialPortModemControl OBJECT-TYPE
                SYNTAX INTEGER { disabled(1), enabled(2) }
                ACCESS read-write
                STATUS mandatory
                DESCRIPTION
                    "Control for observing hardware modem control 
                    signals.  Corresponds directly to PORT MODEM CONTROL 
                    and the value labeled 'Modem Control:' in the PORT 
                    CHARACTERISTICS display."
                ::= { basicSerialPortEntry 12 }


            basicSerialPortSignalCheck OBJECT-TYPE
                SYNTAX INTEGER { disabled(1), enabled(2) }
                ACCESS read-write
                STATUS mandatory
                DESCRIPTION
                    "Control for observing DSR and DCD to bound allowing 
                    sessions.  Corresponds directly to PORT SIGNAL CHECK 
                    and the presence of the label 'Signal Check' 
                    following the label 'Enabled Characteristics:' in 
                    the PORT CHARACTERISTICS display."
                ::= { basicSerialPortEntry 13 }


            basicSerialPortDSRLogout OBJECT-TYPE
                SYNTAX INTEGER { disabled(1), enabled(2) }
                ACCESS read-write
                STATUS mandatory
                DESCRIPTION
                    "Control for logging out the port when DCD is 
                    deasserted.  Corresponds directly to PORT DSRLOGOUT 
                    and the presence of the label 'DSRlogout' following 
                    the label 'Enabled Characteristics:' in the PORT 
                    CHARACTERISTICS display."
                ::= { basicSerialPortEntry 14 }


            basicSerialPortDSRObserve OBJECT-TYPE
                SYNTAX INTEGER { disabled(1), enabled(2) }
                ACCESS read-write
                STATUS mandatory
                DESCRIPTION
                    "Control for beginning the login sequence on the 
                    port when DCD is asserted.  Corresponds directly to 
                    PORT DSRWAIT and the presence of the label 'DSRwait' 
                    following the label 'Enabled Characteristics:' in 
                    the PORT CHARACTERISTICS display."
                ::= { basicSerialPortEntry 15 }


            basicSerialPortDCDTimeout OBJECT-TYPE
                SYNTAX INTEGER (0..10000)
                ACCESS read-write
                STATUS mandatory
                DESCRIPTION
                    "The number of milleseconds that DCD may be asserted 
                    before disconnecting the port.  Corresponds directly 
                    to PORT DCD TIMEOUT and the value labeled 'DCD 
                    Timeout:' in the PORT ALTERNATE CHARACTERISTICS 
                    display."
                ::= { basicSerialPortEntry 16 }


            basicSerialPortDTRAssert OBJECT-TYPE
                SYNTAX INTEGER { always(1), onConnectionOrRing(2),
                                 onConnection(3), onRing(4) }
                ACCESS read-write
                STATUS mandatory
                DESCRIPTION
                    "Control when the system asserts DTR on the port.

                    always               unconditional(DISABLED)
                    onConnectionOrRing   connection formed or RING
                                         asserted(ENABLED)
                    onConnection         connection formed
                                         (FORCONNECTION)
                    onRing               RING asserted (FORRING)

                    Corresponds directly to PORT DTRWAIT and the value 
                    labeled 'DTR Wait:' in the PORT ALTERNATE 
                    CHARACTERISTICS display."
                ::= { basicSerialPortEntry 17 }


            basicSerialPortLimitedCommands OBJECT-TYPE
                SYNTAX INTEGER { disabled(1), enabled(2) }
                ACCESS read-write
                STATUS mandatory
                DESCRIPTION
                    "Control for limiting the commands available to the 
                    user on the port.  Corresponds directly to PORT 
                    SECURITY and the presence of the label 'Security' 
                    following the label 'Enabled Characteristics:' in 
                    the PORT CHARACTERISTICS display."
                ::= { basicSerialPortEntry 18 }


            basicSerialPortLimitedView OBJECT-TYPE
                SYNTAX INTEGER { disabled(1), enabled(2) }
                ACCESS read-write
                STATUS mandatory
                DESCRIPTION
                    "Control for restricting what a user may display.  
                    Corresponds directly to PORT LIMITED VIEW and the 
                    presence of the label 'Limited View' following the 
                    label 'Enabled Characteristics:' in the PORT 
                    CHARACTERISTICS display."
                ::= { basicSerialPortEntry 19 }


            basicSerialPortPassword OBJECT-TYPE
                SYNTAX INTEGER { disabled(1), enabled(2) }
                ACCESS read-write
                STATUS mandatory
                DESCRIPTION
                    "Control for requiring the user to supply the login 
                    password to log in on the port.  Corresponds 
                    directly to PORT PASSWORD and the presence of the 
                    label 'Password' following the label 'Enabled 
                    Characteristics:' in the PORT CHARACTERISTICS 
                    display."
                ::= { basicSerialPortEntry 20 }


            basicSerialPortLineEditor OBJECT-TYPE
                SYNTAX INTEGER { disabled(1), enabled(2) }
                ACCESS read-write
                STATUS mandatory
                DESCRIPTION
                    "Control for allowing the user to use local mode 
                    command line editing.  Corresponds directly to PORT 
                    LINE EDITOR and the presence of the label 'Line 
                    Editor' following the label 'Enabled 
                    Characteristics:' in the PORT CHARACTERISTICS 
                    display."
                ::= { basicSerialPortEntry 21 }

            -- Note that the values for the switching and 
            -- line editing characters are mutally exclusive

            basicSerialPortLineEditorBackspace OBJECT-TYPE
                SYNTAX INTEGER (0..255)
                ACCESS read-write
                STATUS mandatory
                DESCRIPTION
                    "Character input from the character port to move the 
                    cursor to the left.  The value 0 indicates no 
                    character has this effect.  Corresponds directly to 
                    PORT LINE EDITOR BACKSPACE and the value labeled 
                    'Backspace Character:' in the PORT ALTERNATE 
                    CHARACTERISTICS display."
                ::= { basicSerialPortEntry 22 }


            basicSerialPortLineEditorBeginning OBJECT-TYPE
                SYNTAX INTEGER (0..255)
                ACCESS read-write
                STATUS mandatory
                DESCRIPTION
                    "Character input from the character port to move the 
                    cursor to the beginning of the line.  The value 0 
                    indicates no character has this effect.  Corresponds 
                    directly to PORT LINE EDITOR BEGINNING and the value 
                    labeled 'Begin Line Character:' in the PORT 
                    ALTERNATE CHARACTERISTICS display."
                ::= { basicSerialPortEntry 23 }


            basicSerialPortLineEditorCancel OBJECT-TYPE
                SYNTAX INTEGER (0..255)
                ACCESS read-write
                STATUS mandatory
                DESCRIPTION
                    "Character input from the character port to cancel 
                    an interactive dialog or delete the current line.  
                    The value 0 indicates no character has this effect.  
                    Corresponds directly to PORT LINE EDITOR CANCEL and 
                    the value labeled 'Cancel Character:' in the PORT 
                    ALTERNATE CHARACTERISTICS display."
                ::= { basicSerialPortEntry 24 }


            basicSerialPortLineEditorDeleteBeginning OBJECT-TYPE
                SYNTAX INTEGER (0..255)
                ACCESS read-write
                STATUS mandatory
                DESCRIPTION
                    "Character input from the character port to delete 
                    the current line from the cursor to the beginning.  
                    The value 0 indicates no character has this effect.  
                    Corresponds directly to PORT LINE EDITOR DELETE 
                    BEGINNING and the value labeled 'Delete Begin 
                    Character:' in the PORT ALTERNATE CHARACTERISTICS 
                    display."
                ::= { basicSerialPortEntry 25 }


            basicSerialPortLineEditorDeleteLine OBJECT-TYPE
                SYNTAX INTEGER (0..255)
                ACCESS read-write
                STATUS mandatory
                DESCRIPTION
                    "Character input from the character port to delete 
                    the current line.  The value 0 indicates no 
                    character has this effect.  Corresponds directly to 
                    PORT LINE EDITOR DELETE LINE and the value labeled 
                    'Delete Line Character:' in the PORT ALTERNATE 
                    CHARACTERISTICS display."
                ::= { basicSerialPortEntry 26 }


            basicSerialPortLineEditorEnd OBJECT-TYPE
                SYNTAX INTEGER (0..255)
                ACCESS read-write
                STATUS mandatory
                DESCRIPTION
                    "Character input from the character port to move the 
                    cursor to the end of the line.  The value 0 
                    indicates no character has this effect.  Corresponds 
                    directly to PORT LINE EDITOR END and the value 
                    labeled 'End of Line Character:' in the PORT 
                    ALTERNATE CHARACTERISTICS display."
                ::= { basicSerialPortEntry 27 }


            basicSerialPortLineEditorForward OBJECT-TYPE
                SYNTAX INTEGER (0..255)
                ACCESS read-write
                STATUS mandatory
                DESCRIPTION
                    "Character input from the character port to move the 
                    cursor to the right.  The value 0 indicates no 
                    character has this effect.  Corresponds directly to 
                    PORT LINE EDITOR FORWARDS and the value labeled 
                    'Forwards Character:' in the PORT ALTERNATE 
                    CHARACTERISTICS display."
                ::= { basicSerialPortEntry 28 }


            basicSerialPortLineEditorInsertToggle OBJECT-TYPE
                SYNTAX INTEGER (0..255)
                ACCESS read-write
                STATUS mandatory
                DESCRIPTION
                    "Character input from the character port to toggle 
                    between insert and overwrite modes.  The value 0 
                    indicates no character has this effect.  Corresponds 
                    directly to PORT LINE EDITOR INSERT TOGGLE and the 
                    value labeled 'Insert Character:' in the PORT 
                    ALTERNATE CHARACTERISTICS display."
                ::= { basicSerialPortEntry 29 }


            basicSerialPortLineEditorNextLine OBJECT-TYPE
                SYNTAX INTEGER (0..255)
                ACCESS read-write
                STATUS mandatory
                DESCRIPTION
                    "Character input from the character port to recall 
                    the next, newer line in the command history.  The 
                    value -1 indicates no character has this effect.  
                    Corresponds directly to PORT LINE EDITOR NEXT LINE 
                    and the value labeled 'Next Line Character:' in the 
                    PORT ALTERNATE CHARACTERISTICS display."
                ::= { basicSerialPortEntry 30 }


            basicSerialPortLineEditorPreviousLine OBJECT-TYPE
                SYNTAX INTEGER (0..255)
                ACCESS read-write
                STATUS mandatory
                DESCRIPTION
                    "Character input from the character port to recall 
                    the previous, older line in the command history.  
                    The value 0 indicates no character has this effect.  
                    Corresponds directly to PORT LINE EDITOR PREVIOUS 
                    LINE and the value labeled 'Previous Line 
                    Character:' in the PORT ALTERNATE CHARACTERISTICS 
                    display."
                ::= { basicSerialPortEntry 31 }


            basicSerialPortLineEditorQuotingCharacter OBJECT-TYPE
                SYNTAX INTEGER (0..255)
                ACCESS read-write
                STATUS mandatory
                DESCRIPTION
                    "Character input from the character port to inhibit 
                    interpretation of the next input character.  The 
                    value 0 indicates no character has this effect.  
                    Corresponds directly to PORT LINE EDITOR QUOTING 
                    CHARACTER and the value labeled 'Quoting Character:' 
                    in the PORT ALTERNATE CHARACTERISTICS display."
                ::= { basicSerialPortEntry 32 }


            basicSerialPortLineEditorRedisplay OBJECT-TYPE
                SYNTAX INTEGER (0..255)
                ACCESS read-write
                STATUS mandatory
                DESCRIPTION
                    "Character input from the character port to 
                    redisplay the current command line.  The value 0 
                    indicates no character has this effect.  Corresponds 
                    directly to PORT LINE EDITOR REDISPLAY CHARACTER and 
                    the value labeled 'Redisplay Character:' in the PORT 
                    ALTERNATE CHARACTERISTICS display."
                ::= { basicSerialPortEntry 33 }

            -- the Basic group continued

            basicConsoleLogoutDisconnect OBJECT-TYPE
                SYNTAX INTEGER { disabled(1), enabled(2) }
                ACCESS read-write
                STATUS mandatory
                DESCRIPTION
                    "Control for automatic session disconnection when a 
                    console port user logs out.  Corresponds directly to 
                    SERVER CONSOLE LOGOUT and the presence of the label 
                    'Console Logout' following the label 'Enabled 
                    Characteristics:' in the SERVER CHARACTERISTICS 
                    display."
                ::= { basic 19 }

            -- the Queue group
            -- Implementation of this group is mandatory for all Xyplex
            -- systems that implement port queueing

            queueLimit OBJECT-TYPE
                SYNTAX INTEGER (-1..100)
                ACCESS read-write
                STATUS mandatory
                DESCRIPTION
                    "The maximum number of entries that can be made in 
                    the Queue table.  The value -1 indicates the imit is 
                    available memory.  Corresponds directly to SERVER 
                    QUEUE LIMIT and the value labeled 'Queue Limit:' in 
                    the SERVER CHARACTERISTICS display."
                ::= { queue 1 }


            queueHigh OBJECT-TYPE
                SYNTAX Gauge
                ACCESS read-only
                STATUS mandatory
                DESCRIPTION
                    "The highest value of queueNumber since system 
                    initialization.  Corresponds directly to the value 
                    labeled 'Queue Entries' and 'High' in the SERVER 
                    STATUS display."
                ::= { queue 2 }


            queueNumber OBJECT-TYPE
                SYNTAX Gauge
                ACCESS read-only
                STATUS mandatory
                DESCRIPTION
                    "The number of entries in the Queue table.  
                    Corresponds directly to the value labeled 'Queue 
                    Entries' and 'Cur' in the SERVER STATUS display."
                ::= { queue 3 }

            -- The Queue table

            queueTable OBJECT-TYPE
                SYNTAX SEQUENCE OF QueueEntry
                ACCESS not-accessible
                STATUS mandatory
                DESCRIPTION
                    "A list of queue entries."
                ::= { queue 4 }


            queueEntry OBJECT-TYPE
                SYNTAX QueueEntry
                ACCESS not-accessible
                STATUS mandatory
                DESCRIPTION
                    "Parameter values for a queue entry."
                INDEX { queueJob }
                ::= { queueTable 1 }

            QueueEntry ::=
                SEQUENCE {
                    queueJob
                        INTEGER,
                    queueStatus
                        INTEGER,
                    queueSourceName
                        DisplayString,
                    queueServiceName
                        DisplayString,
                    queueServicePortIndex
                        INTEGER,
                    queueServicePortName
                        DisplayString
                }

            queueJob OBJECT-TYPE
                SYNTAX INTEGER
                ACCESS read-only
                STATUS mandatory
                DESCRIPTION
                    "The job number of a queued request.  Corresponds 
                    directly to the value labeled 'Entry' in the QUEUE 
                    display."
                ::= { queueEntry 1 }


            queueStatus OBJECT-TYPE
                SYNTAX INTEGER { invalid(1), valid(2) }
                ACCESS read-write
                STATUS mandatory
                DESCRIPTION
                    "The status of a queue entry.  Set to 'invalid' to 
                    remove the entry, which corresponds directly to the 
                    REMOVE QUEUE ENTRY command.  Actual removal of the 
                    entry is implementation specific."
                ::= { queueEntry 2 }


            queueSourceName OBJECT-TYPE
                SYNTAX DisplayString (SIZE (0..50))
                ACCESS read-only
                STATUS mandatory
                DESCRIPTION
                    "The name of the system that originated the queue 
                    entry.  Corresponds directly to the value labeled 
                    'Source Node' in the QUEUE display."
                ::= { queueEntry 3 }


            queueServiceName OBJECT-TYPE
                SYNTAX DisplayString (SIZE (0..16))
                ACCESS read-only
                STATUS mandatory
                DESCRIPTION
                    "The name of the service for which the originator is 
                    waiting.  Corresponds directly to the value labeled 
                    'Service' in the QUEUE display."
                ::= { queueEntry 4 }


            queueServicePortIndex OBJECT-TYPE
                SYNTAX INTEGER
                ACCESS read-only
                STATUS mandatory
                DESCRIPTION
                    "The charPortIndex of the port for which the 
                    originator is waiting, if supplied by the 
                    originator.  As defined in the Character MIB [12].  
                    Corresponds indirectly to the port number part of 
                    the value labeled 'Port Name' in the QUEUE 
                    display."
                ::= { queueEntry 5 }


            queueServicePortName OBJECT-TYPE
                SYNTAX DisplayString (SIZE (0..16))
                ACCESS read-only
                STATUS mandatory
                DESCRIPTION
                    "The name of the port for which the originator is 
                    waiting, if supplied by the originator.  Corresponds 
                    directly to the port name part of the value labeled 
                    'Port Name' in the SERVER QUEUE display."
                ::= { queueEntry 6 }

            -- the Queue Port table

            queuePortTable OBJECT-TYPE
                SYNTAX SEQUENCE OF QueuePortEntry
                ACCESS not-accessible
                STATUS mandatory
                DESCRIPTION
                    "A list of queuing-related character port entries."
                ::= { queue 5 }


            queuePortEntry OBJECT-TYPE
                SYNTAX QueuePortEntry
                ACCESS not-accessible
                STATUS mandatory
                DESCRIPTION
                    "Queuing parameter values for a port."
                INDEX { queuePortIndex }
                ::= { queuePortTable 1 }

            QueuePortEntry ::=
                SEQUENCE {
                    queuePortIndex
                        INTEGER,
                    queuePortQueuing
                        INTEGER
                }

            queuePortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { queuePortEntry 1 }


            queuePortQueuing OBJECT-TYPE
                SYNTAX INTEGER { disabled(1), enabled(2) }
                ACCESS read-write
                STATUS mandatory
                DESCRIPTION
                    "Control for allowing queued requests for using the 
                    port.  Corresponds directly to PORT QUEUING and the 
                    presence of the label 'Queuing' following the label 
                    'Enabled Characteristics:' in the PORT 
                    CHARACTERISTICS display."
                ::= { queuePortEntry 2 }

            -- the Menu group
            -- Implementation of this group is mandatory for all Xyplex
            -- systems that implement user menus

            menuNumber OBJECT-TYPE
                SYNTAX Gauge
                ACCESS read-only
                STATUS mandatory
                DESCRIPTION
                    "The number of entries in the Menu table.  
                    Corresponds indirectly to SERVER MENU display."
                ::= { menu 1 }


            menuContinuePrompt OBJECT-TYPE
                SYNTAX DisplayString (SIZE (0..50))
                ACCESS read-write
                STATUS mandatory
                DESCRIPTION
                    "The text to use when prompting a menu user to press 
                    RETURN to continue. Corresponds directly to SERVER 
                    MENU CONTINUE PROMPT and the value labeled 'Menu 
                    Continue Prompt:' in the SERVER MENU display."
                ::= { menu 2 }


            menuSelectionPrompt OBJECT-TYPE
                SYNTAX DisplayString (SIZE (0..50))
                ACCESS read-write
                STATUS mandatory
                DESCRIPTION
                    "The text to use when prompting a menu user for a 
                    menu selection. Corresponds directly to SERVER MENU 
                    PROMPT and the value labeled 'Menu Prompt:' in the 
                    SERVER MENU display."
                ::= { menu 3 }

            -- The Menu table

            menuTable OBJECT-TYPE
                SYNTAX SEQUENCE OF MenuEntry
                ACCESS not-accessible
                STATUS mandatory
                DESCRIPTION
                    "A list of menu entries."
                ::= { menu 4 }


            menuEntry OBJECT-TYPE
                SYNTAX MenuEntry
                ACCESS not-accessible
                STATUS mandatory
                DESCRIPTION
                    "Parameter values for a menu entry."
                INDEX { menuIndex }
                ::= { menuTable 1 }

            MenuEntry ::=
                SEQUENCE {
                    menuIndex
                        INTEGER,
                    menuStatus
                        INTEGER,
                    menuText
                        DisplayString,
                    menuCommand
                        DisplayString
                }

            menuIndex OBJECT-TYPE
                SYNTAX INTEGER
                ACCESS read-only
                STATUS mandatory
                DESCRIPTION
                    "The index number of a menu entry.  Corresponds 
                    directly to the numbers down the left of the SERVER 
                    MENU display."
                ::= { menuEntry 1 }


            menuStatus OBJECT-TYPE
                SYNTAX INTEGER { invalid(1), valid(2) }
                ACCESS read-write
                STATUS mandatory
                DESCRIPTION
                    "The status of a the entry.  Set to 'invalid' to
                    remove the entry, which corresponds directly to the 
                    CLEAR SERVER MENU command.  Actual removal of the 
                    entry is implementation specific."
                DEFVAL { valid }
                ::= { menuEntry 2 }


            menuText OBJECT-TYPE
                SYNTAX DisplayString (SIZE (0..30))
                ACCESS read-only
                STATUS mandatory
                DESCRIPTION
                    "The text to be displayed in the menu.  Corresponds 
                    directly to the line next to the entry number in the 
                    SERVER MENU display."
                ::= { menuEntry 3 }


            menuCommand OBJECT-TYPE
                SYNTAX DisplayString (SIZE (0..64))
                ACCESS read-only
                STATUS mandatory
                DESCRIPTION
                    "The commands to execute when the user chooses the 
                    menu entry.  Corresponds directly second line 
                    following the entry number in the SERVER MENU 
                    display."
                ::= { menuEntry 4 }

            -- the Menu Port table

            menuPortTable OBJECT-TYPE
                SYNTAX SEQUENCE OF MenuPortEntry
                ACCESS not-accessible
                STATUS mandatory
                DESCRIPTION
                    "A list of menu-related character port entries."
                ::= { menu 5 }


            menuPortEntry OBJECT-TYPE
                SYNTAX MenuPortEntry
                ACCESS not-accessible
                STATUS mandatory
                DESCRIPTION
                    "Menu parameter values for a port."
                INDEX { menuPortIndex }
                ::= { menuPortTable 1 }

            MenuPortEntry ::=
                SEQUENCE {
                    menuPortIndex
                        INTEGER,
                    menuPortMenuStatus
                        INTEGER
                }

            menuPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { menuPortEntry 1 }


            menuPortMenuStatus OBJECT-TYPE
                SYNTAX INTEGER { disabled(1), enabled(2), privileged(3) }
                ACCESS read-write
                STATUS mandatory
                DESCRIPTION
                    "Control for menu operation on the port.  
                    Corresponds indirectly to PORT MENU and PORT 
                    PRIVILEGED MENU and the presence of the labels 
                    'Menu' and 'Privileged Men' following the label 
                    'Enabled Characteristics:' in the PORT 
                    CHARACTERISTICS display."
                ::= { menuPortEntry 2 }

            -- the Network Login group
            -- Implementation of this group is mandatory for all Xyplex
            -- systems that implement network login

            netLoginNumber OBJECT-TYPE
                SYNTAX INTEGER
                ACCESS read-only
                STATUS mandatory
                DESCRIPTION
                    "The number of entries in the Network Login Server 
                    table."
                ::= { netLogin 1 }

            -- The Network Login Server table

            netLoginServerTable OBJECT-TYPE
                SYNTAX SEQUENCE OF NetLoginServerEntry
                ACCESS not-accessible
                STATUS mandatory
                DESCRIPTION
                    "A list of network login server entries."
                ::= { netLogin 2 }


            netLoginServerEntry OBJECT-TYPE
                SYNTAX NetLoginServerEntry
                ACCESS not-accessible
                STATUS mandatory
                DESCRIPTION
                    "Network login parameter values for a server 
                    entry."
                INDEX { netLoginServerName }
                ::= { netLoginServerTable 1 }

            NetLoginServerEntry ::=
                SEQUENCE {
                    netLoginServerName
                        DisplayString,
                    netLoginServerStatus
                        INTEGER,
                    netLoginServerPath
                        DisplayString
                }

            netLoginServerName OBJECT-TYPE
                SYNTAX DisplayString (SIZE (1..50))
                ACCESS read-write
                STATUS mandatory
                DESCRIPTION
                    "The name of a network login server, suitable for 
                    resolution to a network address.  Corresponds 
                    directly to host portion of SERVER SCRIPT SERVER and 
                    the value labeled 'Script Host' in the SERVER 
                    PARAMETER SERVER display."
                ::= { netLoginServerEntry 1 }


            netLoginServerStatus OBJECT-TYPE
                SYNTAX INTEGER { invalid(1), valid(2) }
                ACCESS read-write
                STATUS mandatory
                DESCRIPTION
                 "Status of this entry.  Set to 'invalid'to remove the  entry, which 
            corresponds directly to the CLEAR SERVER     SCRIPT SERVER 
            command.  Acutal removal of the entry   is implementation 
            specific."
                DEFVAL { valid }
                ::= { netLoginServerEntry 2 }


            netLoginServerPath OBJECT-TYPE
                SYNTAX DisplayString (SIZE (0..40))
                ACCESS read-write
                STATUS mandatory
                DESCRIPTION
                    "The full path name to the script file that is 
                    identified by the user name.  Corresponds directly 
                    to path portion of SERVER SCRIPT SERVER and the 
                    value labeled 'Script Path' in the SERVER PARAMETER 
                    SERVER display."
                ::= { netLoginServerEntry 3 }

            -- the Network Login Port table

            netLoginPortTable OBJECT-TYPE
                SYNTAX SEQUENCE OF NetLoginPortEntry
                ACCESS not-accessible
                STATUS mandatory
                DESCRIPTION
                    "A list of network login character port entries."
                ::= { netLogin 3 }


            netLoginPortEntry OBJECT-TYPE
                SYNTAX NetLoginPortEntry
                ACCESS not-accessible
                STATUS mandatory
                DESCRIPTION
                    "Network login parameter values for a port."
                INDEX { netLoginPortIndex }
                ::= { netLoginPortTable 1 }

            NetLoginPortEntry ::=
                SEQUENCE {
                    netLoginPortIndex
                        INTEGER,
                    netLoginPortScriptUse
                        INTEGER,
                    netLoginPortScriptEcho
                        INTEGER,
                    netLoginPortLoaderAddressType
                        INTEGER,
                    netLoginPortLoaderAddress
                        OCTET STRING,
                    netLoginPortLoaderFile
                        DisplayString
                }

            netLoginPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { netLoginPortEntry 1 }


            netLoginPortScriptUse OBJECT-TYPE
                SYNTAX INTEGER { disabled(1), enabled(2), required(3) }
                ACCESS read-write
                STATUS mandatory
                DESCRIPTION
                    "Control for the script action taken when a user 
                    logs in on the port.  Corresponds directly to PORT 
                    SCRIPT LOGIN and the value labeled 'Script Login:' 
                    in the PORT ALTERNATE CHARACTERISTICS display."
                ::= { netLoginPortEntry 2 }


            netLoginPortScriptEcho OBJECT-TYPE
                SYNTAX INTEGER { disabled(1), enabled(2) }
                ACCESS read-write
                STATUS mandatory
                DESCRIPTION
                    "Control for display of script operation on the port 
                    when running a script.  Corresponds directly to PORT 
                    SCRIPT ECHO and the presence of the label 'Script 
                    Echo' following the label 'Enabled Characteristics:' 
                    in the PORT CHARACTERISTICS display."
                ::= { netLoginPortEntry 3 }


            netLoginPortLoaderAddressType OBJECT-TYPE
                SYNTAX AddressType
                ACCESS read-only
                STATUS mandatory
                DESCRIPTION
                    "The type of network address contained in 
                    netLoginPortLoaderAddress.  'unknown' means no 
                    address has been defined.  'other' means no other 
                    type value applies.  'ip' is an Internet IP address.  
                    'ethernet' is an 802.3 MAC address.  Corresponds 
                    indirectly to the address part of the value labeled 
                    'Script Loaded From:' in the PORT STATUS display."
                ::= { netLoginPortEntry 4 }


            netLoginPortLoaderAddress OBJECT-TYPE
                SYNTAX OCTET STRING
                ACCESS read-only
                STATUS mandatory
                DESCRIPTION
                    "The network address of the server that provided the 
                    script for the current port login.  Corresponds 
                    directly the address part of the value labeled 
                    'Script Loaded From:' in the PORT STATUS display."
                ::= { netLoginPortEntry 5 }


            netLoginPortLoaderFile OBJECT-TYPE
                SYNTAX DisplayString
                ACCESS read-only
                STATUS mandatory
                DESCRIPTION
                    "The path and file name of the script used for the 
                    current port login.  Corresponds directly the file 
                    name  part of the value labeled 'Script Loaded 
                    From:' in the PORT STATUS display."
                ::= { netLoginPortEntry 6 }

            -- the Dial group
            -- Implementation of this group is mandatory for all Xyplex
            -- systems that implement automatic dialing

            dialPortTable OBJECT-TYPE
                SYNTAX SEQUENCE OF DialPortEntry
                ACCESS not-accessible
                STATUS mandatory
                DESCRIPTION
                    "A list of dial character port entries."
                ::= { dial 1 }


            dialPortEntry OBJECT-TYPE
                SYNTAX DialPortEntry
                ACCESS not-accessible
                STATUS mandatory
                DESCRIPTION
                    "Dial parameter values for a port."
                INDEX { dialPortIndex }
                ::= { dialPortTable 1 }

            DialPortEntry ::=
                SEQUENCE {
                    dialPortIndex
                        INTEGER,
                    dialPortDialback
                        INTEGER,
                    dialPortDialbackTimeout
                        INTEGER
                }

            dialPortIndex OBJECT-TYPE
                SYNTAX INTEGER
                ACCESS read-only
                STATUS mandatory
                DESCRIPTION
                    "An index value that uniquely identifies a port.  
                    The port identified by a particular value of this 
                    index is the same port as identified by 
                    charPortIndex in the Character MIB [12]."
                ::= { dialPortEntry 1 }


            dialPortDialback OBJECT-TYPE
                SYNTAX INTEGER { disabled(1), enabled(2) }
                ACCESS read-write
                STATUS mandatory
                DESCRIPTION
                    "Control for use of dialback when a user logs in on 
                    the port.  Corresponds directly to PORT DIALBACK and 
                    the presence of the label 'Dialback' following the 
                    label 'Enabled Characteristics:' in the PORT 
                    CHARACTERISTICS display."
                ::= { dialPortEntry 2 }


            dialPortDialbackTimeout OBJECT-TYPE
                SYNTAX INTEGER (5..60)
                ACCESS read-write
                STATUS mandatory
                DESCRIPTION
                    "The number of seconds to wait for remote modem 
                    response when dialing back.  Corresponds directly to 
                    PORT DIALBACK TIMEOUT and the value labeled 
                    'Dialback Timeout:' in the PORT ALTERNATE 
                    CHARACTERISTICS display."
                ::= { dialPortEntry 3 }

            -- the Session Log group
            -- Implementation of this group is mandatory for all Xyplex
            -- systems that implement logging session information

            sessionLogLimit OBJECT-TYPE
                SYNTAX INTEGER (0..1000)
                ACCESS read-write
                STATUS mandatory
                DESCRIPTION
                    "The maximum number of entries allowed in the 
                    Session Log table.  Corresponds directly to SERVER 
                    ACCOUNTING ENTRIES and the value labeled 'Accounting 
                    Entries:' in the SERVER CHARACTERISTICS display."
                ::= { sessionLog 1 }

            -- The Session Log table

            sessionLogTable OBJECT-TYPE
                SYNTAX SEQUENCE OF SessionLogEntry
                ACCESS not-accessible
                STATUS mandatory
                DESCRIPTION
                    "A list of session log entries."
                ::= { sessionLog 2 }


            sessionLogEntry OBJECT-TYPE
                SYNTAX SessionLogEntry
                ACCESS not-accessible
                STATUS mandatory
                DESCRIPTION
                    "Parameter values for a session log entry."
                INDEX { sessionLogIndex }
                ::= { sessionLogTable 1 }

            SessionLogEntry ::=
                SEQUENCE {
                    sessionLogIndex
                        INTEGER,
                    sessionLogConnectionID
                        INTEGER,
                    sessionLogPort
                        INTEGER,
                    sessionLogEvent
                        INTEGER,
                    sessionLogEventDetail
                        INTEGER,
                    sessionLogUserName
                        DisplayString,
                    sessionLogRemoteName
                        DisplayString,
                    sessionLogConnectTime
                        DateTime,
                    sessionLogDisconnectTime
                        DateTime,
                    sessionLogInCharacters
                        Counter,
                    sessionLogOutCharacters
                        Counter
                }

            sessionLogIndex OBJECT-TYPE
                SYNTAX INTEGER
                ACCESS read-only
                STATUS mandatory
                DESCRIPTION
                    "The index number of a session log entry.  
                    Corresponds directly to the order of the displayed 
                    records in the SERVER ACCOUNTING display.  The 
                    maximum value is sessionLogLimit."
                ::= { sessionLogEntry 1 }


            sessionLogConnectionID OBJECT-TYPE
                SYNTAX INTEGER (1..65535)
                ACCESS read-only
                STATUS mandatory
                DESCRIPTION
                    "An indentifying number for records relating to the 
                    same connection, that is, the connect and disconnect 
                    records, either of which can be missing.  
                    Corresponds directly to value labeled 'Entry' the 
                    SERVER ACCOUNTING display."
                ::= { sessionLogEntry 2 }


            sessionLogPort OBJECT-TYPE
                SYNTAX INTEGER
                ACCESS read-only
                STATUS mandatory
                DESCRIPTION
                    "An index value that uniquely identifies the port 
                    where the event took place.  The port identified by 
                    a particular value of this index is the same port as 
                    identified by charPortIndex in the Character MIB 
                    [12].  Corresponds directly to the value labeled 
                    'Port' in the SERVER ACCOUNTING display."
                ::= { sessionLogEntry 3 }


            sessionLogEvent OBJECT-TYPE
                SYNTAX INTEGER { login(1), connectLocal(2),
                                 connectRemote(3), disconnect(4) }
                ACCESS read-only
                STATUS mandatory
                DESCRIPTION
                    "The type of event.  Corresponds directly to the 
                    alphabetic part of the value labeled 'Type' in the 
                    SERVER ACCOUNTING display."
                ::= { sessionLogEntry 4 }


            sessionLogEventDetail OBJECT-TYPE
                SYNTAX INTEGER { none(1), protocolBadCircuit(2),
                                 protocolBadCredits(3),
                                 protocolBadStartOrRun(4),
                                 protocolBadRange(5),
                                 duplicateQueueID(6), noUsers(7),
                                 noServiceResourced(8),
                                 serviceUserDisconnect(9),
                                 serviceUnavailable(10),
                                 serverUserDisconnect(11),
                                 noNodeResources(12),
                                 systemShutdown(13),
                                 nodeUserdisconnect(14),
                                 badCircuitTimer(15),
                                 badServiceClass(16),
                                 badMessageOrSlot(17),
                                 timeout(18), noProgress(19),
                                 serviceNotOnPort(20), noSuchPort(21),
                                 badPassword(22), serviceBusy(23),
                                 noSuchService(24), 
            serviceDisabled(25),
                                 notInQueue(26), noImmeditatAccess(27),
                                 accessDenied(28),
                                 protocolBadSolicit(29),
                                 protocolBadReasonCode(30),
                                 unsupportedTest(31),
                                 domainTooLong(32),
                                 noSuchNode(33),
                                 noSuchServiceOnNode(34),
                                 rejectService(35),
                                 internetConnectDisabled(36) }
                ACCESS read-only
                STATUS mandatory
                DESCRIPTION
                    "The detailed reason for the event.  Corresponds 
                    directly to the numeric part of the value labeled 
                    'Type' in the SERVER ACCOUNTING display."
                ::= { sessionLogEntry 5 }


            sessionLogUserName OBJECT-TYPE
                SYNTAX DisplayString (SIZE (0..16))
                ACCESS read-only
                STATUS mandatory
                DESCRIPTION
                    "The user name logged in on the port when the event 
                    occurred.  Corresponds directly to the value labeled 
                    'Username' in the SERVER ACCOUNTING display."
                ::= { sessionLogEntry 6 }


            sessionLogRemoteName OBJECT-TYPE
                SYNTAX DisplayString (SIZE (0..16))
                ACCESS read-only
                STATUS mandatory
                DESCRIPTION
                    "The name of the session remote partner.  
                    Corresponds directly to the value labeled 
                    'Destination' in the SERVER ACCOUNTING display."
                ::= { sessionLogEntry 7 }


            sessionLogConnectTime OBJECT-TYPE
                SYNTAX DateTime
                ACCESS read-only
                STATUS mandatory
                DESCRIPTION
                    "The date and time that session connection occurred.  
                    Corresponds directly to the value labeled 'Connect 
                    Time' in the SERVER ACCOUNTING display."
                ::= { sessionLogEntry 8 }


            sessionLogDisconnectTime OBJECT-TYPE
                SYNTAX DateTime
                ACCESS read-only
                STATUS mandatory
                DESCRIPTION
                    "The date and time that session disconnection 
                    occurred.  Corresponds directly to the value labeled 
                    'Disconnect Time' in the SERVER ACCOUNTING 
                    display."
                ::= { sessionLogEntry 9 }


            sessionLogInCharacters OBJECT-TYPE
                SYNTAX Counter
                ACCESS read-only
                STATUS mandatory
                DESCRIPTION
                    "The number of characters that came into the port 
                    for the session.  Corresponds directly to the value 
                    labeled 'Bytes In' in the SERVER ACCOUNTING 
                    display."
                ::= { sessionLogEntry 10 }


            sessionLogOutCharacters OBJECT-TYPE
                SYNTAX Counter
                ACCESS read-only
                STATUS mandatory
                DESCRIPTION
                    "The number of characters that went out of the port 
                    for the session.  Corresponds directly to the value 
                    labeled 'Bytes Out' in the SERVER ACCOUNTING 
                    display."
                ::= { sessionLogEntry 11 }

-- end of Xyplex Character Stream Devices MIB


-- Xyplex Decnet MIB


            decnet          OBJECT IDENTIFIER ::= { xyplex 14 }

            -- Xyplex Internet subgroups

            rcp             OBJECT IDENTIFIER ::= { decnet 1 }

            --  This MIB module uses the extended OBJECT-TYPE macro as
            --  defined in [9]
            --  this is the MIB module for Xyplex DECnet
            --  implementations
            -- the Remote Console group
            -- Implementation of this group is mandatory for all Xyplex
            -- systems that implement DECnet remote console (RCP)

            rcpRemoteAddress OBJECT-TYPE
                SYNTAX OCTET STRING (SIZE (0..6))
                ACCESS read-only
                STATUS mandatory
                DESCRIPTION
                    "If a remote console session exists, the Ethernet 
                    address of the remote partner, otherwise zero 
                    length."
                ::= { rcp 1 }

-- end of Xyplex Decnet MIB


-- Xyplex Ethernet Interfaces MIB

            ethernet        OBJECT IDENTIFIER ::= { xyplex 11 }

            --  This MIB module uses the extended OBJECT-TYPE macro as
            --  defined in [9]
            --  this is the MIB module for Xyplex Ethernet interfaces
            -- the Generic Ethernet group
            -- Implementation of this group is mandatory for all Xyplex
            -- systems that have an Ethernet interface

            etherTable OBJECT-TYPE
                SYNTAX SEQUENCE OF EtherEntry
                ACCESS not-accessible
                STATUS mandatory
                DESCRIPTION
                    "A list of generic entries."
                ::= { ethernet 1 }


            etherEntry OBJECT-TYPE
                SYNTAX EtherEntry
                ACCESS not-accessible
                STATUS mandatory
                DESCRIPTION
                    "Generic status and parameter values for an Ethernet 
                    interface."
                INDEX { etherIndex }
                ::= { etherTable 1 }

            EtherEntry ::=
                SEQUENCE {
                    etherIndex
                        INTEGER,
                    etherAlignmentErrors
                        Counter,
                    etherFCSErrors
                        Counter
                }

            etherIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherEntry 1 }


            etherAlignmentErrors OBJECT-TYPE
                SYNTAX Counter
                ACCESS read-only
                STATUS mandatory
                DESCRIPTION
                    "A count of frames received on a particular 
                    interface that are not an integral number of octets 
                    in length and do not pass the FCS check."
                ::= { etherEntry 2 }


            etherFCSErrors OBJECT-TYPE
                SYNTAX Counter
                ACCESS read-only
                STATUS mandatory
                DESCRIPTION
                    "A count of frames received on a particular 
                    interface that are an integral number of octets in 
                    length that do not pass the FCS check."
                ::= { etherEntry 3 }

            -- the Ethernet Transmit group
            -- Implementation of this group is mandatory for all Xyplex
            -- systems that transmit messages on an Ethernet interface

            etherTxTable OBJECT-TYPE
                SYNTAX SEQUENCE OF EtherTxEntry
                ACCESS not-accessible
                STATUS mandatory
                DESCRIPTION
                    "A list of Ethernet transmit entries."
                ::= { ethernet 2 }


            etherTxEntry OBJECT-TYPE
                SYNTAX EtherTxEntry
                ACCESS not-accessible
                STATUS mandatory
                DESCRIPTION
                    "Transmit status and parameter values for an 
                    Ethernet interface."
                INDEX { etherTxIndex }
                ::= { etherTxTable 1 }

            EtherTxEntry ::=
                SEQUENCE {
                    etherTxIndex
                        INTEGER,
                    etherTxSingleCollisionFrames
                        Counter,
                    etherTxMultipleCollisionFrames
                        Counter
                }

            etherTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherTxEntry 1 }


            etherTxSingleCollisionFrames OBJECT-TYPE
                SYNTAX Counter
                ACCESS read-only
                STATUS mandatory
                DESCRIPTION
                    "A count of successfully transmitted frames on a 
                    particular interface for which transmission is 
                    inhibited by exactly one collision.  A frame that is 
                    counted by an instance of this object is also 
                    counted by the corresponding instance of either the 
                    ifOutUcastPkts or ifOutNUcastPkts object and is not 
                    counted by the corresponding instance of the 
                    etherTxMultipleCollisionFrames object."
                ::= { etherTxEntry 2 }


            etherTxMultipleCollisionFrames OBJECT-TYPE
                SYNTAX Counter
                ACCESS read-only
                STATUS mandatory
                DESCRIPTION
                    "A count of successfully transmitted frames on a 
                    particular interface for which transmission is 
                    inhibited by more than one collision.  A frame that 
                    is counted by an instance of this object is also 
                    counted by the corresponding instance of either the 
                    ifOutUcastPkts or ifOutNUcastPkts object and is not 
                    counted by the corresponding instance of the 
                    etherTxSingleCollisionFrames object."
                ::= { etherTxEntry 3 }

            -- the Ethernet Multicast group
            -- Implementation of this group is optional;  it is
            -- appropriate for all Xyplex systems on which the
            -- necessary monitoring is feasible

            etherMulticastTable OBJECT-TYPE
                SYNTAX SEQUENCE OF EtherMulticastEntry
                ACCESS not-accessible
                STATUS mandatory
                DESCRIPTION
                    "A list of etherMulticast entries."
                ::= { ethernet 3 }


            etherMulticastEntry OBJECT-TYPE
                SYNTAX EtherMulticastEntry
                ACCESS not-accessible
                STATUS mandatory
                DESCRIPTION
                    "EtherMulticast status and parameter values for an 
                    Ethernet interface."
                INDEX { etherMulticastIndex }
                ::= { etherMulticastTable 1 }

            EtherMulticastEntry ::=
                SEQUENCE {
                    etherMulticastIndex
                        INTEGER,
                    etherMulticastBytesIn
                        Counter,
                    etherMulticastBytesOut
                        Counter
                }

            etherMulticastIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherMulticastEntry 1 }


            etherMulticastBytesIn OBJECT-TYPE
                SYNTAX Counter
                ACCESS read-only
                STATUS mandatory
                DESCRIPTION
                    "A count of frames successfully received on a 
                    particular interface and for which the destination 
                    address multicast bit was set.  Bytes that are 
                    counted by an instance of this object are also 
                    counted by the corresponding instance of the 
                    ifInOctets object."
                ::= { etherMulticastEntry 2 }


            etherMulticastBytesOut OBJECT-TYPE
                SYNTAX Counter
                ACCESS read-only
                STATUS mandatory
                DESCRIPTION
                    "A count of successfully frames successfully 
                    transmitted on a particular interface and for which 
                    the destination address multicast bit was set.  
                    Bytes that are counted by an instance of this object 
                    are also counted by the corresponding instance of 
                    the ifOutOctets object."
                ::= { etherMulticastEntry 3 }

            -- the Ethernet Extended Transmit group
            -- Implementation of this group is optional;  it is
            -- appropriate for all Xyplex systems on which the
            -- necessary monitoring is feasible

            etherXTxTable OBJECT-TYPE
                SYNTAX SEQUENCE OF EtherXTxEntry
                ACCESS not-accessible
                STATUS mandatory
                DESCRIPTION
                    "A list of Ethernet extended transmit entries."
                ::= { ethernet 4 }


            etherXTxEntry OBJECT-TYPE
                SYNTAX EtherXTxEntry
                ACCESS not-accessible
                STATUS mandatory
                DESCRIPTION
                    "Extended transmit status and parameter values for 
                    an Ethernet interface."
                INDEX { etherXTxIndex }
                ::= { etherXTxTable 1 }

            EtherXTxEntry ::=
                SEQUENCE {
                    etherXTxIndex
                        INTEGER,
                    etherXTxExcessiveCollisions
                        Counter
                }

            etherXTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherXTxEntry 1 }


            etherXTxExcessiveCollisions OBJECT-TYPE
                SYNTAX Counter
                ACCESS read-only
                STATUS mandatory
                DESCRIPTION
                    "A count of frames for which transmission on a 
                    particular interface fails due to excessive 
                    collisions."
                ::= { etherXTxEntry 2 }

-- end of Xyplex Ethernet Interfaces MIB

-- Xyplex Internet Systems MIB with unimplemented groups removed


            xInternetDep    OBJECT IDENTIFIER ::= { xyplex 4 }


            xInternet       OBJECT IDENTIFIER ::= { xyplex 10 }

            -- Xyplex Internet subgroups

            xIp             OBJECT IDENTIFIER ::= { xInternet 1 }


            xTcp            OBJECT IDENTIFIER ::= { xInternet 2 }


            snmpAgent       OBJECT IDENTIFIER ::= { xInternet 3 }


            domainResolver  OBJECT IDENTIFIER ::= { xInternet 4 }


            slip            OBJECT IDENTIFIER ::= { xInternet 5 }


            telnet          OBJECT IDENTIFIER ::= { xInternet 6 }


            tn3270          OBJECT IDENTIFIER ::= { xInternet 7 }


            kerberos        OBJECT IDENTIFIER ::= { xInternet 8 }


            portSecurity    OBJECT IDENTIFIER ::= { xInternet 9 }


            xremote         OBJECT IDENTIFIER ::= { xInternet 10 }


            rotary          OBJECT IDENTIFIER ::= { xInternet 11 }


            xEgp            OBJECT IDENTIFIER ::= { xInternet 12 }


            ospf            OBJECT IDENTIFIER ::= { xInternet 13 }


            routerIp        OBJECT IDENTIFIER ::= { xInternet 14 }


            routerUdp       OBJECT IDENTIFIER ::= { xInternet 15 }


            routerPolicy    OBJECT IDENTIFIER ::= { xInternet 16 }

            -- This is a MIB module for all Xyplex systems that
            -- implement IP
            -- the IP group
            -- Implementation of this group is mandatory for all Xyplex
            -- systems that implement IP

            ipGatewayAddress1 OBJECT-TYPE
                SYNTAX IpAddress
                ACCESS read-write
                STATUS mandatory
                DESCRIPTION
                    "The internet address of the system's primary (first 
                    choice) gateway.  A value of 0.0.0.0 indicates no 
                    address.  Corresponds directly to SERVER INTERNET 
                    PRIMARY GATEWAY ADDRESS and the value labeled 
                    'Primary Gateway Address:' in the SERVER INTERNET 
                    CHARACTERISTICS display."
                ::= { xIp 1 }


            ipGatewayAddress2 OBJECT-TYPE
                SYNTAX IpAddress
                ACCESS read-write
                STATUS mandatory
                DESCRIPTION
                    "The internet address of the system's secondary 
                    (second choice) gateway.  A value of 0.0.0.0 
                    indicates no address.  Corresponds directly to 
                    SERVER INTERNET SECONDARY GATEWAY ADDRESS and the 
                    value labeled 'Secondary Gateway Address:' in the 
                    SERVER INTERNET CHARACTERISTICS display."
                ::= { xIp 2 }


            ipAutoSubnetMask OBJECT-TYPE
                SYNTAX INTEGER { disabled(1), enabled(2) }
                ACCESS read-write
                STATUS mandatory
                DESCRIPTION
                    "A control for automatic determination of subnet 
                    mask.  'disabled' indicates the system must use the 
                    mask as configured by the network manager.  
                    'enabled' indicates that the system is to 
                    automatically change the subnet mask when the 
                    system's Internet address is changed.  Corresponds 
                    directly to SERVER INTERNET SUBNET MASK 
                    AUTOCONFIGURE and the value labeled 'Subnet Mask 
                    Autoconfigure:' in the SERVER INTERNET 
                    CHARACTERISTICS display."
                ::= { xIp 3 }


            ipReassembly OBJECT-TYPE
                SYNTAX INTEGER { disabled(1), enabled(2) }
                ACCESS read-write
                STATUS mandatory
                DESCRIPTION
                    "A control for reassembly of IP fragments.  
                    Corresponds directly to SERVER INTERNET REASSEMBLY 
                    and the value labeled 'Reassembly:' in the SERVER 
                    INTERNET CHARACTERISTICS display."
                ::= { xIp 4 }

            -- the TCP group
            -- Implementation of this group is mandatory for all Xyplex
            -- systems that implement TCP
            -- the TCP Character Port table

            tcpPortTable OBJECT-TYPE
                SYNTAX SEQUENCE OF TcpPortEntry
                ACCESS not-accessible
                STATUS mandatory
                DESCRIPTION
                    "A list of TCP character port entries."
                ::= { xTcp 1 }


            tcpPortEntry OBJECT-TYPE
                SYNTAX TcpPortEntry
                ACCESS not-accessible
                STATUS mandatory
                DESCRIPTION
                    "TCP parameter values for a character port."
                INDEX { tcpPortIndex }
                ::= { tcpPortTable 1 }

            TcpPortEntry ::=
                SEQUENCE {
                    tcpPortIndex
                        INTEGER,
                    tcpPortConnectByAddress
                        INTEGER,
                    tcpPortWindowSize
                        INTEGER
                }

            tcpPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { tcpPortEntry 1 }


            tcpPortConnectByAddress OBJECT-TYPE
                SYNTAX INTEGER { disabled(1), enabled(2) }
                ACCESS read-write
                STATUS mandatory
                DESCRIPTION
                    "A control for requesting outgoing connection by 
                    internet address.  'disabled' indicates outgoing 
                    connections must be by Domain name.  'enabled' 
                    indicates that outgoing connections may be requested 
                    by internet address.  Corresponds directly to PORT 
                    INTERNET CONNECTIONS and the presence of the label 
                    'Internet Connections' following the label 'Enabled 
                    Characteristics:' in the PORT CHARACTERISTICS 
                    display."
                ::= { tcpPortEntry 2 }


            tcpPortWindowSize OBJECT-TYPE
                SYNTAX INTEGER (64..8192)
                ACCESS read-write
                STATUS mandatory
                DESCRIPTION
                    "Size of the TCP window for TCP connections on the 
                    port.  Corresponds directly to PORT INTERNET TCP 
                    WINDOW SIZE and the value labeled 'TCP Window Size:' 
                    in the PORT ALTERNATE CHARACTERISTICS display."
                ::= { tcpPortEntry 3 }

            -- the SNMP Agent group
            -- Implementation of this group is mandatory for all Xyplex
            -- systems that implement SNMP

            snmpAgentGetCommunity OBJECT-TYPE
                SYNTAX DisplayString (SIZE (0..32))
                ACCESS read-write
                STATUS mandatory
                DESCRIPTION
                    "The SNMP community name allowed to perform 
                    get-requests or get-next requests to this agent.  
                    Use of this value is case-insensitive.  If the size 
                    is 0, the agent does not check the community name 
                    for these operations.  Corresponds directly to 
                    SERVER INTERNET SNMP GET COMMUNITY and the value 
                    labeled 'Get Community:' in the SERVER INTERNET SNMP 
                    CHARACTERISTICS display."
                ::= { snmpAgent 1 }


            snmpAgentSetCommunity OBJECT-TYPE
                SYNTAX DisplayString (SIZE (0..32))
                ACCESS read-write
                STATUS mandatory
                DESCRIPTION
                    "The SNMP community name allowed to perform 
                    set-requests to this agent.  Use of this value is 
                    case-insensitive.  If the size is 0, the agent does 
                    not check the community name for these operations.  
                    Corresponds directly to SERVER INTERNET SNMP SET 
                    COMMUNITY and the value labeled 'Set Community:' in 
                    the SERVER INTERNET SNMP CHARACTERISTICS display."
                ::= { snmpAgent 2 }


            snmpAgentTrapCommunity OBJECT-TYPE
                SYNTAX DisplayString (SIZE (0..32))
                ACCESS read-write
                STATUS mandatory
                DESCRIPTION
                    "The SNMP community name sent in traps from this 
                    agent.  Use of this value preserves case.  
                    Corresponds directly to SERVER INTERNET SNMP TRAP 
                    COMMUNITY and the value labeled 'Trap Community:' in 
                    the SERVER INTERNET SNMP CHARACTERISTICS display."
                ::= { snmpAgent 3 }


            snmpAgentGetClientNumber OBJECT-TYPE
                SYNTAX INTEGER
                ACCESS read-only
                STATUS mandatory
                DESCRIPTION
                    "The number of client source addresses allowed to 
                    perform get-requests or get-next requests to this 
                    agent.  If the value is 0, the agent does not check 
                    source address for these operations.  Corresponds 
                    indirectly to the values labeled 'Get Client n:' in 
                    the SERVER INTERNET SNMP CHARACTERISTICS display."
                ::= { snmpAgent 4 }


            snmpAgentSetClientNumber OBJECT-TYPE
                SYNTAX INTEGER
                ACCESS read-only
                STATUS mandatory
                DESCRIPTION
                    "The number of client source addresses allowed to 
                    perform set-requests to this agent.  If the value is 
                    0, the agent does not check source address for these 
                    operations.  Corresponds indirectly to the values 
                    labeled 'Set Client n:' in the SERVER INTERNET SNMP 
                    CHARACTERISTICS display."
                ::= { snmpAgent 5 }


            snmpAgentTrapClientNumber OBJECT-TYPE
                SYNTAX INTEGER
                ACCESS read-only
                STATUS mandatory
                DESCRIPTION
                    "The number of client source addresses to which this 
                    agent sends traps.  If the value is 0, the agent 
                    does not perform this operation.  Corresponds 
                    indirectly to the values labeled 'Trap Client n:' in 
                    the SERVER INTERNET SNMP CHARACTERISTICS display."
                ::= { snmpAgent 6 }

            -- the Get Client table

            getClientTable OBJECT-TYPE
                SYNTAX SEQUENCE OF GetClientEntry
                ACCESS not-accessible
                STATUS mandatory
                DESCRIPTION
                    "A list of get client entries.  The number of 
                    entries is given by the value of 
                    snmpAgentGetClientNumber."
                ::= { snmpAgent 7 }


            getClientEntry OBJECT-TYPE
                SYNTAX GetClientEntry
                ACCESS not-accessible
                STATUS mandatory
                DESCRIPTION
                    "Parameter values for a get client."
                INDEX { getClientIndex }
                ::= { getClientTable 1 }

            GetClientEntry ::=
                SEQUENCE {
                    getClientIndex
                        INTEGER,
                    getClientEntryStatus
                        INTEGER,
                    getClientAddressType
                        INTEGER,
                    getClientAddress
                        OCTET STRING
                }

            getClientIndex OBJECT-TYPE
                SYNTAX INTEGER
                ACCESS read-only
                STATUS mandatory
                DESCRIPTION
                    "Identification of a get client entry.  Corresponds 
                    directly to the number in the label 'Get Client n:' 
                    in the SERVER INTERNET SNMP CHARACTERISTICS 
                    display."
                ::= { getClientEntry 1 }


            getClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { getClientEntry 2 }


            getClientAddressType OBJECT-TYPE
                SYNTAX AddressType
                ACCESS read-write
                STATUS mandatory
                DESCRIPTION
                    "The type of network address contained in 
                    getClientAddress.  'unknown' means no address has 
                    been defined.  'other' means no other type value 
                    applies.  'ip' is an Internet IP address.  
                    'ethernet' is an 802.3 MAC address.  If 
                    getClientAddressType does not accompany 
                    getClientAddress in a set request, the default type 
                    is 'ip'.  Corresponds indirectly to the address 
                    value labeled 'Get Client n:' in the SERVER INTERNET 
                    SNMP CHARACTERISTICS display."
                DEFVAL { unknown }
                ::= { getClientEntry 3 }


            getClientAddress OBJECT-TYPE
                SYNTAX OCTET STRING
                ACCESS read-write
                STATUS mandatory
                DESCRIPTION
                    "The client's network address.  If 
                    getClientAddressType does not accompany 
                    getClientAddress in a set request, the default type 
                    is 'ip'.  Corresponds directly to the address value 
                    labeled 'Get Client n:' in the SERVER INTERNET SNMP 
                    CHARACTERISTICS display."
                DEFVAL { "" }  -- indicates zero length
                ::= { getClientEntry 4 }

            -- the Set Client table

            setClientTable OBJECT-TYPE
                SYNTAX SEQUENCE OF SetClientEntry
                ACCESS not-accessible
                STATUS mandatory
                DESCRIPTION
                    "A list of set client entries.  The number of 
                    entries is given by the value of 
                    snmpAgentSetClientNumber."
                ::= { snmpAgent 8 }


            setClientEntry OBJECT-TYPE
                SYNTAX SetClientEntry
                ACCESS not-accessible
                STATUS mandatory
                DESCRIPTION
                    "Parameter values for a set client."
                INDEX { setClientIndex }
                ::= { setClientTable 1 }

            SetClientEntry ::=
                SEQUENCE {
                    setClientIndex
                        INTEGER,
                    setClientEntryStatus
                        INTEGER,
                    setClientAddressType
                        INTEGER,
                    setClientAddress
                        OCTET STRING
                }

            setClientIndex OBJECT-TYPE
                SYNTAX INTEGER
                ACCESS read-only
                STATUS mandatory
                DESCRIPTION
                    "Identification of a set client entry.  Corresponds 
                    directly to the number in the label 'Set Client n:' 
                    in the SERVER INTERNET SNMP CHARACTERISTICS 
                    display."
                ::= { setClientEntry 1 }


            setClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { setClientEntry 2 }


            setClientAddressType OBJECT-TYPE
                SYNTAX AddressType
                ACCESS read-write
                STATUS mandatory
                DESCRIPTION
                    "The type of network address contained in 
                    setClientAddress.  'unknown' means no address has 
                    been defined.  'other' means no other type value 
                    applies.  'ip' is an Internet IP address.  
                    'ethernet' is an 802.3 MAC address.  If 
                    setClientAddressType does not accompany 
                    setClientAddress in a set request, the default type 
                    is 'ip'.  Corresponds indirectly to the address 
                    value labeled 'Set Client n:' in the SERVER INTERNET 
                    SNMP CHARACTERISTICS display."
                DEFVAL { unknown }
                ::= { setClientEntry 3 }


            setClientAddress OBJECT-TYPE
                SYNTAX OCTET STRING
                ACCESS read-write
                STATUS mandatory
                DESCRIPTION
                    "The client's network address.  When setting this 
                    value, the requester must supply 
                    setClientAddressType.  If setClientAddressType does 
                    not accompany setClientAddress in a set request, the 
                    default type is 'ip'.  Corresponds directly to the 
                    address value labeled 'Set Client n:' in the SERVER 
                    INTERNET SNMP CHARACTERISTICS display."
                DEFVAL { "" }  -- indicates zero length
                ::= { setClientEntry 4 }

            -- the Trap Client table

            trapClientTable OBJECT-TYPE
                SYNTAX SEQUENCE OF TrapClientEntry
                ACCESS not-accessible
                STATUS mandatory
                DESCRIPTION
                    "A list of trap client entries.  The number of 
                    entries is given by the value of 
                    snmpAgentTrapClientNumber."
                ::= { snmpAgent 9 }


            trapClientEntry OBJECT-TYPE
                SYNTAX TrapClientEntry
                ACCESS not-accessible
                STATUS mandatory
                DESCRIPTION
                    "Parameter values for a trap client."
                INDEX { trapClientIndex }
                ::= { trapClientTable 1 }

            TrapClientEntry ::=
                SEQUENCE {
                    trapClientIndex
                        INTEGER,
                    trapClientEntryStatus
                        INTEGER,
                    trapClientAddressType
                        INTEGER,
                    trapClientAddress
                        OCTET STRING
                }

            trapClientIndex OBJECT-TYPE
                SYNTAX INTEGER
                ACCESS read-only
                STATUS mandatory
                DESCRIPTION
                    "Identification of a trap client entry.  Corresponds 
                    directly to the number in the label 'Trap Client n:' 
                    in the SERVER INTERNET SNMP CHARACTERISTICS 
                    display."
                ::= { trapClientEntry 1 }


            trapClientEntryStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { trapClientEntry 2 }


            trapClientAddressType OBJECT-TYPE
                SYNTAX AddressType
                ACCESS read-write
                STATUS mandatory
                DESCRIPTION
                    "The type of network address contained in 
                    trapClientAddress.  'unknown' means no address has 
                    been defined.  'other' means no other type value 
                    applies.  'ip' is an Internet IP address.  
                    'ethernet' is an 802.3 MAC address.  If 
                    trapClientAddressType does not accompany 
                    trapClientAddress in a set request, the default type 
                    is 'ip'.  Corresponds indirectly to the address 
                    value labeled 'Trap Client n:' in the SERVER 
                    INTERNET SNMP CHARACTERISTICS display."
                DEFVAL { unknown }
                ::= { trapClientEntry 3 }


            trapClientAddress OBJECT-TYPE
                SYNTAX OCTET STRING
                ACCESS read-write
                STATUS mandatory
                DESCRIPTION
                    "The client's network address.  When setting this 
                    value, the requester must supply 
                    trapClientAddressType.  If trapClientAddressType 
                    does not accompany trapClientAddress in a set 
                    request, the default type is 'ip'.  Corresponds 
                    directly to the address value labeled 'Trap Client 
                    n:' in the SERVER INTERNET SNMP CHARACTERISTICS 
                    display."
                DEFVAL { "" }  -- indicates zero length
                ::= { trapClientEntry 4 }

            -- the Domain Resolver group
            -- Implementation of this group is mandatory for all Xyplex
            -- systems that implement Domain name resolution

            domainResolverSuffix OBJECT-TYPE
                SYNTAX DisplayString (SIZE (0..115))
                ACCESS read-write
                STATUS mandatory
                DESCRIPTION
                    "A partial domain name for the server to append to 
                    the end of an incomplete domain name provided by the 
                    user.  Corresponds directly to SERVER INTERNET 
                    DEFAULT DOMAIN SUFFIX and the value labeled 'Domain 
                    Suffix:' in the SERVER INTERNET CHARACTERISTICS 
                    display."
                ::= { domainResolver 1 }


            domainResolverAddress1 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    PRIMARY DOMAIN ADDRESS and the value labeled 
                    'Primary Domain Address:' in the SERVER INTERNET 
                    CHARACTERISTICS display."
                ::= { domainResolver 2 }


            domainResolverAddress2 OBJECT-TYPE
                SYNTAX IpAddress
                ACCESS read-write
                STATUS mandatory
                DESCRIPTION
                    "The internet address of a Domain Name Server.  The 
                    system can use one or two such addresses, without 
                    preference.  A value of 0.0.0.0 indicates no 
                    address.  Corresponds directly to SERVER INTERNET 
                    SECONDARY DOMAIN ADDRESS and the value labeled 
                    'Secondary Domain Address:' in the SERVER INTERNET 
                    CHARACTERISTICS display."
                ::= { domainResolver 3 }


            domainResolverTtl OBJECT-TYPE
                SYNTAX INTEGER (0..168)
                ACCESS read-write
                STATUS mandatory
                DESCRIPTION
                    "The number of hours to keep received Domain 
                    information.  Corresponds directly to SERVER 
                    INTERNET DOMAIN TTL and the value labeled ' Domain 
                    TTL:' in the SERVER INTERNET CHARACTERISTICS 
                    display."
                ::= { domainResolver 4 }


            domainResolverNameNumber OBJECT-TYPE
                SYNTAX INTEGER
                ACCESS read-only
                STATUS mandatory
                DESCRIPTION
                    "The number of Domain name mappings in this system's 
                    name cache."
                ::= { domainResolver 5 }

            -- the Name table

            nameTable OBJECT-TYPE
                SYNTAX SEQUENCE OF NameEntry
                ACCESS not-accessible
                STATUS mandatory
                DESCRIPTION
                    "A list of Domain name entries.  The number of 
                    entries is given by the value of 
                    domainResolverNameNumber."
                ::= { domainResolver 6 }


            nameEntry OBJECT-TYPE
                SYNTAX NameEntry
                ACCESS not-accessible
                STATUS mandatory
                DESCRIPTION
                    "Parameter values for a Domain name."
                INDEX { nameName, nameAddress }
                ::= { nameTable 1 }

            NameEntry ::=
                SEQUENCE {
                    nameName
                        DisplayString,
                    nameAddress
                        IpAddress,
                    nameStatus
                        INTEGER,
                    nameSource
                        INTEGER,
                    nameTtl
                        INTEGER
                }

            nameName OBJECT-TYPE
                SYNTAX DisplayString (SIZE (1..50))
                ACCESS read-only
                STATUS mandatory
                DESCRIPTION
                    "A fully qualified domain name.  Corresponds 
                    directly to the value labeled 'Domain Name' in the 
                    DOMAIN display."
                ::= { nameEntry 1 }


            nameAddress OBJECT-TYPE
                SYNTAX IpAddress
                ACCESS read-write
                STATUS mandatory
                DESCRIPTION
                    "An Internet address corresponding to the Domain 
                    name.  Corresponds directly to the value labeled 
                    'Internet Address' in the DOMAIN display."
                ::= { nameEntry 2 }


            nameStatus OBJECT-TYPE
                SYNTAX INTEGER { invalid(1), valid(2) }
                ACCESS read-write
                STATUS mandatory
                DESCRIPTION
                    "The status of the entry.  Set to 'invalid' to 
                    remove the entry, which corresponds directly to the 
                    PURGE DOMAIN command.  Actual removal of the entry 
                    is implementation specific."
                ::= { nameEntry 3 }


            nameSource OBJECT-TYPE
                SYNTAX INTEGER { manager(1), primary(2), secondary(3) }
                ACCESS read-only
                STATUS mandatory
                DESCRIPTION
                    "Source of this entry.  The value meanings are:

                    local       defined by manager (LOCAL)
                    primary     obtained from a primary name server
                    secondary   obtained from a secondary name server

                    Corresponds directly to the value labeled 'Source' 
                    in the DOMAIN display."
                ::= { nameEntry 4 }


            nameTtl OBJECT-TYPE
                SYNTAX INTEGER
                ACCESS read-only
                STATUS mandatory
                DESCRIPTION
                    "The number of minutes remaining in the entry's time 
                    to live.  Corresponds directly to the value labeled 
                    'TTL' in the DOMAIN display."
--                DEFVAL { domainResolverTtl }
                ::= { nameEntry 5 }

            -- the SLIP group
            -- Implementation of this group is mandatory for all Xyplex
            -- systems that implement SLIP ports

            slipTable OBJECT-TYPE
                SYNTAX SEQUENCE OF SlipEntry
                ACCESS not-accessible
                STATUS mandatory
                DESCRIPTION
                    "A list of SLIP character port entries."
                ::= { slip 1 }


            slipEntry OBJECT-TYPE
                SYNTAX SlipEntry
                ACCESS not-accessible
                STATUS mandatory
                DESCRIPTION
                    "Parameter values for a SLIP port."
                INDEX { slipIndex }
                ::= { slipTable 1 }

            SlipEntry ::=
                SEQUENCE {
                    slipIndex
                        INTEGER,
                    slipState
                        INTEGER,
                    slipLocalAddress
                        IpAddress,
                    slipRemoteAddress
                        IpAddress,
                    slipMask
                        IpAddress,
                    slipPortPacketsReceived
                        Counter,
                    slipPortPacketsSent
                        Counter,
                    slipPortPacketsDiscarded
                        Counter,
                    slipPortPacketLengthErrors
                        Counter,
                    slipPortPacketChecksumErrors
                        Counter,
                    slipNetworkPacketsReceived
                        Counter,
                    slipNetworkPacketsSent
                        Counter,
                    slipNetworkPacketsDiscarded
                        Counter
                }

            slipIndex OBJECT-TYPE
                SYNTAX INTEGER
                ACCESS read-only
                STATUS mandatory
                DESCRIPTION
                    "An index value that uniquely identifies a port that 
                    can run SLIP.  The port identified by a particular 
                    value of this index is the same port as identified 
                    by charPortIndex in the Proposed Standard Internet 
                    Character MIB."
                ::= { slipEntry 1 }


            slipState OBJECT-TYPE
                SYNTAX INTEGER { off(1), on(2) }
                ACCESS read-write
                STATUS mandatory
                DESCRIPTION
                    "A control indicating whether SLIP is in operation 
                    on the port.  Corresponds directly to PORT INTERNET 
                    SLIP and the value labeled 'SLIP' in the PORT 
                    CHARACTERISTICS display."
                ::= { slipEntry 2 }


            slipLocalAddress OBJECT-TYPE
                SYNTAX IpAddress
                ACCESS read-write
                STATUS mandatory
                DESCRIPTION
                    "The IP address assigned to the port.  Corresponds 
                    directly to PORT SLIP ADDRESS and the value labeled 
                    'SLIP Address:' in the PORT ALTERNATE 
                    CHARACTERISTICS display."
                ::= { slipEntry 3 }


            slipRemoteAddress OBJECT-TYPE
                SYNTAX IpAddress
                ACCESS read-write
                STATUS mandatory
                DESCRIPTION
                    "The IP address of the remote system attached to the 
                    port.  Corresponds directly to PORT SLIP REMOTE and 
                    the value labeled 'Remote SLIP Address:' in the PORT 
                    ALTERNATE CHARACTERISTICS display."
                ::= { slipEntry 4 }


            slipMask OBJECT-TYPE
                SYNTAX IpAddress
                ACCESS read-write
                STATUS mandatory
                DESCRIPTION
                    "The subnet mask to use for SLIP operation on the 
                    port.  Corresponds directly to PORT SLIP MASK and 
                    the value labeled 'SLIP Mask:' in the PORT ALTERNATE 
                    CHARACTERISTICS display."
                ::= { slipEntry 5 }


            slipPortPacketsReceived OBJECT-TYPE
                SYNTAX Counter
                ACCESS read-only
                STATUS mandatory
                DESCRIPTION
                    "The number of SLIP packets received from the port.  
                    Corresponds directly to the value labeled 'Serial 
                    Packets Received:' in the PORT COUNTERS display."
                ::= { slipEntry 6 }


            slipPortPacketsSent OBJECT-TYPE
                SYNTAX Counter
                ACCESS read-only
                STATUS mandatory
                DESCRIPTION
                    "The number of SLIP packets sent to the port.  
                    Corresponds directly to the value labeled 'Serial 
                    Packets Sent:' in the PORT COUNTERS display."
                ::= { slipEntry 7 }


            slipPortPacketsDiscarded OBJECT-TYPE
                SYNTAX Counter
                ACCESS read-only
                STATUS mandatory
                DESCRIPTION
                    "The number of SLIP packets received from the port 
                    and discarded.  Corresponds directly to the value 
                    labeled 'Serial Packets Discarded:' in the PORT 
                    COUNTERS display."
                ::= { slipEntry 8 }


            slipPortPacketLengthErrors OBJECT-TYPE
                SYNTAX Counter
                ACCESS read-only
                STATUS mandatory
                DESCRIPTION
                    "The number of SLIP packets received from the port 
                    with an incorrect number of bytes.  Corresponds 
                    directly to the value labeled 'Serial Packet Length 
                    Errors:' in the PORT COUNTERS display."
                ::= { slipEntry 9 }


            slipPortPacketChecksumErrors OBJECT-TYPE
                SYNTAX Counter
                ACCESS read-only
                STATUS mandatory
                DESCRIPTION
                    "The number of SLIP packets received from the port 
                    with an invalid checksum.  Corresponds directly to 
                    the value labeled 'Serial Packet Checksum Errors:' 
                    in the PORT COUNTERS display."
                ::= { slipEntry 10 }


            slipNetworkPacketsReceived OBJECT-TYPE
                SYNTAX Counter
                ACCESS read-only
                STATUS mandatory
                DESCRIPTION
                    "The number of SLIP packets received from the 
                    network for this port.  Corresponds directly to the 
                    value labeled 'Network Packets Received:' in the 
                    PORT COUNTERS display."
                ::= { slipEntry 11 }


            slipNetworkPacketsSent OBJECT-TYPE
                SYNTAX Counter
                ACCESS read-only
                STATUS mandatory
                DESCRIPTION
                    "The number of SLIP packets sent to the network from 
                    this port.  Corresponds directly to the value 
                    labeled 'Network Packets Sent:' in the PORT COUNTERS 
                    display."
                ::= { slipEntry 12 }


            slipNetworkPacketsDiscarded OBJECT-TYPE
                SYNTAX Counter
                ACCESS read-only
                STATUS mandatory
                DESCRIPTION
                    "The number of SLIP packets received from the 
                    network for this port and discarded.  Corresponds 
                    directly to the value labeled 'Network Packets 
                    Discarded:' in the PORT COUNTERS display."
                ::= { slipEntry 13 }

            -- the Telnet group
            -- Implementation of this group is mandatory for all Xyplex
            -- systems that implement Telnet
            -- the Telnet Character Port table
            -- Ports in this table are either serial or parallel

            telnetPortTable OBJECT-TYPE
                SYNTAX SEQUENCE OF TelnetPortEntry
                ACCESS not-accessible
                STATUS mandatory
                DESCRIPTION
                    "A list of Telnet character port entries."
                ::= { telnet 1 }


            telnetPortEntry OBJECT-TYPE
                SYNTAX TelnetPortEntry
                ACCESS not-accessible
                STATUS mandatory
                DESCRIPTION
                    "Telnet parameter values for a character port."
                INDEX { telnetPortIndex }
                ::= { telnetPortTable 1 }

            TelnetPortEntry ::=
                SEQUENCE {
                    telnetPortIndex
                        INTEGER,
                    telnetPortIncomingTcpPort
                        INTEGER,
                    telnetPortOutgoingTcpPort
                        INTEGER,
                    telnetPortNewlineTranslation
                        INTEGER,
                    telnetPortTerminalType
                        DisplayString,
                    telnetPortEorReflection
                        INTEGER,
                    telnetPortBinaryMode
                        INTEGER
                }

            telnetPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetPortEntry 1 }


            telnetPortIncomingTcpPort OBJECT-TYPE
                SYNTAX INTEGER (1..32767)
                ACCESS read-write
                STATUS mandatory
                DESCRIPTION
                    "The TCP port number offered for incoming 
                    connections to this character port.  Corresponds 
                    directly to PORT TELNET REMOTE PORT and the value 
                    labeled 'Remote Port:' in the PORT TELNET 
                    CHARACTERISTICS display."
                ::= { telnetPortEntry 2 }


            telnetPortOutgoingTcpPort OBJECT-TYPE
                SYNTAX INTEGER
                ACCESS read-only
                STATUS mandatory
                DESCRIPTION
                    "The TCP port number used by default for outgoing 
                    connections from this character port.  Corresponds 
                    directly to PORT TELNET DEFAULT PORT and the value 
                    labeled 'Default Port:' in the PORT TELNET 
                    CHARACTERISTICS display."
                ::= { telnetPortEntry 3 }


            telnetPortNewlineTranslation OBJECT-TYPE
                SYNTAX INTEGER { none(1), cr(2), crNull(3), crLf(4) }
                ACCESS read-write
                STATUS mandatory
                DESCRIPTION
                    "Translation to apply to newline sequences (CR/NULL 
                    or CR/LF) received from the network, before sending 
                    the newline to the character port.  The value 
                    indicates the sequence sent to the character port, 
                    with 'none' meaning no translation.  Corresponds 
                    directly to PORT TELNET NEWLINE FILTERING and the 
                    value labeled 'Newline Filtering:' in the PORT 
                    TELNET CHARACTERISTICS display."
                ::= { telnetPortEntry 4 }


            telnetPortTerminalType OBJECT-TYPE
                SYNTAX DisplayString (SIZE (1..20))
                ACCESS read-write
                STATUS mandatory
                DESCRIPTION
                    "The terminal type character string for Telnet 
                    negotiations.  Corresponds directly to PORT TELNET 
                    TERMINALTYPE and the value labeled 'TerminalType:' 
                    in the PORT TELNET CHARACTERISTICS display."
                ::= { telnetPortEntry 5 }


            telnetPortEorReflection OBJECT-TYPE
                SYNTAX INTEGER { disabled(1), enabled(2) }
                ACCESS read-write
                STATUS mandatory
                DESCRIPTION
                    "Control for end-of-record handshake.  Corresponds 
                    directly to PORT TELNET EOR REFLECTION and the value 
                    labeled 'EOR Reflection:' in the PORT TELNET 
                    CHARACTERISTICS display."
                ::= { telnetPortEntry 6 }


            telnetPortBinaryMode OBJECT-TYPE
                SYNTAX INTEGER { flowControl(1), complete(2),
                                 disabled(3) }
                ACCESS read-write
                STATUS mandatory
                DESCRIPTION
                    "Control for operation of Telnet binary mode.  The 
                    value meanings are:

                    disabled      refuse binary mode negotiation
                                  (INTERACTIVE)
                    flowControl   pass all but XON and XOFF (PASTHRU)
                    complete      pass all characters (PASSALL)

                    Corresponds directly to PORT TELNET BINARY SESSION 
                    MODE and the value labeled 'Binary Session Mode:' in 
                    the PORT TELNET CHARACTERISTICS display."
                ::= { telnetPortEntry 7 }

            -- the Telnet Serial Character Port table

            telnetSerialPortTable OBJECT-TYPE
                SYNTAX SEQUENCE OF TelnetSerialPortEntry
                ACCESS not-accessible
                STATUS mandatory
                DESCRIPTION
                    "A list of Telnet character port entries."
                ::= { telnet 2 }


            telnetSerialPortEntry OBJECT-TYPE
                SYNTAX TelnetSerialPortEntry
                ACCESS not-accessible
                STATUS mandatory
                DESCRIPTION
                    "Telnet parameter values for a character port."
                INDEX { telnetSerialPortIndex }
                ::= { telnetSerialPortTable 1 }

            TelnetSerialPortEntry ::=
                SEQUENCE {
                    telnetSerialPortIndex
                        INTEGER,
                    telnetSerialPortOptionDisplay
                        INTEGER,
                    telnetSerialPortCsiEscape
                        INTEGER,
                    telnetSerialPortEchoMode
                        INTEGER,
                    telnetSerialPortNewlineMode
                        INTEGER,
                    telnetSerialPortTransmitMode
                        INTEGER,
                    telnetSerialPortTransmitCharacterTimes
                        INTEGER,
                    telnetSerialPortAbortOutputCharacter
                        INTEGER,
                    telnetSerialPortAttentionCharacter
                        INTEGER,
                    telnetSerialPortEraseKeyCharacter
                        INTEGER,
                    telnetSerialPortEraseLineCharacter
                        INTEGER,
                    telnetSerialPortInterruptCharacter
                        INTEGER,
                    telnetSerialPortQueryCharacter
                        INTEGER,
                    telnetSerialPortSynchronizeCharacter
                        INTEGER
                }

            telnetSerialPortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { telnetSerialPortEntry 1 }


            telnetSerialPortOptionDisplay OBJECT-TYPE
                SYNTAX INTEGER { disabled(1), enabled(2) }
                ACCESS read-write
                STATUS mandatory
                DESCRIPTION
                    "Control for display of Telnet option negotiations.  
                    Corresponds directly to PORT TELNET OPTION DISPLAY 
                    and the value labeled 'Option Display:' in the PORT 
                    TELNET CHARACTERISTICS display."
                ::= { telnetSerialPortEntry 2 }


            telnetSerialPortCsiEscape OBJECT-TYPE
                SYNTAX INTEGER { disabled(1), enabled(2) }
                ACCESS read-write
                STATUS mandatory
                DESCRIPTION
                    "Control for translation of 8-bit escape sequences 
                    received from the character port to 7-bit 
                    equivalents before transmission to the remote 
                    partner.  Corresponds directly to PORT TELNET CSI 
                    ESCAPE and the value labeled 'CSI Escape:' in the 
                    PORT TELNET CHARACTERISTICS display."
                ::= { telnetSerialPortEntry 3 }


            telnetSerialPortEchoMode OBJECT-TYPE
                SYNTAX INTEGER { local(1), remote(2) }
                ACCESS read-write
                STATUS mandatory
                DESCRIPTION
                    "Control for who echoes characters that come from 
                    the character port.  The value meanings are:

                    local    terminal server echoes locally
                    remote   remote system echoes

                    Corresponds directly to PORT TELNET ECHO MODE and 
                    the value labeled 'Echo Mode:' in the PORT TELNET 
                    CHARACTERISTICS display."
                ::= { telnetSerialPortEntry 4 }


            telnetSerialPortNewlineMode OBJECT-TYPE
                SYNTAX INTEGER { crNull(1), crLf(2), verbatim(3) }
                ACCESS read-write
                STATUS mandatory
                DESCRIPTION
                    "Translation to apply to newline (carriage return) 
                    received from the character port, before sending the 
                    newline to the remote partner.  The correspondence 
                    to command keywords is 'crNull' to NULL, 'crLF' to 
                    LINEFEED, and 'verbatim' to NOTHING (that is, no 
                    translation).  Corresponds directly to PORT TELNET 
                    NEWLINE and the value labeled 'Newline:' in the PORT 
                    TELNET CHARACTERISTICS display."
                ::= { telnetSerialPortEntry 5 }


            telnetSerialPortTransmitMode OBJECT-TYPE
                SYNTAX INTEGER { immediate(1), buffered(2), timed(3) }
                ACCESS read-write
                STATUS mandatory
                DESCRIPTION
                    "Criterion for deciding to send to the remote 
                    partner characters received from the character port.  
                    Corresponds directly to PORT TELNET TRANSMIT and the 
                    value labeled 'Transmit:' in the PORT TELNET 
                    CHARACTERISTICS display."
                ::= { telnetSerialPortEntry 6 }


            telnetSerialPortTransmitCharacterTimes OBJECT-TYPE
                SYNTAX INTEGER (1..255)
                ACCESS read-write
                STATUS mandatory
                DESCRIPTION
                    "Number of character times to wait before 
                    transmitting when telnetSerialPortTransmitMode value 
                    is 'timed'.  Corresponds directly to PORT TELNET 
                    TRANSMIT IDLETIME and the value labeled 'Transmit:  
                    Idle Time -' in the PORT TELNET CHARACTERISTICS 
                    display."
                ::= { telnetSerialPortEntry 7 }


            telnetSerialPortAbortOutputCharacter OBJECT-TYPE
                SYNTAX INTEGER (0..255)
                ACCESS read-write
                STATUS mandatory
                DESCRIPTION
                    "Character input from the character port to cause 
                    aborting output.  The value 0 indicates no character 
                    has this effect.  Corresponds directly to PORT 
                    TELNET ABORT OUTPUT and the value labeled 'Abort 
                    Output Character:' in the PORT TELNET 
                    CHARACTERISTICS display."
                ::= { telnetSerialPortEntry 8 }


            telnetSerialPortAttentionCharacter OBJECT-TYPE
                SYNTAX INTEGER (0..255)
                ACCESS read-write
                STATUS mandatory
                DESCRIPTION
                    "Character input from the character port to cause an 
                    attention notification to the remote partner.  The 
                    value 0 indicates no character has this effect.  
                    Corresponds directly to PORT TELNET ATTENTION and 
                    the value labeled 'Attention Character:' in the PORT 
                    TELNET CHARACTERISTICS display."
                ::= { telnetSerialPortEntry 9 }


            telnetSerialPortEraseKeyCharacter OBJECT-TYPE
                SYNTAX INTEGER (0..255)
                ACCESS read-write
                STATUS mandatory
                DESCRIPTION
                    "Character input from the character port to cause 
                    erasure of the previous input character.  The value 
                    0 indicates no character has this effect.  
                    Corresponds directly to PORT TELNET ERASE CHARACTER 
                    and the value labeled 'Erase Keystroke Character:' 
                    in the PORT TELNET CHARACTERISTICS display."
                ::= { telnetSerialPortEntry 10 }


            telnetSerialPortEraseLineCharacter OBJECT-TYPE
                SYNTAX INTEGER (0..255)
                ACCESS read-write
                STATUS mandatory
                DESCRIPTION
                    "Character input from the character port to cause 
                    erasure of the previous line of input.  The value 0 
                    indicates no character has this effect.  Corresponds 
                    directly to PORT TELNET ERASE LINE and the value 
                    labeled 'Erase Line Character:' in the PORT TELNET 
                    CHARACTERISTICS display."
                ::= { telnetSerialPortEntry 11 }


            telnetSerialPortInterruptCharacter OBJECT-TYPE
                SYNTAX INTEGER (0..255)
                ACCESS read-write
                STATUS mandatory
                DESCRIPTION
                    "Character input from the character port to cause 
                    sending an interrupt notification to the remote 
                    partner.  The value 0 indicates no character has 
                    this effect.  Corresponds directly to PORT TELNET 
                    INTERRUPT and the value labeled 'Interrupt 
                    Character:' in the PORT TELNET CHARACTERISTICS 
                    display."
                ::= { telnetSerialPortEntry 12 }


            telnetSerialPortQueryCharacter OBJECT-TYPE
                SYNTAX INTEGER (0..255)
                ACCESS read-write
                STATUS mandatory
                DESCRIPTION
                    "Character input from the character port to cause 
                    sending a status query to the remote partner.  The 
                    value 0 indicates no character has this effect.  
                    Corresponds directly to PORT TELNET QUERY and the 
                    value labeled 'Query Character:' in the PORT TELNET 
                    CHARACTERISTICS display."
                ::= { telnetSerialPortEntry 13 }


            telnetSerialPortSynchronizeCharacter OBJECT-TYPE
                SYNTAX INTEGER (0..255)
                ACCESS read-write
                STATUS mandatory
                DESCRIPTION
                    "Character input from the character port to cause 
                    sending a synchronization attempt to the remote 
                    partner.  The value 0 indicates no character has 
                    this effect.  Corresponds directly to PORT TELNET 
                    SYNCHRONIZE and the value labeled 'Synchronize 
                    Character:' in the PORT TELNET CHARACTERISTICS 
                    display."
                ::= { telnetSerialPortEntry 14 }

            -- the tn3270 group
            -- Implementation of this group is mandatory for all Xyplex
            -- systems that implement tn3270

            tn3270DeviceNumber OBJECT-TYPE
                SYNTAX INTEGER
                ACCESS read-only
                STATUS mandatory
                DESCRIPTION
                    "The number of entries in the tn3270 Device table."
                ::= { tn3270 1 }


            tn3270LanguageNumber OBJECT-TYPE
                SYNTAX INTEGER
                ACCESS read-only
                STATUS mandatory
                DESCRIPTION
                    "The number of entries in the tn3270 Language 
                    table."
                ::= { tn3270 2 }


            tn3270PortKeymapStatus OBJECT-TYPE
                SYNTAX INTEGER { disabled(1), enabled(2) }
                ACCESS read-write
                STATUS mandatory
                DESCRIPTION
                    "Control for individual ports to create their own 
                    keymaps.  Corresponds directly to SERVER TN3270 PORT 
                    KEYMAPS and the value labeled 'Port Keymaps:' in the 
                    SERVER TN3270 display."
                ::= { tn3270 3 }

            -- The tn3270 Device table

            tn3270DeviceTable OBJECT-TYPE
                SYNTAX SEQUENCE OF Tn3270DeviceEntry
                ACCESS not-accessible
                STATUS mandatory
                DESCRIPTION
                    "A list of tn3270 terminal device entries."
                ::= { tn3270 4 }


            tn3270DeviceEntry OBJECT-TYPE
                SYNTAX Tn3270DeviceEntry
                ACCESS not-accessible
                STATUS mandatory
                DESCRIPTION
                    "Tn3270 parameter values for a terminal device 
                    entry."
                INDEX { tn3270DeviceName }
                ::= { tn3270DeviceTable 1 }

            Tn3270DeviceEntry ::=
                SEQUENCE {
                    tn3270DeviceName
                        DisplayString,
                    tn3270DeviceStatus
                        INTEGER,
                    tn3270DeviceType
                        DisplayString,
                    tn3270Device3278Model
                        INTEGER,
                    tn3270DeviceKeyNumber
                        INTEGER,
                    tn3270DeviceScreenNumber
                        INTEGER
                }

            tn3270DeviceName OBJECT-TYPE
                SYNTAX DisplayString (SIZE (1..8))
                ACCESS read-write
                STATUS mandatory
                DESCRIPTION
                    "The name of a generic terminal device.  Corresponds 
                    directly to SERVER TN3270 DEVICE and the value 
                    labeled 'Device Name:' in the SERVER TN3270 DEVICE 
                    display."
                ::= { tn3270DeviceEntry 1 }


            tn3270DeviceStatus OBJECT-TYPE
                SYNTAX INTEGER { invalid(1), valid(2) }
                ACCESS read-write
                STATUS mandatory
                DESCRIPTION
                    "Status of this entry.  Setting the value to 
                    'invalid' invalidates the entry, corresponding 
                    directly to the PURGE SERVER TN3270 DEVICE command.  
                    It is an implementation-specific matter as to 
                    whether the agent removes an invalidated entry from 
                    the table."
                DEFVAL { valid }
                ::= { tn3270DeviceEntry 2 }


            tn3270DeviceType OBJECT-TYPE
                SYNTAX DisplayString (SIZE (1..20))
                ACCESS read-write
                STATUS mandatory
                DESCRIPTION
                    "The terminal type character string for use when 
                    tn3270DeviceTn3270Type is insufficient.  Corresponds 
                    directly to SERVER TN3270 DEVICE TERMINALTYPE and 
                    the value labeled 'TerminalType:' in the SERVER 
                    TN3270 DEVICE display."
                ::= { tn3270DeviceEntry 3 }


            tn3270Device3278Model OBJECT-TYPE
                SYNTAX INTEGER { model2(1), model5(2) }
                ACCESS read-write
                STATUS mandatory
                DESCRIPTION
                    "The 3278 model for the device.  Corresponds 
                    directly to SERVER TN3270 DEVICE TN3278Model and the 
                    value labeled 'Tn3278Model:' in the SERVER TN3270 
                    DEVICE display."
                ::= { tn3270DeviceEntry 4 }


            tn3270DeviceKeyNumber OBJECT-TYPE
                SYNTAX INTEGER
                ACCESS read-only
                STATUS mandatory
                DESCRIPTION
                    "The number of Key table entries for this device."
                ::= { tn3270DeviceEntry 5 }


            tn3270DeviceScreenNumber OBJECT-TYPE
                SYNTAX INTEGER
                ACCESS read-only
                STATUS mandatory
                DESCRIPTION
                    "The number of Screen table entries for this 
                    device."
                ::= { tn3270DeviceEntry 6 }

            -- The Key table

            tn3270KeyTable OBJECT-TYPE
                SYNTAX SEQUENCE OF Tn3270KeyEntry
                ACCESS not-accessible
                STATUS mandatory
                DESCRIPTION
                    "A list of tn3270 key entries by device."
                ::= { tn3270 5 }


            tn3270KeyEntry OBJECT-TYPE
                SYNTAX Tn3270KeyEntry
                ACCESS not-accessible
                STATUS mandatory
                DESCRIPTION
                    "Tn3270 parameter values for a key entry for a 
                    device."
                INDEX { tn3270KeyDeviceName, tn3270KeyName }
                ::= { tn3270KeyTable 1 }

            Tn3270KeyEntry ::=
                SEQUENCE {
                    tn3270KeyDeviceName
                        DisplayString,
                    tn3270KeyName
                        INTEGER,
                    tn3270KeyStatus
                        INTEGER,
                    tn3270KeyCharacterSequence
                        OCTET STRING,
                    tn3270KeyDescription
                        DisplayString
                }

            tn3270KeyDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270KeyEntry 1 }


            tn3270KeyName OBJECT-TYPE
                SYNTAX INTEGER { newline(1), tab(2), backtab(3),
                                 cursorup(4), cursorleft(5),
                                 cursorright(6), cursordown(7),
                                 home(8), delete(9), eraseeof(10),
                                 eraseinput(11), insert(12),
                                 flushinput(13), refresh(14),
                                 centsign(15), duplicate(16),
                                 fieldmark(17), scroll(18),
                                 status(19), reset(20),
                                 fastleft(21), fastright(22),
                                 showkeys(23), print(24),
                                 pf1(39), pf2(40), pf3(41),
                                 pf4(42), pf5(43), pf6(44),
                                 pf7(45), pf8(46), pf9(47), pf10(48),
                                 pf11(49), pf12(50), pf13(51),
                                 pf14(52), pf15(53), pf16(54),
                                 pf17(55), pf18(56), pf19(57),
                                 pf20(58), pf21(59), pf22(60),
                                 pf23(61), pf24(62), pa1(63),
                                 pa2(64), pa3(65), sysreq(66),
                                 enter(67), clear(68), cursorsel(69),
                                 test(70) }
                ACCESS read-only
                STATUS mandatory
                DESCRIPTION
                    "The key name to which this entry applies.  
                    Corresponds directly to the key portion of SERVER 
                    TN3270 DEVICE KEYMAP and the value labeled 
                    '3270-key' in the 'Keymap:' section of the SERVER 
                    TN3270 DEVICE display."
                ::= { tn3270KeyEntry 2 }


            tn3270KeyStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { tn3270KeyEntry 3 }


            tn3270KeyCharacterSequence OBJECT-TYPE
                SYNTAX OCTET STRING (SIZE (0..8))
                ACCESS read-write
                STATUS mandatory
                DESCRIPTION
                    "The ASCII character sequence for the key.  
                    Corresponds directly to the escape-sequence portion 
                    of SERVER TN3270 DEVICE KEYMAP and the value labeled 
                    'KeyCode' in the 'Keymap:' section of the SERVER 
                    TN3270 DEVICE display."
                ::= { tn3270KeyEntry 4 }


            tn3270KeyDescription OBJECT-TYPE
                SYNTAX DisplayString (SIZE (0..5))
                ACCESS read-write
                STATUS mandatory
                DESCRIPTION
                    "Descriptive text for the key.  Corresponds directly 
                    to the description portion of SERVER TN3270 DEVICE 
                    KEYMAP and the value labeled 'Description' in the 
                    SERVER TN3270 DEVICE display."
                ::= { tn3270KeyEntry 5 }

            -- The Screen Action table

            tn3270ScreenTable OBJECT-TYPE
                SYNTAX SEQUENCE OF Tn3270ScreenEntry
                ACCESS not-accessible
                STATUS mandatory
                DESCRIPTION
                    "A list of tn3270 screen action entries by device."
                ::= { tn3270 6 }


            tn3270ScreenEntry OBJECT-TYPE
                SYNTAX Tn3270ScreenEntry
                ACCESS not-accessible
                STATUS mandatory
                DESCRIPTION
                    "Tn3270 parameter values for a screen action entry 
                    for a device."
                INDEX { tn3270ScreenDeviceName, tn3270ScreenActionName }
                ::= { tn3270ScreenTable 1 }

            Tn3270ScreenEntry ::=
                SEQUENCE {
                    tn3270ScreenDeviceName
                        DisplayString,
                    tn3270ScreenActionName
                        INTEGER,
                    tn3270ScreenStatus
                        INTEGER,
                    tn3270ScreenCharacterSequence
                        OCTET STRING
                }

            tn3270ScreenDeviceName OBJECT-TYPE
                SYNTAX DisplayString (SIZE (1..8))
                ACCESS read-only
                STATUS mandatory
                DESCRIPTION
                    "The name of a generic terminal device as in 
                    tn3270DeviceName.  Corresponds directly to SERVER 
                    TN3270 DEVICE and the value labeled 'Device Name:' 
                    in the SERVER TN3270 DEVICE display."
                ::= { tn3270ScreenEntry 1 }


            tn3270ScreenActionName OBJECT-TYPE
                SYNTAX INTEGER { eraseeol(1), clearscr(2),
                                 movecursor(3), col132(4), col80(5),
                                 beep(6), charset(7), boldon(8),
                                 boldoff(9), blinkon(10),
                                 blinkoff(11), underscoreon(12),
                                 underscoreoff(13), reverseon(14),
                                 reverseoff(15),
                                 status1(26), status2(27),
                                 reset1(28), reset2(29),
                                 reset3(30), reset4(31),
                                 base(32), sgr(33) }
                ACCESS read-only
                STATUS mandatory
                DESCRIPTION
                    "The screen action to which this entry applies.  
                    Corresponds directly to the action portion of SERVER 
                    TN3270 DEVICE SCREENMAP and the value labeled 
                    'Terminal Function' in the 'Screenmap: section of 
                    the SERVER TN3270 DEVICE display."
                ::= { tn3270ScreenEntry 2 }


            tn3270ScreenStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { tn3270ScreenEntry 3 }


            tn3270ScreenCharacterSequence OBJECT-TYPE
                SYNTAX OCTET STRING (SIZE (0..15))
                ACCESS read-write
                STATUS mandatory
                DESCRIPTION
                    "The ASCII character sequence for the screen action.  
                    Some actions may have a lesser length limit.  
                    Corresponds directly to the escape-sequence portion 
                    of SERVER TN3270 DEVICE SCREENMAP and the value 
                    labeled 'HexCode' in the 'Screenmap: section of the 
                    SERVER TN3270 DEVICE display."
                ::= { tn3270ScreenEntry 4 }

            -- The Language table

            tn3270LanguageTable OBJECT-TYPE
                SYNTAX SEQUENCE OF Tn3270LanguageEntry
                ACCESS not-accessible
                STATUS mandatory
                DESCRIPTION
                    "A list of tn3270 language entries."
                ::= { tn3270 7 }


            tn3270LanguageEntry OBJECT-TYPE
                SYNTAX Tn3270LanguageEntry
                ACCESS not-accessible
                STATUS mandatory
                DESCRIPTION
                    "Tn3270 parameter values for a language entry."
                INDEX { tn3270LanguageName }
                ::= { tn3270LanguageTable 1 }

            Tn3270LanguageEntry ::=
                SEQUENCE {
                    tn3270LanguageName
                        DisplayString,
                    tn3270LanguageStatus
                        INTEGER
                }

            tn3270LanguageName OBJECT-TYPE
                SYNTAX DisplayString (SIZE (1..8))
                ACCESS read-write
                STATUS mandatory
                DESCRIPTION
                    "The name of language for character translation 
                    tables.  Corresponds directly to SERVER TN3270 
                    LANGUAGE and the value labeled 'Language Name:' in 
                    the SERVER LANGUAGE display."
                ::= { tn3270LanguageEntry 1 }


            tn3270LanguageStatus OBJECT-TYPE
                SYNTAX INTEGER { invalid(1), valid(2) }
                ACCESS read-write
                STATUS mandatory
                DESCRIPTION
                    "Status of this entry.  Setting the value to 
                    'invalid' invalidates the entry.  It is an 
                    implementation-specific matter as to whether the 
                    agent removes an invalidated entry from the table."
                DEFVAL { valid }
                ::= { tn3270LanguageEntry 2 }

            -- The Language EBCDIC to ASCII table

            eToALanguageTable OBJECT-TYPE
                SYNTAX SEQUENCE OF EToALanguageEntry
                ACCESS not-accessible
                STATUS mandatory
                DESCRIPTION
                    "A list of language EBCDIC to ASCII conversion 
                    entries."
                ::= { tn3270 8 }


            eToALanguageEntry OBJECT-TYPE
                SYNTAX EToALanguageEntry
                ACCESS not-accessible
                STATUS mandatory
                DESCRIPTION
                    "EBCDIC to ASCII parameter values for a language 
                    entry."
                INDEX { eToALanguageName, eToAOffset }
                ::= { eToALanguageTable 1 }

            EToALanguageEntry ::=
                SEQUENCE {
                    eToALanguageName
                        DisplayString,
                    eToAOffset
                        INTEGER,
                    eToAValue
                        INTEGER
                }

            eToALanguageName OBJECT-TYPE
                SYNTAX DisplayString (SIZE (1..8))
                ACCESS read-only
                STATUS mandatory
                DESCRIPTION
                    "The name of language from the language table."
                ::= { eToALanguageEntry 1 }


            eToAOffset OBJECT-TYPE
                SYNTAX INTEGER (65..256)
                ACCESS read-only
                STATUS mandatory
                DESCRIPTION
                    "EBCDIC character offset plus one, that is, the 
                    value 1 corresponds to an operational offset of 0.  
                    Corresponds directly to the offset portion of SERVER 
                    TN3270 LANGUAGE and the hexadecimal labels around 
                    the conversion table labeled 'EBCDIC to ASCII' in 
                    the SERVER LANGUAGE display."
                ::= { eToALanguageEntry 2 }


            eToAValue OBJECT-TYPE
                SYNTAX INTEGER (32..255)
                ACCESS read-write
                STATUS mandatory
                DESCRIPTION
                    "ASCII character value for the EBCDIC offset.  
                    Corresponds directly to the value portion of SERVER 
                    TN3270 LANGUAGE and the values in the conversion 
                    table labeled 'EBCDIC to ASCII' in the SERVER 
                    LANGUAGE display."
                ::= { eToALanguageEntry 3 }

            -- The Language ASCII to EBCDIC table

            aToELanguageTable OBJECT-TYPE
                SYNTAX SEQUENCE OF AToELanguageEntry
                ACCESS not-accessible
                STATUS mandatory
                DESCRIPTION
                    "A list of language ASCII to EBCDIC conversion 
                    entries."
                ::= { tn3270 9 }


            aToELanguageEntry OBJECT-TYPE
                SYNTAX AToELanguageEntry
                ACCESS not-accessible
                STATUS mandatory
                DESCRIPTION
                    "ASCII to EBCDIC parameter values for a language 
                    entry."
                INDEX { aToELanguageName, aToEOffset }
                ::= { aToELanguageTable 1 }

            AToELanguageEntry ::=
                SEQUENCE {
                    aToELanguageName
                        DisplayString,
                    aToEOffset
                        INTEGER,
                    aToEValue
                        INTEGER
                }

            aToELanguageName OBJECT-TYPE
                SYNTAX DisplayString (SIZE (1..8))
                ACCESS read-only
                STATUS mandatory
                DESCRIPTION
                    "The name of language from the language table."
                ::= { aToELanguageEntry 1 }


            aToEOffset OBJECT-TYPE
                SYNTAX INTEGER (33..256)
                ACCESS read-only
                STATUS mandatory
                DESCRIPTION
                    "ASCII character offset plus one, that is, the value 
                    1 corresponds to an operational offset of 0.  
                    Corresponds directly to the offset portion of SERVER 
                    TN3270 LANGUAGE and the hexadecimal labels around 
                    the conversion table labeled 'ASCII to EBCDIC' in 
                    the SERVER LANGUAGE display."
                ::= { aToELanguageEntry 2 }


            aToEValue OBJECT-TYPE
                SYNTAX INTEGER (64..255)
                ACCESS read-write
                STATUS mandatory
                DESCRIPTION
                    "EBCDIC character value for the ASCII offset.  
                    Corresponds directly to the value portion of SERVER 
                    TN3270 LANGUAGE and the values in the conversion 
                    table labeled 'ASCII to EBCDIC' in the SERVER 
                    LANGUAGE display."
                ::= { aToELanguageEntry 3 }

            -- the tn3270 Port table

            tn3270PortTable OBJECT-TYPE
                SYNTAX SEQUENCE OF Tn3270PortEntry
                ACCESS not-accessible
                STATUS mandatory
                DESCRIPTION
                    "A list of tn3270 character port entries."
                ::= { tn3270 10 }


            tn3270PortEntry OBJECT-TYPE
                SYNTAX Tn3270PortEntry
                ACCESS not-accessible
                STATUS mandatory
                DESCRIPTION
                    "Parameter values for a tn3270 port."
                INDEX { tn3270PortIndex }
                ::= { tn3270PortTable 1 }

            Tn3270PortEntry ::=
                SEQUENCE {
                    tn3270PortIndex
                        INTEGER,
                    tn3270PortDeviceName
                        DisplayString,
                    tn3270PortLanguageName
                        DisplayString,
                    tn3270PortExtendedAttributes
                        INTEGER,
                    tn3270PortEorNegotiation
                        INTEGER,
                    tn3270PortErrorLock
                        INTEGER
                }

            tn3270PortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { tn3270PortEntry 1 }


            tn3270PortDeviceName OBJECT-TYPE
                SYNTAX DisplayString (SIZE (1..8))
                ACCESS read-write
                STATUS mandatory
                DESCRIPTION
                    "The name of a generic terminal device from the 
                    tn3270 device table.  Corresponds directly to PORT 
                    TELNET TN3270 DEVICE and the value labeled 'Tn3270 
                    Device:' in the PORT TELNET display."
                ::= { tn3270PortEntry 2 }


            tn3270PortLanguageName OBJECT-TYPE
                SYNTAX DisplayString (SIZE (1..8))
                ACCESS read-write
                STATUS mandatory
                DESCRIPTION
                    "The name of language from the tn3270 language 
                    table.  Corresponds directly to PORT TELNET TN3270 
                    LANGUAGE and the value labeled 'Tn3270 Language:' in 
                    the PORT TELNET display."
                ::= { tn3270PortEntry 3 }


            tn3270PortExtendedAttributes OBJECT-TYPE
                SYNTAX INTEGER { disabled(1), enabled(2) }
                ACCESS read-write
                STATUS mandatory
                DESCRIPTION
                    "A control indicating that certain 3270 extended 
                    attributes are supported on the port.  Corresponds 
                    directly to PORT TELNET TN3270 XTDATTRS and the 
                    label 'Tn3270 XtdAttrs' following the label 'Enabled 
                    Characteristics' in the PORT TELNET display."
                ::= { tn3270PortEntry 4 }


            tn3270PortEorNegotiation OBJECT-TYPE
                SYNTAX INTEGER { disabled(1), enabled(2) }
                ACCESS read-write
                STATUS mandatory
                DESCRIPTION
                    "A control for negotiation of the Telnet EOR option 
                    when establishing a tn3270 session on the port.  
                    Corresponds directly to PORT TELNET TN3270 EOR and 
                    the label 'Tn3270 EOR' following the label 'Enabled 
                    Characteristics' in the PORT TELNET display."
                ::= { tn3270PortEntry 5 }


            tn3270PortErrorLock OBJECT-TYPE
                SYNTAX INTEGER { disabled(1), enabled(2) }
                ACCESS read-write
                STATUS mandatory
                DESCRIPTION
                    "A control for requiring use the RESET key when the 
                    host reports an error during a tn3270 session on the 
                    port.  Corresponds directly to PORT TELNET TN3270 
                    ERRORLOCK and the label 'Tn3270 ErrorLock' following 
                    the label 'Enabled Characteristics' in the PORT 
                    TELNET display."
                ::= { tn3270PortEntry 6 }

            -- the Kerberos group
            -- Implementation of this group is mandatory for all Xyplex
            -- systems that implement a Kerberos client

            kerbStatus OBJECT-TYPE
                SYNTAX INTEGER { none(1), login(2) }
                ACCESS read-write
                STATUS mandatory
                DESCRIPTION
                    "A control indicating the level of Kerberos 
                    operation on the system.  Corresponds directly to 
                    SERVER KERBEROS STATUS and the value labeled 
                    'Kerberos Security:' in the SERVER KERBEROS 
                    display."
                ::= { kerberos 1 }


            kerbRealm OBJECT-TYPE
                SYNTAX DisplayString (SIZE (0..40))
                ACCESS read-write
                STATUS mandatory
                DESCRIPTION
                    "The Kerberos realm with which the kerbServerName1 
                    and kerbServerName2 are associated.  Corresponds 
                    directly to SERVER KERBEROS REALM and the value 
                    labeled 'Kerberos Realm:' in the SERVER KERBEROS 
                    display."
                ::= { kerberos 2 }


            kerbQueryLimit OBJECT-TYPE
                SYNTAX INTEGER (1..16)
                ACCESS read-write
                STATUS mandatory
                DESCRIPTION
                    "The maximum number of attempts the system can make 
                    when trying to verify a Kerberos ID.  Corresponds 
                    directly to SERVER KERBEROS QUERY LIMIT and the 
                    value labeled 'Kerberos Query Limit:' in the SERVER 
                    KERBEROS display."
                ::= { kerberos 3 }


            kerbMasterName OBJECT-TYPE
                SYNTAX DisplayString (SIZE (0..50))
                ACCESS read-write
                STATUS mandatory
                DESCRIPTION
                    "The Domain name of the Kerberos master host system, 
                    which holds the Kerberos database.  Corresponds 
                    directly to SERVER KERBEROS MASTER and the value 
                    labeled 'Kerberos Master:' in the SERVER KERBEROS 
                    display."
                ::= { kerberos 4 }


            kerbServerName1 OBJECT-TYPE
                SYNTAX DisplayString (SIZE (0..50))
                ACCESS read-write
                STATUS mandatory
                DESCRIPTION
                    "The Domain name of the first Kerberos server to try 
                    when the system verifys a Kerberos ID.  Corresponds 
                    directly to SERVER KERBEROS PRIMARY SERVER and the 
                    value labeled 'Kerberos Primary Server:' in the 
                    SERVER KERBEROS display."
                ::= { kerberos 5 }


            kerbServerName2 OBJECT-TYPE
                SYNTAX DisplayString (SIZE (0..50))
                ACCESS read-write
                STATUS mandatory
                DESCRIPTION
                    "The Domain name of the Kerberos server to try when 
                    the system verifys a Kerberos ID and cannot reach 
                    the Kerberos primary server.  Corresponds directly 
                    to SERVER KERBEROS SECONDARY SERVER and the value 
                    labeled 'Kerberos Secondary Server:' in the SERVER 
                    KERBEROS display."
                ::= { kerberos 6 }


            kerbInsecureLogins OBJECT-TYPE
                SYNTAX Counter
                ACCESS read-only
                STATUS mandatory
                DESCRIPTION
                    "The number of user logins on ports for which 
                    Kerberos user verification is not enabled.  
                    Corresponds directly to the value labeled 'Logins 
                    without Kerberos:' in the SERVER KERBEROS display."
                ::= { kerberos 7 }


            kerbSecureLogins OBJECT-TYPE
                SYNTAX Counter
                ACCESS read-only
                STATUS mandatory
                DESCRIPTION
                    "The number of successful user logins on ports for 
                    which Kerberos user verification is enabled.  
                    Corresponds directly to the value labeled 
                    'Successful Logins:' in the SERVER KERBEROS 
                    display."
                ::= { kerberos 8 }


            kerbSecureLoginsFailed OBJECT-TYPE
                SYNTAX Counter
                ACCESS read-only
                STATUS mandatory
                DESCRIPTION
                    "The number of verification failures due to 
                    incorrect ID or password for attempted user logins 
                    on ports for which Kerberos user verification is 
                    enabled.  Corresponds directly to the value labeled 
                    'Unsuccessful Logins:' in the SERVER KERBEROS 
                    display."
                ::= { kerberos 9 }


            kerbPasswordChangeFailed OBJECT-TYPE
                SYNTAX Counter
                ACCESS read-only
                STATUS mandatory
                DESCRIPTION
                    "The number of user failures to change their 
                    Kerberos password due to invalid old password or new 
                    password verification.  Corresponds directly to the 
                    value labeled 'Password Change Failures:' in the 
                    SERVER KERBEROS display."
                ::= { kerberos 10 }


            kerbError OBJECT-TYPE
                SYNTAX INTEGER
                ACCESS read-only
                STATUS mandatory
                DESCRIPTION
                    "The error number of the most recent 
                    Kerberos-related failure.  Corresponds directly to 
                    the value labeled 'Last Kerberos Error:' in the 
                    SERVER KERBEROS display.  For a list of error 
                    numbers and their meanings, consult relevant Xyplex 
                    or Kerberos documentation."
                ::= { kerberos 11 }


            kerbErrorTime OBJECT-TYPE
                SYNTAX DateTime
                ACCESS read-only
                STATUS mandatory
                DESCRIPTION
                    "The date and time that kerbError was last updated.  
                    Corresponds directly to the value labeled 
                    'Occurred:' in the SERVER KERBEROS display."
                ::= { kerberos 12 }


            kerbMasterAccess OBJECT-TYPE
                SYNTAX Counter
                ACCESS read-only
                STATUS mandatory
                DESCRIPTION
                    "The number of times the system successfully 
                    accessed the Kerberos master host.  Corresponds 
                    directly to the value labeled 'Attempts to access:', 
                    'Master', and 'Successful:' in the SERVER KERBEROS 
                    display."
                ::= { kerberos 13 }


            kerbMasterAccessFailed OBJECT-TYPE
                SYNTAX Counter
                ACCESS read-only
                STATUS mandatory
                DESCRIPTION
                    "The number of times the system failed access to the 
                    Kerberos master host.  Corresponds directly to the 
                    value labeled 'Attempts to access:', 'Master', and 
                    'Unsuccessful:' in the SERVER KERBEROS display."
                ::= { kerberos 14 }


            kerbServerAccess1 OBJECT-TYPE
                SYNTAX Counter
                ACCESS read-only
                STATUS mandatory
                DESCRIPTION
                    "The number of times the system successfully 
                    accessed the Kerberos primary server.  Corresponds 
                    directly to the value labeled 'Attempts to access:', 
                    'Server1', and 'Successful:' in the SERVER KERBEROS 
                    display."
                ::= { kerberos 15 }


            kerbServerAccessFailed1 OBJECT-TYPE
                SYNTAX Counter
                ACCESS read-only
                STATUS mandatory
                DESCRIPTION
                    "The number of times the system failed access to the 
                    Kerberos primary server.  Corresponds directly to 
                    the value labeled 'Attempts to access:', 'Server1', 
                    and 'Unsuccessful:' in the SERVER KERBEROS 
                    display."
                ::= { kerberos 16 }


            kerbServerAccess2 OBJECT-TYPE
                SYNTAX Counter
                ACCESS read-only
                STATUS mandatory
                DESCRIPTION
                    "The number of times the system successfully 
                    accessed the Kerberos secondary server.  Corresponds 
                    directly to the value labeled 'Attempts to access:', 
                    'Server2', and 'Successful:' in the SERVER KERBEROS 
                    display."
                ::= { kerberos 17 }


            kerbServerAccessFailed2 OBJECT-TYPE
                SYNTAX Counter
                ACCESS read-only
                STATUS mandatory
                DESCRIPTION
                    "The number of times the system failed access to the 
                    Kerberos secondary server.  Corresponds directly to 
                    the value labeled 'Attempts to access:', 'Server2', 
                    and 'Unsuccessful:' in the SERVER KERBEROS 
                    display."
                ::= { kerberos 18 }

            -- the Kerberos Port table

            kerbPortTable OBJECT-TYPE
                SYNTAX SEQUENCE OF KerbPortEntry
                ACCESS not-accessible
                STATUS mandatory
                DESCRIPTION
                    "A list of Kerberos character port entries."
                ::= { kerberos 19 }


            kerbPortEntry OBJECT-TYPE
                SYNTAX KerbPortEntry
                ACCESS not-accessible
                STATUS mandatory
                DESCRIPTION
                    "Parameter values for a Kerberos port."
                INDEX { kerbPortIndex }
                ::= { kerbPortTable 1 }

            KerbPortEntry ::=
                SEQUENCE {
                    kerbPortIndex
                        INTEGER,
                    kerbPortStatus
                        INTEGER
                }

            kerbPortIndex OBJECT-TYPE
                SYNTAX INTEGER
                ACCESS read-only
                STATUS mandatory
                DESCRIPTION
                    "An index value that uniquely identifies a port 
                    could relate to Kerberos.  The port identified by a 
                    particular value of this index is the same port as 
                    identified by charPortIndex in the Character 
                    MIB [11]."
                ::= { kerbPortEntry 1 }


            kerbPortStatus OBJECT-TYPE
                SYNTAX INTEGER { none(1), login(2) }
                ACCESS read-write
                STATUS mandatory
                DESCRIPTION
                    "A control indicating the level of Kerberos 
                    operation on the port.  Corresponds directly to PORT 
                    KERBEROS and the value 'Kerberos' following the 
                    label 'Enabled Characteristics' in the PORT 
                    CHARACTERISTICS display."
                ::= { kerbPortEntry 2 }

            -- the Port Security group
            -- Implementation of this group is mandatory for all Xyplex
            -- systems that implement Internet port security

            psEntryNumber OBJECT-TYPE
                SYNTAX INTEGER
                ACCESS read-only
                STATUS mandatory
                DESCRIPTION
                    "The number of security entries in this system's 
                    port security table with psEntryStatus of 'valid'."
                ::= { portSecurity 1 }


            psEntryNumberLimit OBJECT-TYPE
                SYNTAX INTEGER
                ACCESS read-only
                STATUS mandatory
                DESCRIPTION
                    "The maximum number of security entries in this 
                    system's port security table."
                ::= { portSecurity 2 }


            psEntryInvalidIndex OBJECT-TYPE
                SYNTAX INTEGER
                ACCESS read-only
                STATUS mandatory
                DESCRIPTION
                    "A value of psEntryIndex for an entry that has 
                    psEntryStatus of 'invalid'.  A management station 
                    may choose this value when adding a new entry.  
                    Collisions between independent management stations 
                    simultaneously using the same number are beyond the 
                    scope of this document."
                ::= { portSecurity 3 }

            -- the Port Security table

            psPortTable OBJECT-TYPE
                SYNTAX SEQUENCE OF PsPortEntry
                ACCESS not-accessible
                STATUS mandatory
                DESCRIPTION
                    "A list of port security character port entries."
                ::= { portSecurity 4 }


            psPortEntry OBJECT-TYPE
                SYNTAX PsPortEntry
                ACCESS not-accessible
                STATUS mandatory
                DESCRIPTION
                    "Port security parameter values for a port."
                INDEX { psPortIndex }
                ::= { psPortTable 1 }

            PsPortEntry ::=
                SEQUENCE {
                    psPortIndex
                        INTEGER,
                    psPortDefaultInboundAccess
                        INTEGER,
                    psPortDefaultOutboundAccess
                        INTEGER
                }

            psPortIndex OBJECT-TYPE
                SYNTAX INTEGER
                ACCESS read-only
                STATUS mandatory
                DESCRIPTION
                    "An index value that uniquely identifies a port for 
                    security purposes.  The port identified by a 
                    particular value of this index is the same port as 
                    identified by charPortIndex in the Proposed Standard 
                    Internet Character MIB."
                ::= { psPortEntry 1 }


            psPortDefaultInboundAccess OBJECT-TYPE
                SYNTAX INTEGER { allow(1), deny(2) }
                ACCESS read-write
                STATUS mandatory
                DESCRIPTION
                    "The default access to the port for incoming TCP 
                    connections.  Corresponds directly to PORT INTERNET 
                    SECURITY DEFAULT INBOUND and the value labeled 
                    'Inbound Default:' in the PORT INTERNET SECURITY 
                    display."
                ::= { psPortEntry 2 }


            psPortDefaultOutboundAccess OBJECT-TYPE
                SYNTAX INTEGER { allow(1), deny(2) }
                ACCESS read-write
                STATUS mandatory
                DESCRIPTION
                    "The default access to the port for outgoing TCP 
                    connections.  Corresponds directly to PORT INTERNET 
                    SECURITY DEFAULT OUTBOUND and the value labeled 
                    'Outbound Default:' in the PORT INTERNET SECURITY 
                    display."
                ::= { psPortEntry 3 }

            -- the Port Security table

            psTable OBJECT-TYPE
                SYNTAX SEQUENCE OF PsEntry
                ACCESS not-accessible
                STATUS mandatory
                DESCRIPTION
                    "A list of port security entries."
                ::= { portSecurity 5 }


            psEntry OBJECT-TYPE
                SYNTAX PsEntry
                ACCESS not-accessible
                STATUS mandatory
                DESCRIPTION
                    "Port security parameter values for an entry for a 
                    port."
                INDEX { psEntryIndex }
                ::= { psTable 1 }

            PsEntry ::=
                SEQUENCE {
                    psEntryIndex
                        INTEGER,
                    psEntryStatus
                        INTEGER,
                    psEntryAddress
                        IpAddress,
                    psEntryMask
                        IpAddress,
                    psEntryAccess
                        INTEGER,
                    psEntryDirection
                        INTEGER,
                    psEntryPortMap
                        OCTET STRING
                }

            psEntryIndex OBJECT-TYPE
                SYNTAX INTEGER
                ACCESS read-only
                STATUS mandatory
                DESCRIPTION
                    "A small, numeric distinguisher for port security 
                    entries.  When adding a new entry, the client should 
                    specify an unused value, such as 
                    psEntryInvalidIndex.  Corresponds directly to the 
                    value labeled 'Entry' in the SERVER INTERNET 
                    SECURITY display."
                ::= { psEntry 1 }


            psEntryStatus OBJECT-TYPE
                SYNTAX INTEGER { invalid(1), valid(2) }
                ACCESS read-write
                STATUS mandatory
                DESCRIPTION
                    "Status of this entry.  Setting the value to 
                    'invalid' invalidates the entry, corresponding 
                    directly to the CLEAR INTERNET SECURITY command.  It 
                    is an implementation-specific matter as to whether 
                    the agent removes an invalidated entry from the 
                    table.  When creating a new instance, 
                    psEntryAddress, psEntryMask, psEntryAccess, and 
                    psEntryDirection for the new instance must be 
                    present in the set request."
                DEFVAL { valid }
                ::= { psEntry 2 }


            psEntryAddress OBJECT-TYPE
                SYNTAX IpAddress
                ACCESS read-write
                STATUS mandatory
                DESCRIPTION
                    "The IP address to which the entry pertains.  
                    Corresponds directly to the PORT INTERNET SECURITY 
                    internet address and the value labeled 'Internet 
                    Address' in the SERVER INTERNET SECURITY display."
                ::= { psEntry 3 }


            psEntryMask OBJECT-TYPE
                SYNTAX IpAddress
                ACCESS read-write
                STATUS mandatory
                DESCRIPTION
                    "The mask applied to psEntryAddress when making a 
                    security check based on this entry.  Corresponds 
                    directly to PORT INTERNET SECURITY MASK and the 
                    value labeled 'Security Mask' in the SERVER INTERNET 
                    SECURITY display."
                ::= { psEntry 4 }


            psEntryAccess OBJECT-TYPE
                SYNTAX INTEGER { allow(1), deny(2) }
                ACCESS read-write
                STATUS mandatory
                DESCRIPTION
                    "The access to the port for TCP connections when 
                    making a security check based on this entry.  
                    Corresponds directly to PORT INTERNET SECURITY ALLOW 
                    or DENY and the value labeled 'Access' in the SERVER 
                    INTERNET SECURITY display."
                ::= { psEntry 5 }


            psEntryDirection OBJECT-TYPE
                SYNTAX INTEGER { inbound(1), outbound(2) }
                ACCESS read-write
                STATUS mandatory
                DESCRIPTION
                    "The direction of TCP connections to which this 
                    entry applies.  Corresponds directly to PORT 
                    INTERNET SECURITY INBOUND or OUTBOUND and the value 
                    labeled 'Direction' in the SERVER INTERNET SECURITY 
                    display."
                ::= { psEntry 6 }


            psEntryPortMap OBJECT-TYPE
                SYNTAX OCTET STRING
                ACCESS read-write
                STATUS mandatory
                DESCRIPTION
                    "The list of character ports to which this entry 
                    applies.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to PORT INTERNET SECURITY and 
                    the value labeled 'Ports' in the SERVER INTERNET 
                    SECURITY display."
                ::= { psEntry 7 }

            -- the XREMOTE group
            -- Implementation of this group is mandatory for all Xyplex
            -- systems that implement XREMOTE

            xremoteServerName1 OBJECT-TYPE
                SYNTAX DisplayString (SIZE (0..50))
                ACCESS read-write
                STATUS mandatory
                DESCRIPTION
                    "The Domain name of the first XREMOTE font server to 
                    try for downloading fonts.  Corresponds directly to 
                    SERVER XREMOTE PRIMARY SERVER and the value labeled 
                    'Xremote Primary Font Server:' in the SERVER XREMOTE 
                    display."
                ::= { xremote 1 }


            xremoteServerName2 OBJECT-TYPE
                SYNTAX DisplayString (SIZE (0..50))
                ACCESS read-write
                STATUS mandatory
                DESCRIPTION
                    "The Domain name of the XREMOTE font server to try 
                    for downloading fonts and the primary font server 
                    does not respond.  Corresponds directly to SERVER 
                    XREMOTE SECONDARY SERVER and the value labeled 
                    'Xremote Secondary Font Server:' in the SERVER 
                    XREMOTE display."
                ::= { xremote 2 }


            xremoteServerAccess1 OBJECT-TYPE
                SYNTAX Counter
                ACCESS read-only
                STATUS mandatory
                DESCRIPTION
                    "The number of times the system successfully 
                    accessed the XREMOTE primary font server.  
                    Corresponds directly to the value labeled 'Attempts 
                    to access:', 'Server1', and 'Successful:' in the 
                    SERVER XREMOTE display."
                ::= { xremote 3 }


            xremoteServerAccessFailed1 OBJECT-TYPE
                SYNTAX Counter
                ACCESS read-only
                STATUS mandatory
                DESCRIPTION
                    "The number of times the system failed access to the 
                    XREMOTE primary font server.  Corresponds directly 
                    to the value labeled 'Attempts to access:', 
                    'Server1', and 'Unsuccessful:' in the SERVER XREMOTE 
                    display."
                ::= { xremote 4 }


            xremoteServerAccess2 OBJECT-TYPE
                SYNTAX Counter
                ACCESS read-only
                STATUS mandatory
                DESCRIPTION
                    "The number of times the system successfully 
                    accessed the XREMOTE secondary font server.  
                    Corresponds directly to the value labeled 'Attempts 
                    to access:', 'Server2', and 'Successful:' in the 
                    SERVER XREMOTE display."
                ::= { xremote 5 }


            xremoteServerAccessFailed2 OBJECT-TYPE
                SYNTAX Counter
                ACCESS read-only
                STATUS mandatory
                DESCRIPTION
                    "The number of times the system failed access to the 
                    XREMOTE secondary font server.  Corresponds directly 
                    to the value labeled 'Attempts to access:', 
                    'Server2', and 'Unsuccessful:' in the SERVER XREMOTE 
                    display."
                ::= { xremote 6 }


            xremoteSessions OBJECT-TYPE
                SYNTAX Gauge
                ACCESS read-only
                STATUS mandatory
                DESCRIPTION
                    "The number of connected XREMOTE sessions.  
                    Corresponds directly to the value labeled 'Current 
                    Number of Xremote Sessions:' in the SERVER XREMOTE 
                    display."
                ::= { xremote 7 }

            -- Additional individual objects follow port table
            -- the XREMOTE Port table

            xremotePortTable OBJECT-TYPE
                SYNTAX SEQUENCE OF XremotePortEntry
                ACCESS not-accessible
                STATUS mandatory
                DESCRIPTION
                    "A list of XREMOTE character port entries."
                ::= { xremote 8 }


            xremotePortEntry OBJECT-TYPE
                SYNTAX XremotePortEntry
                ACCESS not-accessible
                STATUS mandatory
                DESCRIPTION
                    "XREMOTE parameter values for a port."
                INDEX { psPortIndex }
                ::= { xremotePortTable 1 }

            XremotePortEntry ::=
                SEQUENCE {
                    psPortIndex
                        INTEGER,
                    xremotePortIndex
                        INTEGER,
                    xremotePortXremote
                        INTEGER,
                    xremotePortXdmQuery
                        INTEGER,
                    xremotePortXdmHost
                        DisplayString
                }

            xremotePortIndex OBJECT-TYPE
                SYNTAX INTEGER
                ACCESS read-only
                STATUS mandatory
                DESCRIPTION
                    "An index value that uniquely identifies a port.  
                    The port identified by a particular value of this 
                    index is the same port as identified by 
                    charPortIndex in the Proposed Standard Internet 
                    Character MIB."
                ::= { xremotePortEntry 1 }


            xremotePortXremote OBJECT-TYPE
                SYNTAX INTEGER { disabled(1), enabled(2) }
                ACCESS read-write
                STATUS mandatory
                DESCRIPTION
                    "Control for use of XREMOTE on the port.  
                    Corresponds directly to PORT XREMOTE and the 
                    presence of the label 'Xremote' following the label 
                    'Enabled Characteristics:' in the PORT 
                    CHARACTERISTICS display."
                ::= { xremotePortEntry 2 }


            xremotePortXdmQuery OBJECT-TYPE
                SYNTAX INTEGER { specific(1), broadcast(2),
                                 indirect(3) }
                ACCESS read-write
                STATUS mandatory
                DESCRIPTION
                    "The type of query message issued by a port when 
                    searching for an X Display Manager (XDM). 
                    Corresponds directly to the PORT XDM QUERY and the 
                    'XDM Query:' in the PORT ALTERNATE CHARACTERISTICS 
                    display"
                ::= { xremotePortEntry 3 }


            xremotePortXdmHost OBJECT-TYPE
                SYNTAX DisplayString (SIZE (0..50))
                ACCESS read-write
                STATUS mandatory
                DESCRIPTION
                    "The Domain name or Internet address of the X 
                    Display Manager (XDM) for a port. Corresponds 
                    directly to the PORT XDM HOST and the 'XDM Host:' in 
                    the PORT ALTERNATE CHARACTERISTICS display"
                ::= { xremotePortEntry 4 }

            -- Additional individual objects

            xremoteServerClients OBJECT-TYPE
                SYNTAX Gauge
                ACCESS read-only
                STATUS mandatory
                DESCRIPTION
                    "The number of active X clients.  Corresponds 
                    directly to the value labeled 'Current Number of 
                    XClients:' in the SERVER XREMOTE display."
                ::= { xremote 9 }

            -- the Rotary group
            -- Implementation of this group is mandatory for all Xyplex
            -- systems that implement rotaries

            rotaryNumber OBJECT-TYPE
                SYNTAX INTEGER
                ACCESS read-only
                STATUS mandatory
                DESCRIPTION
                    "The number of entries in the Rotary  table."
                ::= { rotary 1 }

            -- The Rotary  table

            rotaryTable OBJECT-TYPE
                SYNTAX SEQUENCE OF RotaryEntry
                ACCESS not-accessible
                STATUS mandatory
                DESCRIPTION
                    "A list of rotary  entries."
                ::= { rotary 2 }


            rotaryEntry OBJECT-TYPE
                SYNTAX RotaryEntry
                ACCESS not-accessible
                STATUS mandatory
                DESCRIPTION
                    "Parameter values for a rotary."
                INDEX { rotaryAddress }
                ::= { rotaryTable 1 }

            RotaryEntry ::=
                SEQUENCE {
                    rotaryAddress
                        IpAddress,
                    rotaryStatus
                        INTEGER,
                    rotaryPortMap
                        OCTET STRING
                }

            rotaryAddress OBJECT-TYPE
                SYNTAX IpAddress
                ACCESS read-write
                STATUS mandatory
                DESCRIPTION
                    "The internet address to be recognized as a rotary.  
                    Corresponds directly to the ip-address portion of 
                    SERVER INTERNET ROTARY and the value labeled 
                    'Internet Address' in the SERVER INTERNET ROTARY 
                    display."
                ::= { rotaryEntry 1 }


            rotaryStatus OBJECT-TYPE
                SYNTAX INTEGER { invalid(1), valid(2) }
                ACCESS read-write
                STATUS mandatory
                DESCRIPTION
                    "Status of this entry.  Setting the value to 
                    'invalid' invalidates the entry, corresponding 
                    directly to the CLEAR SERVER INTERNET ROTARY 
                    command.  It is an implementation-specific matter as 
                    to whether the agent removes an invalidated entry 
                    from the table."
                DEFVAL { valid }
                ::= { rotaryEntry 2 }


            rotaryPortMap OBJECT-TYPE
                SYNTAX OCTET STRING
                ACCESS read-write
                STATUS mandatory
                DESCRIPTION
                    "The list of character ports that compose the 
                    rotary.  The OCTET STRING contains a bitmap, with 
                    one bit for each port, and enough octets for all the 
                    ports on the system.  Port numbers are as defined 
                    for charPortIndex in the Proposed Standard Internet 
                    Character MIB.  Corresponding bit numbers start with 
                    1 as the high-order bit of the first octet.  
                    Corresponds directly to port-list portion of SERVER 
                    INTERNET ROTARY and the value labeled 'Ports' in the 
                    SERVER INTERNET ROTARY display."
                ::= { rotaryEntry 3 }

-- end of Xyplex Internet Systems MIB


-- Xyplex LAT MIB


            lat             OBJECT IDENTIFIER ::= { xyplex 3 }

            -- This MIB module uses the extended OBJECT-TYPE macro as
            -- defined in [9]
            -- This is a MIB module for all Xyplex systems that
            -- implement LAT
            -- the LAT group
            -- Implementation of this group is mandatory for all Xyplex
            -- systems that implement LAT

            latAnnounceServices OBJECT-TYPE
                SYNTAX INTEGER { disabled(1), enabled(2) }
                ACCESS read-write
                STATUS mandatory
                DESCRIPTION
                    "Control for automatic, periodic announcement of 
                    local services to the network.  Corresponds directly 
                    to SERVER ANNOUNCEMENTS and the presence of the 
                    label 'Announcements' following the label 'Enabled 
                    Characteristics:' in the SERVER CHARACTERISTICS 
                    display."
                ::= { lat 1 }


            latCircuitTimer OBJECT-TYPE
                SYNTAX INTEGER (30..200)
                ACCESS read-write
                STATUS mandatory
                DESCRIPTION
                    "Number of milleseconds to collect port input data 
                    before sending it to the host.  Corresponds directly 
                    to SERVER CIRCUIT TIMER and the value labeled 
                    'Circuit Timer:' in the SERVER CHARACTERISTICS 
                    display."
                ::= { lat 2 }


            latIdentificationLengthLimit OBJECT-TYPE
                SYNTAX INTEGER (0..63)
                ACCESS read-write
                STATUS mandatory
                DESCRIPTION
                    "Maximum number of characters to store in the 
                    instances of latVisibleServiceIdentification.  
                    Corresponds directly to SERVER IDENTIFICATION SIZE 
                    and the value labeled 'Identification Size:' in the 
                    SERVER CHARACTERISTICS display."
                ::= { lat 3 }


            latKeepaliveTimer OBJECT-TYPE
                SYNTAX INTEGER (10..180)
                ACCESS read-write
                STATUS mandatory
                DESCRIPTION
                    "Number of seconds of inactivity before sending a 
                    null message to the host.  Corresponds directly to 
                    SERVER KEEPALIVE TIMER and the value labeled 
                    'Keepalive Timer:' in the SERVER CHARACTERISTICS 
                    display."
                ::= { lat 4 }


            latMulticastTimer OBJECT-TYPE
                SYNTAX INTEGER (10..180)
                ACCESS read-write
                STATUS mandatory
                DESCRIPTION
                    "Number of seconds between transmission of local 
                    service announcements.  Corresponds directly to 
                    SERVER MULTICAST TIMER and the value labeled 
                    'Multicast Timer:' in the SERVER CHARACTERISTICS 
                    display."
                ::= { lat 5 }


            latNodeLimit OBJECT-TYPE
                SYNTAX INTEGER (0..1000)
                ACCESS read-write
                STATUS mandatory
                DESCRIPTION
                    "Maximum number of service nodes to keep in the node 
                    table.  Corresponds directly to SERVER NODE LIMIT 
                    and the value labeled 'Node Limit:' in the SERVER 
                    CHARACTERISTICS display."
                ::= { lat 6 }


            latNumber OBJECT-TYPE
                SYNTAX INTEGER (0..32767)
                ACCESS read-write
                STATUS mandatory
                DESCRIPTION
                    "An arbitrary number assigned and used for 
                    administrative purposes.  Corresponds directly to 
                    SERVER NUMBER and the value labeled 'Number:' in the 
                    SERVER CHARACTERISTICS display."
                ::= { lat 7 }


            latRetransmitLimit OBJECT-TYPE
                SYNTAX INTEGER (4..120)
                ACCESS read-write
                STATUS mandatory
                DESCRIPTION
                    "Maximum number of times to retransmit an 
                    unacknowledged message.  Corresponds directly to 
                    SERVER RETRANSMIT LIMIT and the value labeled 
                    'Retransmit Limit:' in the SERVER CHARACTERISTICS 
                    display."
                ::= { lat 8 }


            latLocalServiceGroups OBJECT-TYPE
                SYNTAX OCTET STRING (SIZE (32))
                ACCESS read-write
                STATUS mandatory
                DESCRIPTION
                    "The list of group numbers allowed to use local 
                    services, where a group number is in the range 
                    0-255.  The OCTET STRING contains a bitmap, with one 
                    bit for each group.  Corresponding bit numbers start 
                    with 0 as the high-order bit of the first octet.  
                    Corresponds directly to SERVER SERVICE GROUPS and 
                    the value labeled 'Service Groups:' in the SERVER 
                    CHARACTERISTICS display."
                ::= { lat 9 }


            latGroupPurge OBJECT-TYPE
                SYNTAX INTEGER { disabled(1), enabled(2) }
                ACCESS read-write
                STATUS mandatory
                DESCRIPTION
                    "Control for automatic deletion of all node table 
                    entries when latServiceGroups or 
                    latPortCurrentGroups is changed.  Corresponds 
                    directly to SERVER PURGE GROUP and the presence of 
                    the label 'Purge Group' following the label 'Enabled 
                    Characteristics:' in the SERVER CHARACTERISTICS 
                    display."
                ::= { lat 10 }


            latNodePurge OBJECT-TYPE
                SYNTAX INTEGER { disabled(1), enabled(2) }
                ACCESS read-write
                STATUS mandatory
                DESCRIPTION
                    "Control for automatic deletion of all node table 
                    entries with status 'reachable' when the number of 
                    entries exceeds latNodeLimit.  Corresponds directly 
                    to SERVER PURGE NODE and the presence of the label 
                    'Purge Node' following the label 'Enabled 
                    Characteristics:' in the SERVER CHARACTERISTICS 
                    display."
                ::= { lat 11 }


            latNodesRejected OBJECT-TYPE
                SYNTAX Counter
                ACCESS read-only
                STATUS mandatory
                DESCRIPTION
                    "Number of nodes not added to the node table because 
                    there was no room.  Corresponds directly to the 
                    value labeled 'Discarded Nodes:' in the SERVER 
                    STATUS display."
                ::= { lat 12 }


            latInMessages OBJECT-TYPE
                SYNTAX Counter
                ACCESS read-only
                STATUS mandatory
                DESCRIPTION
                    "Number of LAT messages received.  Corresponds 
                    directly to the value labeled 'Messages Received:' 
                    in the SERVER COUNTERS display."
                ::= { lat 13 }


            latOutMessages OBJECT-TYPE
                SYNTAX Counter
                ACCESS read-only
                STATUS mandatory
                DESCRIPTION
                    "Number of LAT messages sent.  Corresponds directly 
                    to the value labeled 'Messages Transmitted:' in the 
                    SERVER COUNTERS display."
                ::= { lat 14 }


            latInSessionsAccepted OBJECT-TYPE
                SYNTAX Counter
                ACCESS read-only
                STATUS mandatory
                DESCRIPTION
                    "Number of incoming LAT session connection attempts 
                    accepted.  Corresponds directly to the value labeled 
                    'Solicitations Accepted:' in the SERVER COUNTERS 
                    display."
                ::= { lat 15 }


            latInSessionsRejected OBJECT-TYPE
                SYNTAX Counter
                ACCESS read-only
                STATUS mandatory
                DESCRIPTION
                    "Number of incoming LAT session connection attempts 
                    rejected.  Corresponds directly to the value labeled 
                    'Solicitations Rejected:' in the SERVER COUNTERS 
                    display."
                ::= { lat 16 }


            latAddressChange OBJECT-TYPE
                SYNTAX Counter
                ACCESS read-only
                STATUS mandatory
                DESCRIPTION
                    "Number of times a service announcement contained a 
                    node name already in the visible service table but 
                    with a different address.  Corresponds directly to 
                    the value labeled 'Multiple Node Addresses:' in the 
                    SERVER COUNTERS display."
                ::= { lat 17 }


            latInDuplicates OBJECT-TYPE
                SYNTAX Counter
                ACCESS read-only
                STATUS mandatory
                DESCRIPTION
                    "Number of duplicate LAT messages received.  
                    Corresponds directly to the value labeled 
                    'Duplicates Received:' in the SERVER COUNTERS 
                    display."
                ::= { lat 18 }


            latOutRetransmits OBJECT-TYPE
                SYNTAX Counter
                ACCESS read-only
                STATUS mandatory
                DESCRIPTION
                    "Number of LAT messages retransmitted due to no 
                    acknowledgement.  Corresponds directly to the value 
                    labeled 'Messages Re-transmitted:' in the SERVER 
                    COUNTERS display."
                ::= { lat 19 }


            latInBadMessages OBJECT-TYPE
                SYNTAX Counter
                ACCESS read-only
                STATUS mandatory
                DESCRIPTION
                    "Number of LAT messages received with invalid 
                    format.  Corresponds directly to the value labeled 
                    'Illegal Messages Rcv'd:' in the SERVER COUNTERS 
                    display."
                ::= { lat 20 }


            latInBadSlots OBJECT-TYPE
                SYNTAX Counter
                ACCESS read-only
                STATUS mandatory
                DESCRIPTION
                    "Number of LAT messages received with invalid slot 
                    format.  Corresponds directly to the value labeled 
                    'Illegal Slots Rcv'd:' in the SERVER COUNTERS 
                    display."
                ::= { lat 21 }


            latInBadMulticasts OBJECT-TYPE
                SYNTAX Counter
                ACCESS read-only
                STATUS mandatory
                DESCRIPTION
                    "Number of multicast LAT messages received with 
                    invalid format.  Corresponds directly to the value 
                    labeled 'Illegal Multicasts Rcv'd:' in the SERVER 
                    COUNTERS display."
                ::= { lat 22 }

            -- the LAT Port table

            latPortTable OBJECT-TYPE
                SYNTAX SEQUENCE OF LatPortEntry
                ACCESS not-accessible
                STATUS mandatory
                DESCRIPTION
                    "A list of LAT character port entries."
                ::= { lat 23 }


            latPortEntry OBJECT-TYPE
                SYNTAX LatPortEntry
                ACCESS not-accessible
                STATUS mandatory
                DESCRIPTION
                    "LAT parameter values for a port."
                INDEX { latPortIndex }
                ::= { latPortTable 1 }

            LatPortEntry ::=
                SEQUENCE {
                    latPortIndex
                        INTEGER,
                    latPortAuthorizedGroups
                        OCTET STRING,
                    latPortAutoPrompt
                        INTEGER,
                    latPortCurrentGroups
                        OCTET STRING,
                    latPortRemoteModification
                        INTEGER
                }

            latPortIndex OBJECT-TYPE
                SYNTAX INTEGER
                ACCESS read-only
                STATUS mandatory
                DESCRIPTION
                    "An index value that uniquely identifies a port.  
                    The port identified by a particular value of this 
                    index is the same port as identified by 
                    charPortIndex in the Character MIB [11]."
                ::= { latPortEntry 1 }


            latPortAuthorizedGroups OBJECT-TYPE
                SYNTAX OCTET STRING (SIZE (32))
                ACCESS read-write
                STATUS mandatory
                DESCRIPTION
                    "The list of group numbers to which the port is 
                    allowed to set access, where a group number is in 
                    the range 0-255.  The OCTET STRING contains a 
                    bitmap, with one bit for each group.  Corresponding 
                    bit numbers start with 0 as the high-order bit of 
                    the first octet.  Corresponds directly to PORT 
                    AUTHORIZED GROUPS and the value labeled 'Authorized 
                    Groups:' in the PORT
