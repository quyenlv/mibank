USR-GWCBSP-MIB DEFINITIONS ::= BEGIN
          IMPORTS
                MODULE-IDENTITY, OBJECT-TYPE, Integer32, IpAddress
                    FROM SNMPv2-SMI
                UsrConfigStatus, common, UsrDisplayString
                    FROM USR-DEFINITIONS-MIB;
usrGWCBSP MODULE-IDENTITY
         LAST-UPDATED "200201091935Z" -- January 9, 19:35, 2002
         ORGANIZATION "CommWorks Corporation, a 3Com Company"
         CONTACT-INFO "Customer Support"
         DESCRIPTION
                 "The commWorks enterprise defined MIB objects
                   for the GWC BSP specific platform"
         ::= { common 38 }
usrGWCBSPProductCode OBJECT-TYPE
        SYNTAX      OCTET STRING (SIZE(3))
	MAX-ACCESS  read-only
	STATUS      current
	DESCRIPTION
        	"The Code number assigned for the product"
	::= { usrGWCBSP 1}
usrGWCBSPHWVersion OBJECT-TYPE
	SYNTAX      OCTET STRING (SIZE(1 | 2))
	MAX-ACCESS  read-only
	STATUS      current
	DESCRIPTION
		"Hardware version number"
	::= { usrGWCBSP 2}
usrGWCBSPSerialNumber OBJECT-TYPE
	SYNTAX      OCTET STRING (SIZE(8))
	MAX-ACCESS  read-only
	STATUS      current
	DESCRIPTION
		"Serial number of the product"
	::= { usrGWCBSP 3}
usrGWCBSPCardID OBJECT-TYPE
	SYNTAX      Integer32
	MAX-ACCESS  read-only
	STATUS      current
	DESCRIPTION
		"Assigned card ID"
	::= { usrGWCBSP 4}
usrGWCBSPFeatureKey OBJECT-TYPE
	SYNTAX      OCTET STRING (SIZE(4))
	MAX-ACCESS  read-only
	STATUS      current
	DESCRIPTION
		"Bitmap of the features supported in the product"
	::= { usrGWCBSP 5}
usrGWCBSPNICID OBJECT-TYPE
	SYNTAX      Integer32
	MAX-ACCESS  read-only
	STATUS      current
	DESCRIPTION
		"NIC card Identifier"
	::= { usrGWCBSP 6}
usrGWCBSPNICName OBJECT-TYPE
	SYNTAX      OCTET STRING (SIZE(0..128))
	MAX-ACCESS  read-only
	STATUS      current
	DESCRIPTION
		"NIC card name"
	::= { usrGWCBSP 7}
usrGWCBSPNACID OBJECT-TYPE
	SYNTAX      Integer32
	MAX-ACCESS  read-only
	STATUS      current
	DESCRIPTION
		"NAC card Identifier"
	::= { usrGWCBSP 8}
usrGWCBSPNACName OBJECT-TYPE
	SYNTAX      OCTET STRING (SIZE(0..128))
	MAX-ACCESS  read-only
	STATUS      current
	DESCRIPTION
		"NAC Card Name "
	::= { usrGWCBSP 9}
usrGWCBSPCPUType OBJECT-TYPE
	SYNTAX      OCTET STRING (SIZE(0..64))
	MAX-ACCESS  read-only
	STATUS      current
	DESCRIPTION
		"CPU of the product"
	::= { usrGWCBSP 10}
usrGWCBSPCPUSpeed OBJECT-TYPE
	SYNTAX      Integer32
	MAX-ACCESS  read-only
	STATUS      current
	DESCRIPTION
		"The speed in Mhz in which the CPU runs "
	::= { usrGWCBSP 11}
usrGWCBSPBootMode OBJECT-TYPE
	SYNTAX      INTEGER {
			flash(0),
			network(1)
			}
	MAX-ACCESS  read-write
	STATUS      current
	DESCRIPTION
		"This variable decides the booting type. The
		 possible booting types are FLASH ( the boot image
		 is taken from the flash memory) or NETWORK (the 
		 boot image is downloaded from the network"
	--CONFIGURABLE
	::= { usrGWCBSP 12}
usrGWCBSPIPConfigSource OBJECT-TYPE
	SYNTAX      INTEGER  {
			static(0),
			bootp(1)
			 }
	MAX-ACCESS  read-write
	STATUS      current
	DESCRIPTION
		"The IP configuration source"
	--CONFIGURABLE
	::= { usrGWCBSP 13}
usrGWCBSPIPTable OBJECT-TYPE
	SYNTAX SEQUENCE OF UsrGWCBSPIPEntry
	MAX-ACCESS  not-accessible
	STATUS  current
	DESCRIPTION
		" IP Interface Table"
	::= { usrGWCBSP 14 }
usrGWCBSPIPEntry OBJECT-TYPE
	SYNTAX  UsrGWCBSPIPEntry
	MAX-ACCESS  not-accessible
	STATUS  current
	DESCRIPTION
		"IP interface Table"
	INDEX   { usrGWCBSPInterfaceIndex   }
	::= { usrGWCBSPIPTable 1 }
UsrGWCBSPIPEntry  ::=
	   SEQUENCE	{
			usrGWCBSPInterfaceIndex
				OCTET STRING (SIZE(0..16)),
			usrGWCBSPTFTPServer
				IpAddress, 
			usrGWCBSPIPAddress 
				IpAddress,
			usrGWCBSPIPGateway 
				IpAddress,
			usrGWCBSPNetMask 
				IpAddress,
			usrGWCBSPCrashDumpFile 
				UsrDisplayString (SIZE(0..128)),
			usrGWCBSPNetworkFile 
				UsrDisplayString (SIZE(0..128)),
			usrGWCBSPTFTPStatus
				INTEGER
			   }
usrGWCBSPInterfaceIndex OBJECT-TYPE
	SYNTAX      OCTET STRING (SIZE(0..16))
	MAX-ACCESS  not-accessible
	STATUS      current
	DESCRIPTION
		"The boot interface of the product. The possible
		values are eth:1 or eth:2"
	::= { usrGWCBSPIPEntry 1}
usrGWCBSPTFTPServer OBJECT-TYPE
	SYNTAX      IpAddress 
	MAX-ACCESS  read-write
	STATUS      current
	DESCRIPTION
		"TFTP server used to down load the application 
		image or upload crashdump file"
	--CONFIGURABLE
	::= { usrGWCBSPIPEntry 2}
usrGWCBSPIPAddress OBJECT-TYPE
	SYNTAX      IpAddress
	MAX-ACCESS  read-write
	STATUS      current
	DESCRIPTION
		"IP address of the selected interface"
	--CONFIGURABLE
	::= { usrGWCBSPIPEntry 3}
usrGWCBSPIPGateway OBJECT-TYPE
	SYNTAX      IpAddress
	MAX-ACCESS  read-write
	STATUS      current
	DESCRIPTION
		"IP gateway for the selected interface"
	--CONFIGURABLE
	::= { usrGWCBSPIPEntry 4}
usrGWCBSPNetMask OBJECT-TYPE
	SYNTAX      IpAddress
	MAX-ACCESS  read-write
	STATUS      current
	DESCRIPTION
		"IP netmask of the selected interface"
	--CONFIGURABLE
	::= { usrGWCBSPIPEntry 5}
usrGWCBSPCrashDumpFile OBJECT-TYPE
	SYNTAX      UsrDisplayString (SIZE(0..128))
	MAX-ACCESS  read-write
	STATUS      current
	DESCRIPTION
		"File name to which the crashdump will be uploaded
                 - maximum length is 127 chars + terminator"
	--CONFIGURABLE
	::= { usrGWCBSPIPEntry 6}
usrGWCBSPNetworkFile OBJECT-TYPE
	SYNTAX      UsrDisplayString (SIZE(0..128))
	MAX-ACCESS  read-write
	STATUS      current
	DESCRIPTION
		"The download application image file name - the
                 maximum length is 127 characters + terminator"
	--CONFIGURABLE
	::= { usrGWCBSPIPEntry 7}
usrGWCBSPTFTPStatus OBJECT-TYPE
        SYNTAX      INTEGER {
                            never(0),
                            once(1),
                            always(2)
                            }
        MAX-ACCESS  read-write
        STATUS      current
        DESCRIPTION
                "TFTP download config type"
	--CONFIGURABLE
        ::= { usrGWCBSPIPEntry 8}
usrGWCBSPCrashEnable OBJECT-TYPE
	SYNTAX      INTEGER {
			disable(0),
			enable(1)
			}
	MAX-ACCESS  read-write
	STATUS      current
	DESCRIPTION
		"Says whether the crashupload option is Enabled or
		Disabled"
	--CONFIGURABLE
	::= { usrGWCBSP 15}
usrGWCBSPDiag OBJECT-TYPE
	SYNTAX      INTEGER {
			disable(0),
			enable(1)
			}
	MAX-ACCESS  read-write
	STATUS      current
	DESCRIPTION
		"To enable or disable Mfg Diagnostics"
	--CONFIGURABLE
	::= { usrGWCBSP 16}
usrGWCBSPDipSwitches OBJECT-TYPE
	SYNTAX      OCTET STRING (SIZE(0..512))
	MAX-ACCESS  read-only
	STATUS      current
	DESCRIPTION
		"The current DIP switch settings"
	::= { usrGWCBSP 17}
usrGWCBSPCrashDump OBJECT-TYPE
	SYNTAX      OCTET STRING (SIZE(0..1400))
	MAX-ACCESS  read-only
	STATUS      current
	DESCRIPTION
		"Information about the previous crash -
                 not accessible via SNMP, CLI only."
	--CONFIGURABLE
	::= { usrGWCBSP 18}
usrGWCBSPInterface OBJECT-TYPE
	SYNTAX      OCTET STRING (SIZE(0..16))
	MAX-ACCESS  read-write
	STATUS      current
	DESCRIPTION
		"The boot interface of the product. The possible
		values are eth:1 or eth:2"
	--CONFIGURABLE
	::= { usrGWCBSP 19}
usrGWCBSPCrashDumpReset OBJECT-TYPE
	SYNTAX      INTEGER {
			disable(0),
			enable(1)
			}
	MAX-ACCESS  read-write
	STATUS      current
	DESCRIPTION
		"To Reset the Last Crash Dump"
	::= { usrGWCBSP 20}
usrGWCBSPCommandLineParameters OBJECT-TYPE
	SYNTAX      OCTET STRING (SIZE(0..127))
	MAX-ACCESS  read-write
	STATUS      current
	DESCRIPTION
        	"Contains the command line parameters which are 
                 passed to the router at startup"
	--CONFIGURABLE
	::= { usrGWCBSP 21}
usrGWCBSPCFMStatusFlag OBJECT-TYPE
        SYNTAX      UsrConfigStatus
        MAX-ACCESS  read-write
        STATUS      current
        DESCRIPTION
                "This variable controls saving and loading of configuration
                 information for the bsp manager Module. The value can
                 be set to either save or load by a management station. 
                 The other values indicate if any configuration operation 
                 and what type is in progress."
        --CONFIGURABLE
        ::= { usrGWCBSP 22 }
usrGWCBSPKernelVersion OBJECT-TYPE
        SYNTAX      Integer32
        MAX-ACCESS  read-only
        STATUS      current
        DESCRIPTION
                "The Kernel Version"     
        ::= { usrGWCBSP 23}
END
