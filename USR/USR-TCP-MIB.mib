USR-TCP-MIB DEFINITIONS ::= BEGIN
	IMPORTS
          OBJECT-TYPE, MODULE-IDENTITY,
          Integer32
                  FROM SNMPv2-SMI
          common, UsrConfigStatus, UsrDisplayString
                  FROM USR-DEFINITIONS-MIB;
usrTcp  MODULE-IDENTITY
        LAST-UPDATED "200205012030Z"
        ORGANIZATION "CommWorks Corporation, a 3Com Company"
        CONTACT-INFO "Customer Support"
        DESCRIPTION
                 "The commWorks enterprise defined MIB objects for 
                  the TCP process."
--      REVISION "200205012030Z"
--      DESCRIPTION "Converted to SNMPv2"
        ::= { common 45 }
   -- Begin managed object definitions here...
usrTcpCFMStatusFlag OBJECT-TYPE
	SYNTAX		UsrConfigStatus
	MAX-ACCESS		read-write
	STATUS		    current
	DESCRIPTION
		"This variable controls saving and loading of configuration
           information for the TCP Module. The value can 
           be set to either save or load by a management station. The other
           values indicate if any configuration operation and what type
           is in progress."
::= { usrTcp 1 }
usrTcpCfgFileName OBJECT-TYPE
	SYNTAX      UsrDisplayString
	MAX-ACCESS      read-only
	STATUS          current
	DESCRIPTION		
		"The name of a ConfigFile to read/write  permanent database records.
		 If the value of this object is an empty string, then the
		 TCP module uses the default name `@file://TCPModule.cfg'. "
::= { usrTcp 2 }
usrTcpMaxConn	OBJECT-TYPE
	SYNTAX	Integer32 (0..4096)
	MAX-ACCESS	read-write
	STATUS	    current
	DESCRIPTION
		"The limit on the total number of TCP connections
           the entity can support.  In entities where the
           maximum number of connections is dynamic, this
           object should contain the value -1.
           This a read-write version of the tcpMaxConn object in rfc1213."
	--CONFIGURABLE
::= { usrTcp 3 }
usrTcpNagleStatus	OBJECT-TYPE
	SYNTAX	INTEGER {
               enable(1),       -- enable tcp nagle algorithm
               disable(0)       -- disable tcp nagle algorithm
               }
	MAX-ACCESS	read-write
	STATUS	    current
	DESCRIPTION
		"Enable or disable tcp Nagle Algorithm.  When read, it 
           returns the current setting"
	--CONFIGURABLE
::= { usrTcp 4 }
usrTcpKeepaliveStatus	OBJECT-TYPE
	SYNTAX	INTEGER {
               enable(1),       -- enable TCP keep-alives
               disable(0)       -- disable TCP keep-alives
               }
	MAX-ACCESS	read-write
	STATUS	    current
	DESCRIPTION
		"Enable or disable TCP keep-alives.  When read, it 
           returns the current setting."
	--CONFIGURABLE
::= { usrTcp 5 }
usrTcpKeepaliveInterval	OBJECT-TYPE
	SYNTAX	Integer32 (1..2147483)
	MAX-ACCESS	read-write
	STATUS	    current
	DESCRIPTION
		"The number of seconds of inactivity on a TCP session
		after which a TCP keep-alive packet is transmitted on
		the session to discover whether it is still active."
	--CONFIGURABLE
::= { usrTcp 6 }
usrTcpAheadofSegDropped	OBJECT-TYPE
	SYNTAX	Integer32
	MAX-ACCESS	read-only
	STATUS	    current
	DESCRIPTION
	"Ahead of TCP sequences received and dropped counter can 
  	also be a good indication of network packet dropping"
::= { usrTcp 7 }
END         -- End of USR-TCP-MIB DEFINITIONS
