USR-PPPML-MIB DEFINITIONS ::= BEGIN
          IMPORTS
               OBJECT-TYPE, MODULE-IDENTITY,
               IpAddress, Counter32, Integer32
                    FROM SNMPv2-SMI
               DisplayString
                    FROM SNMPv2-TC
               common, UsrConfigStatus, UsrUserName, UsrDisplayString
                    FROM USR-DEFINITIONS-MIB;
usrPPP  MODULE-IDENTITY
        LAST-UPDATED "200303172004Z"
        ORGANIZATION "CommWorks Corporation, a 3Com Company"
        CONTACT-INFO "Customer Support"
        DESCRIPTION
                "The commWorks enterprise defined MIB objects
                  for PPP multilink."
--      REVISION "200303172004Z"
--      DESCRIPTION "Added usrPPPBaseNoAuthSIP"
--      REVISION "200211221959Z"
--      DESCRIPTION "Added usrPPPBaseLCPTermOnDereg"
--      REVISION "200211112007Z"
--      DESCRIPTION "Added usrPPPBaseLCPDelay "
--      REVISION "200208231330Z"
--      DESCRIPTION "Define usrPPPBaseSessionStartMessage as DisplayString"
--      REVISION "200208142248Z"
--      DESCRIPTION "Obsoleted usrPPPBaseAcctForImatureDisc"
--      REVISION "200205051645Z"
--      DESCRIPTION "Convert to SNMPv2"
        ::= { common 11 }
          -- All representations of MAC addresses in this MIB Module use,
          -- as a textual convention (i.e. this convention does not affect
          -- their encoding), the data type:
          MacAddress ::= OCTET STRING (SIZE (6))    -- a 6 octet address in
                                                    -- the "canonical" order
          -- defined by IEEE 802.1a, i.e., as if it were transmitted least
          -- significant bit first, even though 802.5 (in contrast to other
          -- 802.x protocols) requires MAC addresses to be transmitted most
          -- significant bit first.
          --
          -- 16-bit addresses, if needed, are represented by setting their
          -- upper 4 octets to all 0's, i.e., AAFF would be represented
          -- as 00000000AAFF.
          IpxAddress ::= IpAddress   -- a 4 octet address which represents
                                     -- represents 32-bit IPX Network Address.
          usrPPPBase      OBJECT IDENTIFIER ::= { usrPPP 1 }
          usrPPPMl        OBJECT IDENTIFIER ::= { usrPPP 2 }
--
-- The PPP Base Group.
--
usrPPPBaseRxAuth OBJECT-TYPE
    SYNTAX  INTEGER {
                    none(1),
                    pap(2),
                    chap(3),
                    any(4),
                    eapMD5(5),
                    msChap(6),
                    encryptedOnly(7),
                    radiusEapProxy(8),
                    anyExceptMsChap(9),
                    mschapv2(10)
                    }
    MAX-ACCESS   read-write
    STATUS       current
    DESCRIPTION
          "Indicates whether PPP requires dial-in users
          to authenticate strictly via PAP, CHAP, EAP-MD5, with any,
          none, encrypted only (CHAP, EAP-MD5, MS-CHAP), or 
          RADIUS-EAP-Proxy."
    DEFVAL { anyExceptMsChap }
    --CONFIGURABLE
::= { usrPPPBase 1 }
usrPPPBaseCfgFileName OBJECT-TYPE
    SYNTAX       UsrDisplayString
    MAX-ACCESS   read-only
    STATUS       current
    DESCRIPTION
          "The name of a ConfigFile to read/write
          permanent database records. If the value of this
          object is an empty string, then the PPP process
          uses the default name `@file://PppFile.cfg'."
::= { usrPPPBase 2 }
usrPPPBaseCFMSaveStatus OBJECT-TYPE
    SYNTAX  UsrConfigStatus
    MAX-ACCESS  read-write
    STATUS      current
    DESCRIPTION
          "Setting the value of this object to `save'
          causes the values of the PPP Base Group
          entries to be written out to the current PPP
          config file. While the new config file is being
          written, the PPP process will set the value
          of this flag set to `saving''. Any attempts to set
          the value while it is  not `normal' (i.e. the file
          is currently being written to the config file)
          while result in a badValue error being returned.
          Setting the value to `normal' will result in no
          action."
::= { usrPPPBase 3 }
usrPPPBaseTraceInterfaceIndex OBJECT-TYPE
    SYNTAX      Integer32 (0..2147483647)
    MAX-ACCESS  read-write
    STATUS  obsolete
    DESCRIPTION
          "Sets the interface index for which the PPP
           frames will be decoded and displayed according
           to PPP Trace facility loglevel. When this value
           is set to 0 none of the interfaces is selected"
    DEFVAL { 0 }
::= { usrPPPBase 4 }
usrPPPBaseOffloading OBJECT-TYPE
    SYNTAX  INTEGER {
                    yes(2),
                    no(1)
                     }
    MAX-ACCESS   read-write
    STATUS       current
    DESCRIPTION
          "Indicates whether PPP framing can be offloaded to
          the modem card, if modem card is capable of doing it."
    DEFVAL { yes }
    --CONFIGURABLE
::= { usrPPPBase 5 }
usrPPPBaseCCPModemType OBJECT-TYPE
    SYNTAX        Integer32
    MAX-ACCESS    read-write
    STATUS        current
    DESCRIPTION
          "Indicates the types of call, for which CCP compression
          will be enabled in the Gateway card PPP module. Possible
          values are none(0x1) or all (0x10) or subset of 
          digital(0x2), compressed analog(0x4), uncompressed analog (0x08) 
          and pppoe (0x20). Default value is digital and uncompressed analog."
    DEFVAL { 20  }
    --CONFIGURABLE
::= { usrPPPBase 6 }
usrPPPBaseNBNSPrimary OBJECT-TYPE
    SYNTAX    IpAddress 
    MAX-ACCESS    read-write
    STATUS        current
    DESCRIPTION
          " Global config for NBNS primary server address. In the
            absence of user specific NBNS address, this will be send
            in IPCP negotiation"
    DEFVAL { 0  }
    --CONFIGURABLE
::= { usrPPPBase 7 }
usrPPPBaseNBNSSecondary OBJECT-TYPE
    SYNTAX  IpAddress 
    MAX-ACCESS    read-write
    STATUS        current
    DESCRIPTION
         " Global config for NBNS primary server address. In the
            absence of user specific NBNS address, this will be send
            in IPCP negotiation"
    DEFVAL { 0  }
    --CONFIGURABLE
::= { usrPPPBase 8 }
usrPPPBaseSystemDNSUsage OBJECT-TYPE
    SYNTAX  INTEGER {
                    system(0),
                    ppp(1),
                    none(2)
                     }
    MAX-ACCESS  read-write
    STATUS      current
    DESCRIPTION
          "In the absence of user configured DNS addresses,
           PPP will take DNS addresses from the system DNS
           table. Source of the DNS table can be controlled by
           this switch, system-dns or ppp-dns or none. If this
           value set to none, none of these DNS table used"
    DEFVAL { 0  }
    --CONFIGURABLE
::= { usrPPPBase 9 }
usrPPPBasePPPDNSPrimary OBJECT-TYPE
    SYNTAX  IpAddress
    MAX-ACCESS  read-write
    STATUS      current
    DESCRIPTION
          " Global config for PPP DNS primary server address. In the
            absence of user specific DNS address, this will be send
            in IPCP negotiation"
    DEFVAL { 0  }
    --CONFIGURABLE
::= { usrPPPBase 10 }
usrPPPBasePPPDNSSecondary OBJECT-TYPE
    SYNTAX  IpAddress
    MAX-ACCESS  read-write
    STATUS      current
    DESCRIPTION
          " Global config for PPP DNS secondary server address. In the
            absence of user specific DNS address, this will be send
            in IPCP negotiation"
    DEFVAL { 0  }
    --CONFIGURABLE
::= { usrPPPBase 11 }
usrPPPBaseSessionStartMessage OBJECT-TYPE
    SYNTAX       DisplayString
    MAX-ACCESS   read-write
    STATUS       current
    DESCRIPTION
         " This is the session start display message"
    --CONFIGURABLE
::= { usrPPPBase 12 }
usrPPPBaseAuthPreference OBJECT-TYPE        
    SYNTAX  INTEGER {
                    default (1),
                    pap  (2),
                    chap (3),
                    mschap (4),
                    eap (5),
                    radiuseapproxy (6)
                    }
    MAX-ACCESS  read-write
    STATUS      current
    DESCRIPTION
          "If PPP receive authentication is configured for ANY or,
           ENCRYPTED_ANY this setting can be used to set the 
           first authentication attempted" 
     DEFVAL { chap  }
    --CONFIGURABLE
::= { usrPPPBase 13 }
usrPPPBaseAcctForImatureDisc OBJECT-TYPE
    SYNTAX  INTEGER {
                   yes(2),
                   no(1)
                   }
    MAX-ACCESS   read-write
    STATUS       obsolete
    DESCRIPTION
		  "Indicates whether to send Acct Records to premature disconnect.
           NOTE: obsolete, This MIB is not supported any more"
    DEFVAL { no }
::= { usrPPPBase 14 }
--
-- The PPP Bundle Group.
--
-- The following object reflect the values of the option
-- parameters used over the PPP Bundle
--   usrPPPBundleInstance
--   usrPPPBundleOperStatus
--   usrPPPBundleUserProfile
--   usrPPPBundleActiveLinks
--   usrPPPBundleLocalMMRU
--   usrPPPBundleRemoteMMRU
--   usrPPPBundleLocalEndptClass
--   usrPPPBundleLocalEndptLength
--   usrPPPBundleLocalEndptID
--   usrPPPBundleRemoteEndptClass
--   usrPPPBundleRemoteEndptLength
--   usrPPPBundleRemoteEndptID
--   usrPPPBundleTxTotalPkts
--   usrPPPBundleTxCompPkts
--   usrPPPBundleTxNoncompPkts
--   usrPPPBundleTxEncryptPkts
--   usrPPPBundleTxNonEncryptPkts
--   usrPPPBundleTxTotalOrigBytes
--   usrPPPBundleTxTotalLineBytes
--   usrPPPBundleRxBadHdrs
--   usrPPPBundleRxTotalPkts
--   usrPPPBundleRxCompPkts
--   usrPPPBundleRxNoncompPkts
--   usrPPPBundleRxEncryptPkts
--   usrPPPBundleRxNonEncryptPkts
--   usrPPPBundleRxTotalOrigBytes
--   usrPPPBundleRxTotalLineBytes
usrPPPBundleTable   OBJECT-TYPE
     SYNTAX    SEQUENCE OF UsrPPPBundleEntry
     MAX-ACCESS    not-accessible
     STATUS        current
     DESCRIPTION
         "Table containing the Bundle parameters and
         statistics for the local PPP entity."
::= { usrPPPMl 1 }
    usrPPPBundleEntry   OBJECT-TYPE
         SYNTAX    UsrPPPBundleEntry
         MAX-ACCESS    not-accessible
         STATUS        current
         DESCRIPTION
             "Status information for the PPP bundle."
         INDEX     { usrPPPBundleInstance }
    ::= { usrPPPBundleTable 1 }
        UsrPPPBundleEntry ::= SEQUENCE {
                 usrPPPBundleInstance           Integer32,
                 usrPPPBundleOperStatus         INTEGER,
                 usrPPPBundleUserProfile        UsrUserName,
                 usrPPPBundleActiveLinks        Integer32,
                 usrPPPBundleLocalMMRU          Integer32,
                 usrPPPBundleRemoteMMRU         Integer32,
                 usrPPPBundleLocalEndptClass    INTEGER,
                 usrPPPBundleLocalEndptLength   Integer32,
                 usrPPPBundleLocalEndptID       OCTET STRING,
                 usrPPPBundleRemoteEndptClass   INTEGER,
                 usrPPPBundleRemoteEndptLength  Integer32,
                 usrPPPBundleRemoteEndptID      OCTET STRING,
                 usrPPPBundleTxTotalPkts        Counter32,
                 usrPPPBundleTxCompPkts         Counter32,
                 usrPPPBundleTxNonCompPkts      Counter32,
                 usrPPPBundleTxTotalOrigBytes   Counter32,
                 usrPPPBundleTxTotalLineBytes   Counter32,
                 usrPPPBundleRxBadHeaders       Counter32,
                 usrPPPBundleRxTotalPkts        Counter32,
                 usrPPPBundleRxCompPkts         Counter32,
                 usrPPPBundleRxNonCompPkts      Counter32,
                 usrPPPBundleRxTotalOrigBytes   Counter32,
                 usrPPPBundleRxTotalLineBytes   Counter32,
                 usrPPPBundleTxEncryptPkts      Counter32,
                 usrPPPBundleTxNonEncryptPkts   Counter32,
                 usrPPPBundleRxEncryptPkts      Counter32,
                 usrPPPBundleRxNonEncryptPkts   Counter32
                }
usrPPPBundleInstance   OBJECT-TYPE
    SYNTAX    Integer32
    MAX-ACCESS    read-only
    STATUS        current
    DESCRIPTION
         "The unique identifier of the instance of PPP
         bundle to which this entry corresponds."
::= { usrPPPBundleEntry 1 }
usrPPPBundleOperStatus   OBJECT-TYPE
    SYNTAX    INTEGER {opened(1), not-opened(2)}
    MAX-ACCESS    read-only
    STATUS        current
    DESCRIPTION
         "The operational status of the IP network
         protocol. If the value of this object is up
         then the finite state machine for the IP
         network protocol has reached the Opened state."
::= { usrPPPBundleEntry 2 }
usrPPPBundleUserProfile   OBJECT-TYPE
    SYNTAX    UsrUserName
    MAX-ACCESS    read-only
    STATUS        current
    DESCRIPTION
         "The name of the User Profile that is being used
         to contain the characteristics for this session.
         The value of this object is meaningful only when
         the link has reached the open state
         (usrPPPBundleOperStatus is up)."
::= { usrPPPBundleEntry 3 }
usrPPPBundleActiveLinks   OBJECT-TYPE
    SYNTAX    Integer32(1..2147483647)
    MAX-ACCESS    read-only
    STATUS        current
    DESCRIPTION
         "The current number of links active for this
         bundle. This count will be incremented when the
         authentication control protocol for a new link
         has reached the open state (usrPPPAuthOperStatus
         is up). This count will be decremented when the
         link is in a state where it can no longer pass
         any application data packets."
::= { usrPPPBundleEntry 4 }
usrPPPBundleLocalMMRU   OBJECT-TYPE
    SYNTAX    Integer32(1..2147483647)
    MAX-ACCESS    read-only
    STATUS        current
    DESCRIPTION
         "The current value of the MMRU for the local PPP
         Entity. This value is the MMRU that the remote
         entity is using when sending packets to the
         local PPP entity. The value of this object is
         meaningful only when the link has reached the
         open state (usrPPPBundleOperStatus is up)."
::= { usrPPPBundleEntry 5 }
usrPPPBundleRemoteMMRU   OBJECT-TYPE
    SYNTAX    Integer32(1..2147483647)
    MAX-ACCESS    read-only
    STATUS        current
    DESCRIPTION
         "The current value of the MMRU for the remote
         PPP Entity. This value is the MMRU that the
         local entity is using when sending packets to
         the remote PPP entity. The value of this object
         is meaningful only when the link has reached
         the open state (usrPPPBundleOperStatus is up)."
::= { usrPPPBundleEntry 6 }
usrPPPBundleLocalEndptClass   OBJECT-TYPE
    SYNTAX    INTEGER {
                     nullClass(1),
                     locallyAssignedAddress(2),
                     ipAddress(3),
                     ieeeMacAddress(4),
                     pppMagicNumberBlock(5),
                     networkDirNumber(6)
                    }
    MAX-ACCESS    read-only
    STATUS        current
    DESCRIPTION
         "The current value of the local Endpoint
         Descriminator Class. This value indicates the type
         of address being used as the identifier. The value
         of this object is meaningful only when the link has
         reached the open state (usrPPPBundleOperStatus is
         up)."
::= { usrPPPBundleEntry 7 }
usrPPPBundleLocalEndptLength   OBJECT-TYPE
    SYNTAX    Integer32(0..20)
    MAX-ACCESS    read-only
    STATUS        current
    DESCRIPTION
         "The maximum length of the local Endpoint
         Descriminator Address. The value of this object is
         meaningful only when the link has reached the open
         state (usrPPPBundleOperStatus is up)."
::= { usrPPPBundleEntry 8 }
usrPPPBundleLocalEndptID   OBJECT-TYPE
    SYNTAX    OCTET STRING (SIZE(20))
    MAX-ACCESS    read-only
    STATUS        current
    DESCRIPTION
         "The value of the local Endpoint Descriminator
         Address. The value of this object is meaningful
         only when the link has reached the open state
         (usrPPPBundleOperStatus is up)."
::= { usrPPPBundleEntry 9 }
usrPPPBundleRemoteEndptClass   OBJECT-TYPE
    SYNTAX    INTEGER {
                     nullClass(1),
                     locallyAssignedAddress(2),
                     ipAddress(3),
                     ieeeMacAddress(4),
                     pppMagicNumberBlock(5),
                     networkDirNumber(6)
                    }
    MAX-ACCESS    read-only
    STATUS        current
    DESCRIPTION
         "The current value of the remote Endpoint
         Descriminator Class. This value indicates the type
         of address being used as the identifier. The value
         of this object is meaningful only when the link has
         reached the open state (usrPPPBundleOperStatus is
         up)."
::= { usrPPPBundleEntry 10 }
usrPPPBundleRemoteEndptLength   OBJECT-TYPE
    SYNTAX    Integer32(0..20)
    MAX-ACCESS    read-only
    STATUS        current
    DESCRIPTION
         "The maximum length of the remote Endpoint
         Descriminator Address. The value of this object is
         meaningful only when the link has reached the open
         state (usrPPPBundleOperStatus is up)."
::= { usrPPPBundleEntry 11 }
usrPPPBundleRemoteEndptID   OBJECT-TYPE
    SYNTAX    OCTET STRING (SIZE(20))
    MAX-ACCESS    read-only
    STATUS        current
    DESCRIPTION
         "The value of the remote Endpoint Descriminator
         Address. The value of this object is meaningful
         only when the link has reached the open state
         (usrPPPBundleOperStatus is up)."
::= { usrPPPBundleEntry 12 }
usrPPPBundleTxTotalPkts   OBJECT-TYPE
    SYNTAX    Counter32
    MAX-ACCESS    read-only
    STATUS        current
    DESCRIPTION
        "The total number of packets received from an upper
         layer application for transmission over this bundle.
         The value of this object is meaningful only when the
         link has reached the open state
         (usrPPPBundleOperStatus is up)."
::= { usrPPPBundleEntry 13 }
usrPPPBundleTxCompPkts   OBJECT-TYPE
    SYNTAX    Counter32
    MAX-ACCESS    read-only
    STATUS        current
    DESCRIPTION
         "The total number of packets received from an upper
         layer application for transmission over this bundle
         that were compressed by the PPP application before
         handing the packet (or fragments) down to the lower
         layer application. The value of this object is
         meaningful only when the link has reached the open
         state (usrPPPBundleOperStatus is up). Note that this
         counter only represents packets that were compressed
         over the BUNDLE (not links). If compression occurred
         after the packet was fragmented (multilink), those
         counters can be found at the link level."
::= { usrPPPBundleEntry 14 }
usrPPPBundleTxNonCompPkts   OBJECT-TYPE
    SYNTAX    Counter32
    MAX-ACCESS    read-only
    STATUS        current
    DESCRIPTION
         "The total number of packets received from an upper
         layer application for transmission over this bundle
         that were NOT compressed by the PPP application before
         handing the packet (or fragments) down to the lower
         layer application. The value of this object is
         meaningful only when the link has reached the open
         state (usrPPPBundleOperStatus is up). Note that this
         counter only represents packets that were candidates
         for compression over the BUNDLE (not links). If
         link compression was enabled (multilink), the non-
         compressed packet counters can be found at the link
         level."
::= { usrPPPBundleEntry 15 }
usrPPPBundleTxTotalOrigBytes   OBJECT-TYPE
    SYNTAX    Counter32
    MAX-ACCESS    read-only
    STATUS        current
    DESCRIPTION
         "The total number of bytes received from an upper
         layer application for transmission over this bundle.
         This counter represents all data handed down to the
         PPP application BEFORE compression takes place.
         The value of this object is meaningful only when the
         link has reached the open state
         (usrPPPBundleOperStatus is up)."
::= { usrPPPBundleEntry 16 }
usrPPPBundleTxTotalLineBytes   OBJECT-TYPE
    SYNTAX    Counter32
    MAX-ACCESS    read-only
    STATUS        current
    DESCRIPTION
         "The total number of bytes that sent to a lower layer
         application for transmission over this bundle.  This
         counter represents all data to be handed down to
         the lower layer application AFTER compression takes
         place. The value of this object is meaningful only
         when the link has reached the open state
         (usrPPPBundleOperStatus is up)."
::= { usrPPPBundleEntry 17 }
usrPPPBundleRxBadHeaders   OBJECT-TYPE
    SYNTAX    Counter32
    MAX-ACCESS    read-only
    STATUS        current
    DESCRIPTION
         "The number of packets received with an
         incorrect PPP Header (Address, Control,
         or PID Field)."
::= { usrPPPBundleEntry 18 }
usrPPPBundleRxTotalPkts   OBJECT-TYPE
    SYNTAX    Counter32
    MAX-ACCESS    read-only
    STATUS        current
    DESCRIPTION
         "The total number of packets received from a lower
         layer application over this bundle. The value of
         this object is meaningful only when the link has
         reached the open state
         (usrPPPBundleOperStatus is up)."
::= { usrPPPBundleEntry 19 }
usrPPPBundleRxCompPkts   OBJECT-TYPE
    SYNTAX    Counter32
    MAX-ACCESS    read-only
    STATUS        current
    DESCRIPTION
         "The total number of packets received from a lower
         layer application over this bundle that were
         decompressed by the PPP application before handing
         the packet to the upper layer application. The value
         of this object is meaningful only when the link has
         reached the open state (usrPPPBundleOperStatus is up).
         Note that this counter only represents packets that
         were decompressed over the BUNDLE (not links). If
         decompression occurred before the packet was
         reassembled (multilink), those counters can be found
         at the link level."
::= { usrPPPBundleEntry 20 }
usrPPPBundleRxNonCompPkts   OBJECT-TYPE
    SYNTAX    Counter32
    MAX-ACCESS    read-only
    STATUS        current
    DESCRIPTION
         "The total number of packets received from a lower
         layer application over this bundle that were NOT
         decompressed by the PPP application before
         handing the packet to the upper layer application.
         The value of this object is meaningful only when
         the link has reached the open state
         (usrPPPBundleOperStatus is up). Note that this
         counter only represents packets that were candidates
         for decompression over the BUNDLE (not links). If
         link (de)compression was enabled (multilink), the non-
         compressed frame counters can be found at the link
         level."
::= { usrPPPBundleEntry 21 }
usrPPPBundleRxTotalOrigBytes   OBJECT-TYPE
    SYNTAX    Counter32
    MAX-ACCESS    read-only
    STATUS        current
    DESCRIPTION
         "The total number of bytes that are to be handed up
         to an upper layer application over this bundle. This
         counter represents all data to be handed up AFTER
         decompression and reassembly takes place. The value
         of this object is meaningful only when the link has
         reached the open state
         (usrPPPBundleOperStatus is up)."
::= { usrPPPBundleEntry 22 }
usrPPPBundleRxTotalLineBytes   OBJECT-TYPE
    SYNTAX    Counter32
    MAX-ACCESS    read-only
    STATUS        current
    DESCRIPTION
         "The total number of bytes received from a lower
         layer application over this bundle.  This
         counter represents all data received BEFORE
         decompression or reassembly takes place. The value
         of this object is meaningful only when the link has
         reached the open state
         (usrPPPBundleOperStatus is up)."
::= { usrPPPBundleEntry 23 }
usrPPPBundleTxEncryptPkts   OBJECT-TYPE
    SYNTAX    Counter32
    MAX-ACCESS    read-only
    STATUS        current
    DESCRIPTION
         "The total number of packets received from an upper
         layer application for transmission over this bundle
         that were encrypted by the PPP application before
         handing the packet (or fragments) down to the lower
         layer application. The value of this object is
         meaningful only when the link has reached the open
         state (usrPPPBundleOperStatus is up). Note that this
         counter only represents packets that were encrypted
         over the BUNDLE (not links). If encryption occurred
         after the packet was fragmented (multilink), those
         counters can be found at the link level."
::= { usrPPPBundleEntry 24 }
usrPPPBundleTxNonEncryptPkts   OBJECT-TYPE
    SYNTAX    Counter32
    MAX-ACCESS    read-only
    STATUS        current
    DESCRIPTION
         "The total number of packets received from an upper
         layer application for transmission over this bundle
         that were NOT encrypted by the PPP application before
         handing the packet (or fragments) down to the lower
         layer application. The value of this object is
         meaningful only when the link has reached the open
         state (usrPPPBundleOperStatus is up). Note that this
         counter only represents packets that were candidates
         for encryption over the BUNDLE (not links). If
         link encryption was enabled (multilink), the non-
         encrypted packet counters can be found at the link
         level."
::= { usrPPPBundleEntry 25 }
usrPPPBundleRxEncryptPkts   OBJECT-TYPE
    SYNTAX    Counter32
    MAX-ACCESS    read-only
    STATUS        current
    DESCRIPTION
         "The total number of packets received from a lower
         layer application over this bundle that were
         decrypted by the PPP application before handing
         the packet to the upper layer application. The value
         of this object is meaningful only when the link has
         reached the open state (usrPPPBundleOperStatus is up).
         Note that this counter only represents packets that
         were decrypted over the BUNDLE (not links). If
         decryption occurred before the packet was
         reassembled (multilink), those counters can be found
         at the link level."
::= { usrPPPBundleEntry 26 }
usrPPPBundleRxNonEncryptPkts   OBJECT-TYPE
    SYNTAX    Counter32
    MAX-ACCESS    read-only
    STATUS        current
    DESCRIPTION
         "The total number of packets received from a lower
         layer application over this bundle that were NOT
         decrypted by the PPP application before
         handing the packet to the upper layer application.
         The value of this object is meaningful only when
         the link has reached the open state
         (usrPPPBundleOperStatus is up). Note that this
         counter only represents packets that were candidates
         for decryption over the BUNDLE (not links). If
         link decryption was enabled (multilink), the non-
         encrypted frame counters can be found at the link
         level."
::= { usrPPPBundleEntry 27 }
--
-- The PPP IP NCP Group.
--
-- The following object reflect the values of the option
-- parameters used in the PPP IP Control Protocol
--   usrPPPIpLocalToRemoteCompressionProtocol
--   usrPPPIpRemoteToLocalCompressionProtocol
--   usrPPPIpRemoteMaxSlotId
--   usrPPPIpLocalMaxSlotId
--   usrPPPIpLocalIpAddress
--   usrPPPIpRemoteIpAddress
-- These values are not available until after the PPP Option
-- negotiation has completed, which is indicated by the link
-- reaching the open state (i.e., usrPPPIpOperStatus is set to
-- opened).
--
-- Therefore, when usrPPPIpOperStatus is not opened
-- the contents of these objects is undefined. The value
-- returned when accessing the objects is an implementation
-- dependent issue.
usrPPPIpTable   OBJECT-TYPE
    SYNTAX    SEQUENCE OF UsrPPPIpEntry
    MAX-ACCESS    not-accessible
    STATUS        current
    DESCRIPTION
         "Table containing the IP parameters and
         statistics for the local PPP entity."
::= { usrPPPMl 2 }
    usrPPPIpEntry   OBJECT-TYPE
        SYNTAX    UsrPPPIpEntry
        MAX-ACCESS    not-accessible
        STATUS        current
        DESCRIPTION
             "IPCP status information for the PPP bundle."
         INDEX     { usrPPPBundleInstance }
    ::= { usrPPPIpTable 1 }
        UsrPPPIpEntry ::= SEQUENCE {
             usrPPPIpOperStatus                         INTEGER,
             usrPPPIpLocalToRemoteCompressionProtocol   INTEGER,
             usrPPPIpRemoteToLocalCompressionProtocol   INTEGER,
             usrPPPIpRemoteMaxSlotId                    Integer32,
             usrPPPIpLocalMaxSlotId                     Integer32,
             usrPPPIpLocalIpAddress                     IpAddress,
             usrPPPIpRemoteIpAddress                    IpAddress
}
usrPPPIpOperStatus   OBJECT-TYPE
    SYNTAX    INTEGER {opened(1), not-opened(2)}
    MAX-ACCESS    read-only
    STATUS        current
    DESCRIPTION
         "The operational status of the IP network
         protocol. If the value of this object is up
         then the finite state machine for the IP
         network protocol has reached the Opened state."
::= { usrPPPIpEntry 1 }
usrPPPIpLocalToRemoteCompressionProtocol   OBJECT-TYPE
    SYNTAX    INTEGER {
                     none(1),
                     vj-tcp(2)
                    }
    MAX-ACCESS    read-only
    STATUS        current
    DESCRIPTION
         "The IP compression protocol that the local
         PPP-IP entity uses when sending packets to the
         remote PPP-IP entity. The value of this object
         is meaningful only when the link has reached
         the open state (usrPPPIpOperStatus is opened)."
::= { usrPPPIpEntry 2 }
usrPPPIpRemoteToLocalCompressionProtocol   OBJECT-TYPE
    SYNTAX    INTEGER {
                     none(1),
                     vj-tcp(2)
                    }
    MAX-ACCESS    read-only
    STATUS        current
    DESCRIPTION
         "The IP compression protocol that the remote
         PPP-IP entity uses when sending packets to the
         local PPP-IP entity. The value of this object
         is meaningful only when the link has reached
         the open state (usrPPPIpOperStatus is opened)."
::= { usrPPPIpEntry 3 }
usrPPPIpRemoteMaxSlotId   OBJECT-TYPE
    SYNTAX    Integer32(0..255)
    MAX-ACCESS    read-only
    STATUS        current
    DESCRIPTION
         "The Max-Slot-Id parameter that the remote node
         has advertised and that is in use on the link.
         If vj-tcp header compression is not in use on
         the link then the value of this object shall be
         0. The value of this object is meaningful only
         when the link has reached the open state
         (usrPPPIpOperStatus is opened)."
::= { usrPPPIpEntry 4 }
usrPPPIpLocalMaxSlotId   OBJECT-TYPE
    SYNTAX    Integer32(0..255)
    MAX-ACCESS    read-only
    STATUS        current
    DESCRIPTION
         "The Max-Slot-Id parameter that the local node
         has advertised and that is in use on the link.
         If vj-tcp header compression is not in use on
         the link then the value of this object shall be
         0. The value of this object is meaningful only
         when the link has reached the open state
         (usrPPPIpOperStatus is opened)."
::= { usrPPPIpEntry 5 }
usrPPPIpLocalIpAddress    OBJECT-TYPE
    SYNTAX    IpAddress
    MAX-ACCESS    read-only
    STATUS        current
    DESCRIPTION
         "The IP Address that the local node was either
         configured for or assigned by the remote node.
         The value of this object is meaningful only
         when the link has reached the open state
         (usrPPPIpOperStatus is opened)."
::= { usrPPPIpEntry 6 }
usrPPPIpRemoteIpAddress    OBJECT-TYPE
    SYNTAX    IpAddress
    MAX-ACCESS    read-only
    STATUS        current
    DESCRIPTION
         "The IP Address that the remote node supplied
         to the local node during link negotiation.
         The value of this object is meaningful only
         when the link has reached the open state
         (usrPPPIpOperStatus is opened)."
::= { usrPPPIpEntry 7 }
--
-- The PPP IPX NCP Group.
--
-- The following object reflect the values of the option
-- parameters used in the PPP IPX Control Protocol
--   usrPPPIpxLocalIpxNetAddress
--   usrPPPIpxRemoteIpxNetAddress
--   usrPPPIpxLocalIpxNodeAddress
--   usrPPPIpxRemoteIpxNodeAddress
-- These values are not available until after the PPP Option
-- negotiation has completed, which is indicated by the link
-- reaching the open state (i.e., usrPPPIpxOperStatus is set to
-- opened).
--
-- Therefore, when usrPPPIpxOperStatus is not opened
-- the contents of these objects is undefined. The value
-- returned when accessing the objects is an implementation
-- dependent issue.
usrPPPIpxTable  OBJECT-TYPE
    SYNTAX    SEQUENCE OF UsrPPPIpxEntry
    MAX-ACCESS    not-accessible
    STATUS        current
    DESCRIPTION
         "Table containing the IPX parameters and
         statistics for the local PPP entity."
::= { usrPPPMl 3 }
    usrPPPIpxEntry  OBJECT-TYPE
        SYNTAX    UsrPPPIpxEntry
        MAX-ACCESS    not-accessible
        STATUS        current
        DESCRIPTION
             "IPXCP status information for the PPP bundle."
         INDEX     { usrPPPBundleInstance }
    ::= { usrPPPIpxTable 1 }
            UsrPPPIpxEntry ::= SEQUENCE {
                 usrPPPIpxOperStatus            INTEGER,
                 usrPPPIpxLocalIpxNetAddress    IpxAddress,
                 usrPPPIpxRemoteIpxNetAddress   IpxAddress,
                 usrPPPIpxLocalIpxNodeAddress   MacAddress,
                 usrPPPIpxRemoteIpxNodeAddress  MacAddress
                }
usrPPPIpxOperStatus   OBJECT-TYPE
    SYNTAX    INTEGER {opened(1), not-opened(2)}
    MAX-ACCESS    read-only
    STATUS        current
    DESCRIPTION
         "The operational status of the IPX network
         protocol. If the value of this object is up
         then the finite state machine for the IPX
         network protocol has reached the Opened state."
::= { usrPPPIpxEntry 1 }
usrPPPIpxLocalIpxNetAddress    OBJECT-TYPE
    SYNTAX    IpxAddress
    MAX-ACCESS    read-only
    STATUS        current
    DESCRIPTION
         "The IPX Network Address that the local node was
         either configured for or assigned by the remote
         node. The value of this object is meaningful
         only when the link has reached the open state
         (usrPPPIpxOperStatus is opened)."
::= { usrPPPIpxEntry 2 }
usrPPPIpxRemoteIpxNetAddress    OBJECT-TYPE
    SYNTAX    IpxAddress
    MAX-ACCESS    read-only
    STATUS        current
    DESCRIPTION
         "The IPX Network Address that the remote node
         supplied to the local node during link negotiation.
         The value of this object is meaningful only
         when the link has reached the open state
         (usrPPPIpxOperStatus is opened)."
::= { usrPPPIpxEntry 3 }
usrPPPIpxLocalIpxNodeAddress    OBJECT-TYPE
    SYNTAX    MacAddress
    MAX-ACCESS    read-only
    STATUS        current
    DESCRIPTION
         "The IPX Node Address that the local node was
         either configured for or assigned by the remote
         node. The value of this object is meaningful
         only when the link has reached the open state
         (usrPPPIpxOperStatus is opened)."
::= { usrPPPIpxEntry 4 }
usrPPPIpxRemoteIpxNodeAddress    OBJECT-TYPE
    SYNTAX    MacAddress
    MAX-ACCESS    read-only
    STATUS        current
    DESCRIPTION
         "The IPX Node Address that the remote node
         supplied to the local node during link negotiation.
         The value of this object is meaningful only
         when the link has reached the open state
         (usrPPPIpxOperStatus is opened)."
::= { usrPPPIpxEntry 5 }
--
-- The PPP AppleTalk NCP Group.
--
-- The following object reflect the values of the option
-- parameters used in the PPP AppleTalk Control Protocol
--   usrPPPAtLocalAtNetAddress
--   usrPPPAtRemoteAtNetAddress
--   usrPPPAtLocalAtNodeAddress
--   usrPPPAtRemoteAtNodeAddress
-- These values are not available until after the PPP Option
-- negotiation has completed, which is indicated by the link
-- reaching the open state (i.e., usrPPPAtOperStatus is set to
-- opened).
--
-- Therefore, when usrPPPAtOperStatus is not opened
-- the contents of these objects is undefined. The value
-- returned when accessing the objects is an implementation
-- dependent issue.
usrPPPAtTable  OBJECT-TYPE
    SYNTAX    SEQUENCE OF UsrPPPAtEntry
    MAX-ACCESS    not-accessible
    STATUS        current
    DESCRIPTION
         "Table containing the AppleTalk parameters and
         statistics for the local PPP entity."
::= { usrPPPMl 4 }
    usrPPPAtEntry  OBJECT-TYPE
        SYNTAX    UsrPPPAtEntry
        MAX-ACCESS    not-accessible
        STATUS        current
        DESCRIPTION
             "ATCP status information for the PPP bundle."
         INDEX     { usrPPPBundleInstance }
    ::= { usrPPPAtTable 1 }
        UsrPPPAtEntry ::= SEQUENCE {
             usrPPPAtOperStatus         INTEGER,
             usrPPPAtLocalAtNetAddress  Integer32,
             usrPPPAtRemoteAtNetAddress Integer32,
             usrPPPAtLocalAtNodeAddress Integer32,
             usrPPPAtRemoteAtNodeAddress Integer32
}
usrPPPAtOperStatus   OBJECT-TYPE
    SYNTAX    INTEGER {opened(1), not-opened(2)}
    MAX-ACCESS    read-only
    STATUS        current
    DESCRIPTION
         "The operational status of the AppleTalk network
         protocol. If the value of this object is up
         then the finite state machine for the AppleTalk
         network protocol has reached the Opened state."
    ::= { usrPPPAtEntry 1 }
usrPPPAtLocalAtNetAddress    OBJECT-TYPE
    SYNTAX    Integer32
    MAX-ACCESS    read-only
    STATUS        current
    DESCRIPTION
         "The AppleTalk Network Address that the local node
         was either configured for or assigned by the remote
         node. The value of this object is meaningful
         only when the link has reached the open state
         (usrPPPAtOperStatus is opened)."
::= { usrPPPAtEntry 2 }
usrPPPAtRemoteAtNetAddress    OBJECT-TYPE
    SYNTAX    Integer32
    MAX-ACCESS    read-only
    STATUS        current
    DESCRIPTION
         "The AppleTalk Network Address that the remote node
         supplied to the local node during link negotiation.
         The value of this object is meaningful only
         when the link has reached the open state
         (usrPPPAtOperStatus is opened)."
::= { usrPPPAtEntry 3 }
usrPPPAtLocalAtNodeAddress    OBJECT-TYPE
    SYNTAX    Integer32
    MAX-ACCESS    read-only
    STATUS        current
    DESCRIPTION
         "The AppleTalk Node Address that the local node was
         either configured for or assigned by the remote
         node. The value of this object is meaningful
         only when the link has reached the open state
         (usrPPPAtOperStatus is opened)."
::= { usrPPPAtEntry 4 }
usrPPPAtRemoteAtNodeAddress    OBJECT-TYPE
    SYNTAX    Integer32
    MAX-ACCESS    read-only
    STATUS        current
    DESCRIPTION
         "The AppleTalk Node Address that the remote node
         supplied to the local node during link negotiation.
         The value of this object is meaningful only
         when the link has reached the open state
         (usrPPPAtOperStatus is opened)."
::= { usrPPPAtEntry 5 }
--
-- The PPP Bridge NCP Group.
--
-- The following object reflect the values of the option
-- parameters used in the PPP Link Control Protocol
--   usrPPPBridgeLocalToRemoteTinygramCompression
--   usrPPPBridgeRemoteToLocalTinygramCompression
--   usrPPPBridgeLocalToRemoteLanId
--   usrPPPBridgeRemoteToLocalLanId
--   usrPPPBridgeMacType
--
-- These values are not available until after the PPP Option
-- negotiation has completed, which is indicated by the link
-- reaching the open state (i.e. usrPPPBridgeOperStatus is set to
-- opened).
--
-- Therefore, when usrPPPBridgeOperStatus is not opened
-- the contents of these objects is undefined. The value
-- returned when accessing the objects is an implementation
-- dependent issue.
usrPPPBridgeTable   OBJECT-TYPE
    SYNTAX    SEQUENCE OF UsrPPPBridgeEntry
    MAX-ACCESS    not-accessible
    STATUS        current
    DESCRIPTION
         "Table containing the parameters and statistics
         for the local PPP entity that are related to
         the operation of Bridging over the PPP."
::= { usrPPPMl 5 }
    usrPPPBridgeEntry   OBJECT-TYPE
        SYNTAX    UsrPPPBridgeEntry
        MAX-ACCESS    not-accessible
        STATUS        current
        DESCRIPTION
             "Bridging information for a particular PPP
             link."
         INDEX     { usrPPPBundleInstance }
    ::= { usrPPPBridgeTable 1 }
        UsrPPPBridgeEntry ::= SEQUENCE {
             usrPPPBridgeOperStatus                         INTEGER,
             usrPPPBridgeLocalToRemoteTinygramCompression   INTEGER,
             usrPPPBridgeRemoteToLocalTinygramCompression   INTEGER,
             usrPPPBridgeLocalToRemoteLanId                 INTEGER,
             usrPPPBridgeRemoteToLocalLanId                 INTEGER,
             usrPPPBridgeMacType                            INTEGER
}
usrPPPBridgeOperStatus   OBJECT-TYPE
    SYNTAX    INTEGER {opened(1), not-opened(2)}
    MAX-ACCESS    read-only
    STATUS        current
    DESCRIPTION
         "The operational status of the Bridge network
         protocol. If the value of this object is up
         then the finite state machine for the Bridge
         network protocol has reached the Opened state."
::= { usrPPPBridgeEntry 1 }
usrPPPBridgeLocalToRemoteTinygramCompression   OBJECT-TYPE
    SYNTAX    INTEGER { true(1), false(2) }
    MAX-ACCESS    read-only
    STATUS        current
    DESCRIPTION
         "Indicates whether the local node will perform
         Tinygram Compression when sending packets to
         the remote entity. If false then the local
         entity will not perform Tinygram Compression.
         If true then the local entity will perform
         Tinygram Compression. The value of this object
         is meaningful only when the link has reached
         the open state (usrPPPBridgeOperStatus is
         opened)."
    REFERENCE
         "Section 6.7, Tinygram Compression Option, of
         RFC1220"
::= { usrPPPBridgeEntry 2 }
usrPPPBridgeRemoteToLocalTinygramCompression   OBJECT-TYPE
    SYNTAX    INTEGER { true(1), false(2) }
    MAX-ACCESS    read-only
    STATUS        current
    DESCRIPTION
         "If false then the remote entity is not
         expected to perform Tinygram Compression. If
         true then the remote entity is expected to
         perform Tinygram Compression. The value of this
         object is meaningful only when the link has
         reached the open state (usrPPPBridgeOperStatus is
         opened)."
     REFERENCE
         "Section 6.7, Tinygram Compression Option, of
         RFC1220"
::= { usrPPPBridgeEntry 3 }
usrPPPBridgeLocalToRemoteLanId   OBJECT-TYPE
    SYNTAX    INTEGER { true(1), false(2) }
    MAX-ACCESS    read-only
    STATUS        current
    DESCRIPTION
         "Indicates whether the local node will include
         the LAN Identification field in transmitted
         packets or not. If false then the local node
         will not transmit this field, true means
         that the field will be transmitted. The value
         of this object is meaningful only when the link
         has reached the open state (usrPPPBridgeOperStatus
         is opened)."
     REFERENCE
         "Section 6.8, LAN Identification Option, of
         RFC1220"
::= { usrPPPBridgeEntry 4 }
usrPPPBridgeRemoteToLocalLanId   OBJECT-TYPE
    SYNTAX    INTEGER { true(1), false(2) }
    MAX-ACCESS    read-only
    STATUS        current
    DESCRIPTION
         "Indicates whether the remote node has
         indicated that it will include the LAN
         Identification field in transmitted packets or
         not. If false then the field will not be
         transmitted, if true then the field will be
         transmitted. The value of this object is
         meaningful only when the link has reached the
         open state (usrPPPBridgeOperStatus is opened)."
     REFERENCE
         "Section 6.8, LAN Identification Option, of
         RFC1220"
::= { usrPPPBridgeEntry 5 }
usrPPPBridgeMacType   OBJECT-TYPE
    SYNTAX    INTEGER { ieee8023-ethernet(1), ieee8025(3) }
    MAX-ACCESS    read-only
    STATUS        current
    DESCRIPTION
         "Indicates which MAC framing type the local node
         will accept and process properly. The value of
         this object is meaningful only when the link has
         reached the open state (usrPPPBridgeOperStatus
         is opened)."
     REFERENCE
         "Section 6.6, MAC Type Support Selection, of
         RFC1212."
::= { usrPPPBridgeEntry 6 }
--
-- The PPP Compression CP Group.
--
-- The following object reflect the values of the option
-- parameters used in the PPP Compression Control Protocol
--   usrPPPCompOperStatus
--   usrPPPCompAlgorithm
-- These values are not available until after the PPP Option
-- negotiation has completed, which is indicated by the link
-- reaching the open state (i.e., usrPPPCompOperStatus is set to
-- opened).
--
-- Therefore, when usrPPPCompOperStatus is not opened
-- the contents of these objects is undefined. The value
-- returned when accessing the objects is an implementation
-- dependent issue.
usrPPPCompTable   OBJECT-TYPE
    SYNTAX    SEQUENCE OF UsrPPPCompEntry
    MAX-ACCESS    not-accessible
    STATUS        current
    DESCRIPTION
         "Table containing the Compression parameters and
         statistics for the local PPP entity."
::= { usrPPPMl 6 }
    usrPPPCompEntry   OBJECT-TYPE
        SYNTAX    UsrPPPCompEntry
        MAX-ACCESS    not-accessible
        STATUS        current
        DESCRIPTION
             "CCP status information for the PPP bundle."
         INDEX     { usrPPPBundleInstance }
    ::= { usrPPPCompTable 1 }
        UsrPPPCompEntry ::= SEQUENCE {
             usrPPPCompOperStatus       INTEGER,
             usrPPPCompAlgorithm        INTEGER
            }
usrPPPCompOperStatus   OBJECT-TYPE
    SYNTAX    INTEGER {opened(1), not-opened(2), paused(3)}
    MAX-ACCESS    read-only
    STATUS        current
    DESCRIPTION
         "The operational status of the Compression control
         protocol. If the value of this object is up
         then the finite state machine for the Compression
         control protocol has reached the Opened state."
::= { usrPPPCompEntry 1 }
usrPPPCompAlgorithm   OBJECT-TYPE
    SYNTAX    INTEGER {
     none(1),
     microsoft(2),
     ascend(3),
     stac(4),
     auto(5),
     deflate(6)
}
    MAX-ACCESS    read-only
    STATUS        current
    DESCRIPTION
         "The compression protocol that the local
         PPP entity uses when sending packets to the
         remote PPP entity. The value of this object
         is meaningful only when the link has reached
         the open state (usrPPPCompOperStatus is opened)."
::= { usrPPPCompEntry 2 }
--
-- The PPP Encryption Group.
--
-- The following object reflect the values of the option
-- parameters used in the PPP Encryption.  Currently only
-- MPPE is supported
--   usrPPPEncryptOperStatus
--   usrPPPEncryptAlgorithm
-- These values are not available until after the PPP Option
-- negotiation has completed, which is indicated by the link
-- reaching the open state (i.e., usrPPPEncryptOperStatus is set to
-- opened).
--
-- Therefore, when usrPPPEncryptOperStatus is not opened
-- the contents of these objects is undefined. The value
-- returned when accessing the objects is an implementation
-- dependent issue.
usrPPPEncryptTable   OBJECT-TYPE
    SYNTAX    SEQUENCE OF UsrPPPEncryptEntry
    MAX-ACCESS    not-accessible
    STATUS        current
    DESCRIPTION
         "Table containing the Encryption parameters and
         statistics for the local PPP entity."
::= { usrPPPMl 7 }
    usrPPPEncryptEntry   OBJECT-TYPE
        SYNTAX    UsrPPPEncryptEntry
        MAX-ACCESS    not-accessible
        STATUS        current
        DESCRIPTION
             "CCP (encryption) status information for the PPP bundle."
         INDEX     { usrPPPBundleInstance }
    ::= { usrPPPEncryptTable 1 }
        UsrPPPEncryptEntry ::= SEQUENCE {
             usrPPPEncryptOperStatus    INTEGER,
             usrPPPEncryptAlgorithm     INTEGER
}
usrPPPEncryptOperStatus   OBJECT-TYPE
    SYNTAX    INTEGER {opened(1), not-opened(2)}
    MAX-ACCESS    read-only
    STATUS        current
    DESCRIPTION
         "The operational status of the Compression control
         protocol when used to negotiate MPPE encryption. 
         If the value of this object is up
         then the finite state machine for the Compression
         control protocol has reached the Opened state and
         MPPE has been negotiated."
::= { usrPPPEncryptEntry 1 }
usrPPPEncryptAlgorithm   OBJECT-TYPE
    SYNTAX    INTEGER {
                     none(1),
                     microsoft40bit(2),
                     microsoft128bit(3),
                     strongest(4),
                     try(5)
                    }
    MAX-ACCESS    read-only
    STATUS        current
    DESCRIPTION
         "The encryption protocol that the local
         PPP entity uses when sending packets to the
         remote PPP entity. The value of this object
         is meaningful only when the link has reached
         the open state (usrPPPEncryptOperStatus is opened)."
::= { usrPPPEncryptEntry 2 }
usrPPPBaseProtFieldComp OBJECT-TYPE
    SYNTAX  INTEGER {
                    enabled(1),
                    disabled(0)
                    }
    MAX-ACCESS   read-write
    STATUS       current
    DESCRIPTION
          "Indicates whether PPP Protocol field compression is
           enabled/disabled."
    --CONFIGURABLE
::= { usrPPPBase 15 }
usrPPPBaseAddrFieldComp OBJECT-TYPE
    SYNTAX  INTEGER {
                    enabled(1),
                    disabled(0)
                   }
    MAX-ACCESS   read-write
    STATUS       current
    DESCRIPTION
      "Indicates whether PPP Address field compression is
       enabled/disabled."
    --CONFIGURABLE
::= { usrPPPBase 16 }
usrPPPBaseBacpBap OBJECT-TYPE
    SYNTAX  INTEGER {
                    enabled(1),
                    disabled(0)
                   }
    MAX-ACCESS   read-write
    STATUS       current
    DESCRIPTION
          "Indicates whether PPP Bacp and Bap enabled/disabled."
    --CONFIGURABLE
::= { usrPPPBase 17 }
usrPPPBaseBapPhone OBJECT-TYPE
    SYNTAX  OCTET STRING (SIZE (0..240))
    MAX-ACCESS   read-write
    STATUS       current
    DESCRIPTION
          "The hunt_group phone number to be sent in BAP call-response"
    --CONFIGURABLE
::= { usrPPPBase 18 }
usrPPPBaseMPPP OBJECT-TYPE
    SYNTAX  INTEGER {
                    enabled(1),
                    disabled(0)
                   }
    MAX-ACCESS   read-write
    STATUS       current
    DESCRIPTION
          "Indicates whether PPP Mutlilink is Enabled/Disabled"
    --CONFIGURABLE
::= { usrPPPBase 19 }
usrPPPBaseReceiveACCM OBJECT-TYPE
    SYNTAX  INTEGER {
                    enabled(1),
                    disabled(0)
                   }
    MAX-ACCESS   read-write
    STATUS       current
    DESCRIPTION
          "Indicates whether PPP receive ACCM is Enabled/Disabled"
    --CONFIGURABLE
::= { usrPPPBase 20 }
usrPPPBaseNegCallback OBJECT-TYPE
    SYNTAX  INTEGER {
                    enabled(1),
                    disabled(0)
                   }
    MAX-ACCESS   read-write
    STATUS       current
    DESCRIPTION
          "Indicates whether PPP CBCP  enabled/disabled."
    --CONFIGURABLE
::= { usrPPPBase 21 }
usrPPPSystemMRU   OBJECT-TYPE
    SYNTAX    Integer32(128..1518)
    MAX-ACCESS    read-write
    STATUS        current
    DESCRIPTION
         "The current value of the MRU for the local PPP
         Entity. This value is the MRU that the remote
         entity is using when sending packets to the
         local PPP entity." 
    DEFVAL      { 1514 }
    --CONFIGURABLE
::= { usrPPPBase 22 }
usrPPPBaseRADIUSChallengeInPAP OBJECT-TYPE
    SYNTAX  INTEGER {
                    enabled(1),
                    disabled(0)
                   }
    MAX-ACCESS   read-write
    STATUS       current
    DESCRIPTION
          "Special processing of RADIUS Challenge, if the
           authentication is PAP"
    --CONFIGURABLE
::= { usrPPPBase 23 }
usrPPPBasePapRetries OBJECT-TYPE
    SYNTAX    Integer32(0..10)
    MAX-ACCESS    read-write
    STATUS        current
    DESCRIPTION
          "Indicates the retry limit for PAP protocol. Number of times
          PAP request shall be re-transmitted before timing out"
    DEFVAL { 3 }
    --CONFIGURABLE
::= { usrPPPBase 24 }
usrPPPBaseRestartTimeout OBJECT-TYPE
    SYNTAX    Integer32(1..10)
    MAX-ACCESS    read-write
    STATUS        current
    DESCRIPTION
          "The Restart timer is used to time transmissions of
          Configure-Request and Terminate-Request packets. Expiration of
          the Restart timer causes a Timeout event, and retransmission
          of the corresponding Congigure-Request or Terminate-Request
          packet"
    DEFVAL { 3 }
    --CONFIGURABLE
::= { usrPPPBase 34 }
usrPPPBaseMaxConfigure OBJECT-TYPE
    SYNTAX    Integer32(1..20)
    MAX-ACCESS    read-write
    STATUS        current
    DESCRIPTION
          "Max-Configure indicates the number of Configure-Request
          packets sent without receiving a valid Configure-Ack,
          Configure-Nak or Configure-Reject before assuming that the
          peer is unable to repsond"
    DEFVAL { 10 }
    --CONFIGURABLE
::= { usrPPPBase 35 }
usrPPPBaseDormLCPTerm OBJECT-TYPE
    SYNTAX    INTEGER{
                     enabled(1),
                     disabled(2)
                    }
    MAX-ACCESS    read-write
    STATUS        current
    DESCRIPTION
           "A toggle switch which determines whether to send out
            LCP TERM REQ when a call is dormant"
    DEFVAL { 2 }
    --CONFIGURABLE
::= { usrPPPBase 36 }
usrPPPBaseLCPDelay OBJECT-TYPE
    SYNTAX    Integer32(0..3000)
    UNITS     "Milliseconds"
    MAX-ACCESS    read-write
    STATUS        current
    DESCRIPTION
          "Indicates the amount of time the PDSN should wait before 
          sending out an LCP Configure-Request"
    DEFVAL { 0 }
    --CONFIGURABLE
::= { usrPPPBase 37 }
usrPPPBaseLCPTermOnDereg OBJECT-TYPE
    SYNTAX  INTEGER {
                    enabled(1),
                    disabled(2)
                   }
    MAX-ACCESS   read-write
    STATUS       current
    DESCRIPTION
      "Indicates whether the PDSN should transmit an LCP Term_Req on receipt of a 
      deregistration req from the PCF"
    --CONFIGURABLE
::= { usrPPPBase 40 }
usrPPPBaseNoAuthSIP OBJECT-TYPE
    SYNTAX  INTEGER {
                    enabled(1),
                    disabled(2)
                   }
    MAX-ACCESS   read-write
    STATUS       current
    DESCRIPTION
      "Indicates whether the PDSN should allow Simple IP (SIP) calls that reject authentication
       during LCP. disabled means that the PDSN will tear down the call if the mobile node rejects 
       authentication for a simple IP call. enabled means that the PDSN will accept simple ip calls 
       from mobiles that reject authentication during LCP."
    --CONFIGURABLE
::= { usrPPPBase 43 }
END     -- End of USR-PPPML-MIB DEFINITIONS
