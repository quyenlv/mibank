USR-TAP-MIB DEFINITIONS ::= BEGIN
       IMPORTS
          OBJECT-TYPE, MODULE-IDENTITY,
          IpAddress, Integer32
                FROM SNMPv2-SMI
          UsrDisplayString, common
                FROM USR-DEFINITIONS-MIB;
usrTap  MODULE-IDENTITY
        LAST-UPDATED "200204061326Z"
        ORGANIZATION "CommWorks Corporation, a 3Com Company"
        CONTACT-INFO "Customer Support"
        DESCRIPTION
                "The commWorks enterprise defined MIB objects for
                 the Port Tapping Service functionality."
--      REVISION      "200204061326Z"
--      DESCRIPTION " Corrected SNMPv2 format"
::= { common 57 }
   -- Begin managed object definitions here...
usrTapTable OBJECT-TYPE
	SYNTAX SEQUENCE OF UsrTapEntry
	MAX-ACCESS not-accessible
	STATUS current
	DESCRIPTION
		"The table of Tap entries. "
::= { usrTap 1 }
usrTapEntry OBJECT-TYPE
	SYNTAX UsrTapEntry
	MAX-ACCESS not-accessible
	STATUS current
	DESCRIPTION
		"A entry for one tap."
	INDEX { usrTapOutput }
::= { usrTapTable 1 }
UsrTapEntry ::= SEQUENCE {
	usrTapIfaceName		UsrDisplayString,
	usrTapIface		    Integer32,
	usrTapUserName		UsrDisplayString,
	usrTapUser		    Integer32,
	usrTapNext		    Integer32,
	usrTapPermanent 	INTEGER,
	usrTapOutput		INTEGER,
	usrTapFormat		INTEGER,
	usrTapFacility		INTEGER,
	usrTapPriority     	INTEGER,
	usrTapAddress     	IpAddress,
	usrTapOutputIcb		Integer32,
	usrTapStatus		Integer32
	}
usrTapIfaceName OBJECT-TYPE
	SYNTAX		UsrDisplayString 
	MAX-ACCESS	read-write
	STATUS		current
	DESCRIPTION
		"The name of the interface being tapped."
::= { usrTapEntry 1 }
usrTapUserName OBJECT-TYPE
	SYNTAX		UsrDisplayString 
	MAX-ACCESS	read-write
	STATUS		current
	DESCRIPTION
		"The name of the user being tapped."
::= { usrTapEntry 2 }
usrTapOutput OBJECT-TYPE
	SYNTAX		INTEGER { syslog(0), screen(1) }
	MAX-ACCESS	read-write
	STATUS		current
	DESCRIPTION
		"The tapped output can be sent to syslog or to screen."
::= { usrTapEntry 3 }
usrTapFormat OBJECT-TYPE
	SYNTAX		INTEGER { ascii(0), hex(1), clear(2) }
	MAX-ACCESS	read-write
	STATUS		current
	DESCRIPTION
		"The output can be in hex, ascii or clear formats."
::= { usrTapEntry 4 }
usrTapFacility OBJECT-TYPE
	SYNTAX		INTEGER { auth(1), local0(2), local1(3), local2(4), local3(5), local4(6), local5(7), local6(8), local7(9) }
	MAX-ACCESS	read-write
	STATUS		current
	DESCRIPTION
		"The syslog facility used for logging."
::= { usrTapEntry 5 }
usrTapPriority OBJECT-TYPE
	SYNTAX		INTEGER { critical(0), unusual(1), common(2), verbose(3) }
	MAX-ACCESS	read-write
	STATUS		current
	DESCRIPTION
		"The syslog level used for logging."
::= { usrTapEntry 6 }
usrTapAddress OBJECT-TYPE
	SYNTAX		IpAddress 
	MAX-ACCESS	read-write
	STATUS		current
	DESCRIPTION
		"The IP address for logging the output to."
::= { usrTapEntry 7 }
usrTapOutputIcb OBJECT-TYPE
	SYNTAX		Integer32 
	MAX-ACCESS	read-write
	STATUS		current
	DESCRIPTION
		"The icb ptr for tap commands issued via cli."
::= { usrTapEntry 8 }
usrTapStatus OBJECT-TYPE
	SYNTAX		Integer32 
	MAX-ACCESS	read-write
	STATUS		current
	DESCRIPTION
		"The status of the tap"
::= { usrTapEntry 9 }
usrTapIface OBJECT-TYPE
	SYNTAX		Integer32 
	MAX-ACCESS	read-write
	STATUS		current
	DESCRIPTION
		"Whether this is a interface based tap."
::= { usrTapEntry 10 }
usrTapUser OBJECT-TYPE
	SYNTAX		Integer32 
	MAX-ACCESS	read-write
	STATUS		current
	DESCRIPTION
		"Whether this is a user based tap."
::= { usrTapEntry 11 }
usrTapNext OBJECT-TYPE
	SYNTAX		Integer32 
	MAX-ACCESS	read-write
	STATUS		current
	DESCRIPTION
		"Whether the next call is to be tapped."
::= { usrTapEntry 12 }
usrTapPermanent OBJECT-TYPE
	SYNTAX		INTEGER { temporary(0), permanent(1) }
	MAX-ACCESS	read-write
	STATUS		current
	DESCRIPTION
		"Whether the tap is permanent (user profile has it) or temp (CLI issued)"
::= { usrTapEntry 13 }
END         -- End USR-TAP-MIB definitions
