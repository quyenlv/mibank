USR-PM-MIB DEFINITIONS ::= BEGIN
	IMPORTS
          OBJECT-TYPE, MODULE-IDENTITY, Integer32
                  FROM SNMPv2-SMI
          TruthValue, DisplayString
		  FROM SNMPv2-TC
          UsrDisplayString, common, UsrConfigStatus, UsrPolicyfileName
                  FROM USR-DEFINITIONS-MIB;
usrPm    MODULE-IDENTITY
         LAST-UPDATED "200203121800Z"
         ORGANIZATION "CommWorks Corporation, a 3Com Company"
         CONTACT-INFO "Customer Support"
         DESCRIPTION
                 "The commWorks enterprise defined MIB objects
                  for the Policy Manager process."
--       REVISION       "200203121800Z"
--       DESCRIPTION
--               "Converted to SNMPv2"
         ::= { common 69 }
   -- Begin managed object definitions here...
   --  Added dynamic ipsec MIB object.
usrPmCFMStatusFlag OBJECT-TYPE
	SYNTAX		UsrConfigStatus
	MAX-ACCESS	read-write
	STATUS		current
	DESCRIPTION
		"This variable controls saving and loading of configuration
           information for the PM Module. The value can 
           be set to either save or load by a management station. The other
           values indicate if any configuration operation and what type
           is in progress."
::= { usrPm 1 }
usrPmCfgFileName OBJECT-TYPE
	SYNTAX      UsrDisplayString
	MAX-ACCESS  read-only
	STATUS      current
	DESCRIPTION		
		"The name of a ConfigFile to read/write  permanent database records.
		 If the value of this object is an empty string, then the
		 PM module uses the default name `@file://PMModule.cfg'. "
::= { usrPm 2 }
usrPmConfigTable OBJECT-TYPE
	SYNTAX SEQUENCE OF UsrPmConfigEntry
	MAX-ACCESS not-accessible
	STATUS current
	DESCRIPTION
		""
::= { usrPm 3 }
usrPmConfigEntry OBJECT-TYPE
	SYNTAX UsrPmConfigEntry
	MAX-ACCESS not-accessible
	STATUS current
	DESCRIPTION
		""
	INDEX { usrPmConfigIndex }
::= { usrPmConfigTable 1 }
UsrPmConfigEntry ::= SEQUENCE {
	usrPmState						TruthValue,
	usrPmRemoteManAccess			TruthValue,
	usrPmRemoteManType			UsrDisplayString,
	usrPmAlarmLevel					Integer32,
	usrPmAlarmPktSize				Integer32,
	usrPmAlarmStorageLocation		UsrDisplayString,
	usrPmRefreshTimeout				Integer32,
	usrPmSupportedApplications		UsrDisplayString,
        usrPmConfigIndex Integer32
	}
usrPmConfigIndex         OBJECT-TYPE
           SYNTAX          Integer32
           MAX-ACCESS      read-only
           STATUS          current
           DESCRIPTION
              " A unique value for each PM Config file. "
           ::= { usrPmConfigEntry 9 }
usrPmState OBJECT-TYPE
 	SYNTAX  TruthValue
 	MAX-ACCESS  read-only
 	STATUS  current
 	DESCRIPTION
    "This flag shows whether the Policy Manager has been enabled or disabled."
::= { usrPmConfigEntry 1 }
usrPmRemoteManAccess OBJECT-TYPE
 	SYNTAX  TruthValue
 	MAX-ACCESS  read-only
 	STATUS  current
 	DESCRIPTION
    "This flag shows whether the Policy Manager allows remote configuration/management
    by an Management Station or not."
::= { usrPmConfigEntry 2 }
usrPmRemoteManType OBJECT-TYPE
 	SYNTAX  UsrDisplayString
 	MAX-ACCESS  read-only
 	STATUS  current
 	DESCRIPTION
    "Describes the means by which a remote management station can configure/manage the
    Policy Manager, e.g. via http, snmp etc."
::= { usrPmConfigEntry 3 }
usrPmAlarmLevel OBJECT-TYPE
 	SYNTAX  Integer32
 	MAX-ACCESS  read-only
 	STATUS  current
 	DESCRIPTION
    "This value determines the grade of information logging done by the Policy Manager
    /Flow Manager."
::= { usrPmConfigEntry 4 }
usrPmAlarmPktSize OBJECT-TYPE
 	SYNTAX  Integer32
 	MAX-ACCESS  read-only
 	STATUS  current
 	DESCRIPTION
    "The size of the packet that will be saved in syslog (or other) records."
::= { usrPmConfigEntry 5 }
usrPmAlarmStorageLocation OBJECT-TYPE
 	SYNTAX  UsrDisplayString
 	MAX-ACCESS  read-only
 	STATUS  current
 	DESCRIPTION
    "The destination for alarm messages and records."
::= { usrPmConfigEntry 6 }
usrPmRefreshTimeout OBJECT-TYPE
 	SYNTAX  Integer32
 	MAX-ACCESS  read-only
 	STATUS  current
 	DESCRIPTION
    "The time (in minutes) during checks on validity of flows in the flow database."
::= { usrPmConfigEntry 7 }
usrPmSupportedApplications OBJECT-TYPE
 	SYNTAX  UsrDisplayString
 	MAX-ACCESS  read-only
 	STATUS  current
 	DESCRIPTION
    "Client Applications registered with the Policy Manager (QOS,IPSEC,NAT,FW,SOCKS)."
::= { usrPmConfigEntry 8 }
usrPolicyTable OBJECT-TYPE
     SYNTAX   SEQUENCE OF UsrPolicyEntry
     MAX-ACCESS   not-accessible
     STATUS   current
     DESCRIPTION
        "A table of policy file names.  The actual policy
         information is stored in an ASCII file in flash."
 ::= { usrPm 4 }
usrPolicyEntry OBJECT-TYPE
     SYNTAX   UsrPolicyEntry
     MAX-ACCESS   not-accessible
     STATUS   current
     DESCRIPTION
            "The parameters for a policy file."
       INDEX {usrPolicyfileName}
 ::= { usrPolicyTable 1 }
 --
 -- The row is composed of these components
 --
 UsrPolicyEntry ::=
     SEQUENCE {
     usrPolicyfileName
       UsrPolicyfileName ,
     usrPolicyfileStatus
        INTEGER,
     usrPolicyfileAssociation
        DisplayString,
     usrPolicyfileVerifyError
        DisplayString,
     usrPolicyPrintAccess
        INTEGER
 }
 usrPolicyfileName OBJECT-TYPE
     SYNTAX  UsrPolicyfileName
     MAX-ACCESS  not-accessible
     STATUS  current
     DESCRIPTION
        "The character name for this policy file."
 ::= { usrPolicyEntry 1 }
 usrPolicyfileStatus OBJECT-TYPE
     SYNTAX  INTEGER {
                     normal(1),
                     delete(2),
                     update(4),
                     reading(8),       -- File reading in progress
                     converting(16),     -- Filter verification in progress
                     compiling(32),     -- Filter compilation in progress
                     compileFailed(64),  -- Filter verification failed
                     starting(128)       -- Filter operation starting
                     }
     MAX-ACCESS  read-write
     STATUS  current
     DESCRIPTION
        "The status of this policy file entry. Valid row entries in this
         table have the status field set to normal. The settable values
         are normal and delete.  If the instance is not in the table 
         and the status is normal, this will be an add operation.  If the
         instance is in the table and the status is normal, this will be a
         modify operation.  If the instance is in the table and the 
         status is delete, this will be a delete operation.  The values 
         reading, verifying, and compiling are read-only."
     --CONFIGURABLE
 ::= { usrPolicyEntry 2 }
 usrPolicyfileAssociation OBJECT-TYPE
     SYNTAX  DisplayString (SIZE (0..255))
     MAX-ACCESS  read-only
     STATUS  current
     DESCRIPTION
        "Details the interface/user that this Policy file is associated with."
 ::= { usrPolicyEntry 3 }
 usrPolicyfileVerifyError OBJECT-TYPE
     SYNTAX  DisplayString (SIZE (0..255))
     MAX-ACCESS  read-only
     STATUS  current
     DESCRIPTION
        "The error string returned when a policy file fails its verification
         process.  Otherwise, this field is NULL."
 ::= { usrPolicyEntry 4 }
usrPolicyPrintAccess OBJECT-TYPE
       SYNTAX      INTEGER {
                            off (0),
                            on (1)
                           }
       MAX-ACCESS      read-write
       STATUS      current
       DESCRIPTION "This  will allow user policy to be printed 
                    during compilation. "
::= { usrPolicyEntry 5 }
usrDynamicIPSec         OBJECT-TYPE
           SYNTAX          INTEGER {
                                        off (0),
                                        on (1)
                                   }
           MAX-ACCESS      read-write
           STATUS      current
           DESCRIPTION
              " This variable controls the Dynamic 
		IPSec Association capability."
     --CONFIGURABLE
::= { usrPm 5 }
END    -- End of USR-PM-MIB DEFINITIONS
