USR-SLIP-MIB DEFINITIONS ::= BEGIN
          IMPORTS
               OBJECT-TYPE, MODULE-IDENTITY
				    FROM SNMPv2-SMI
			   common, UsrDisplayString, UsrConfigStatus
						FROM USR-DEFINITIONS-MIB;
usrSLIP MODULE-IDENTITY
        LAST-UPDATED "200205051800Z"
        ORGANIZATION "CommWorks Corporation, a 3Com Company"
        CONTACT-INFO "Customer Support"
        DESCRIPTION
           "The commWorks enterprise defined MIB objects for SLIP"
--      REVISION  "200205051800Z"
--      DESCRIPTION "Converted to SNMPv2"
       ::= { common 35 }
          usrSLIPBase      OBJECT IDENTIFIER ::= { usrSLIP 1 }
          usrSLIPBaseOffloading OBJECT-TYPE
              SYNTAX  INTEGER {
                        yes(2),
                        no(1)
                      }
              MAX-ACCESS   read-write
              STATUS       current
              DESCRIPTION
                      "Indicates whether SLIP framing can be offloaded to
					  the modem card, if modem card is capable of doing it."
              DEFVAL { yes }
              --CONFIGURABLE
              ::= { usrSLIPBase 1 }
          usrSLIPBaseCfgFileName OBJECT-TYPE
              SYNTAX   UsrDisplayString
              MAX-ACCESS   read-only
              STATUS       current
              DESCRIPTION
                      "The name of a ConfigFile to read/write
                      permanent database records. If the value of this
                      object is an empty string, then the SLIP process
                      uses the default name `@file://SlipFile.cfg'."
              ::= { usrSLIPBase 2 }
          usrSLIPBaseCFMSaveStatus OBJECT-TYPE
              SYNTAX  UsrConfigStatus
              MAX-ACCESS  read-write
              STATUS      current
              DESCRIPTION
                      "Setting the value of this object to `save'
                      causes the values of the SLIP Base Group
                      entries to be written out to the current SLIP
                      config file. While the new config file is being
                      written, the SLIP process will set the value
                      of this flag set to `saving''. Any attempts to set
                      the value while it is  not `normal' (i.e. the file
                      is currently being written to the config file)
                      while result in a badValue error being returned.
                      Setting the value to `normal' will result in no
                      action."
              ::= { usrSLIPBase 3 }
          usrSLIPStartMsg OBJECT-TYPE
              SYNTAX  UsrDisplayString
              MAX-ACCESS  read-write
              STATUS      current
              DESCRIPTION
                      "Startup Message for SLIP connection"
              --CONFIGURABLE
              ::= { usrSLIPBase 4 }
END     -- End of USR-SLIP-MIB DEFINITIONS
-- ************************************************************************
--
--	usr_ping.mib - The CommWorks Ping MIB
--
