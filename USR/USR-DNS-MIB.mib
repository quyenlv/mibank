USR-DNS-MIB DEFINITIONS ::= BEGIN
	IMPORTS
    	  RowStatus, DisplayString
                FROM SNMPv2-TC
          OBJECT-TYPE, MODULE-IDENTITY, 
          Integer32, Counter32, IpAddress
                FROM SNMPv2-SMI
          UsrDisplayString, UsrConfigStatus, common
                FROM USR-DEFINITIONS-MIB
          DnsName, DnsClass, DnsType, DnsQClass, DnsQType, DnsTime
                FROM DNS-SERVER-MIB;
usrDns   MODULE-IDENTITY
         LAST-UPDATED "200209061420Z"
         ORGANIZATION "CommWorks Corporation, a 3Com Company"
         CONTACT-INFO "Customer Support"
         DESCRIPTION
                 "The commWorks enterprise defined MIB objects
                  for the Domain Name Service functionality."
--       REVISION "200209061420Z"
--       DESCRIPTION "Clarify usage of usrDnsTimeout."
--       REVISION "200204061300Z"
--       DESCRIPTION "Correct SNMPv2 conversion."
::= { common 17 }
   -- Begin managed object definitions here...
usrDnsVersion OBJECT-TYPE
	SYNTAX		DisplayString
	MAX-ACCESS	read-only
	STATUS		current
	DESCRIPTION
		"The current software version of the Domain Name Server."
::= { usrDns 1 }
usrDnsCFMStatusFlag OBJECT-TYPE
	SYNTAX		UsrConfigStatus
	MAX-ACCESS	read-write
	STATUS		current
	DESCRIPTION
	"This variable controls saving and loading of all the configuration
           information for the Domain Name Service. The value can 
           be set to either save or load by a management station. The other
           values indicate if any configuration operation and what type
           is in progress."
::= { usrDns 2 }
usrDnsCfgFileName OBJECT-TYPE
	SYNTAX      UsrDisplayString
	MAX-ACCESS  read-only
	STATUS      current
	DESCRIPTION		
		"The name of a ConfigFile to read/write  permanent database records.
		 If the value of this object is an empty string, then the
		 DNS module uses the default name `@file://DNS.cfg'. "
	--CONFIGURABLE
::= { usrDns 3 }
usrDnsDomainName OBJECT-TYPE
	SYNTAX      DisplayString
	MAX-ACCESS  read-write
	STATUS      current
	DESCRIPTION		
		"The default Domain Name to be appended to a Host Name if
           it cannot be resolved without a Domain Name."
	--CONFIGURABLE
::= { usrDns 4 }
usrDnsNumberRetries OBJECT-TYPE
     SYNTAX   Integer32 (1..5)
     MAX-ACCESS   read-write
     STATUS   current
     DESCRIPTION
            "The number of times DNS will attempt to resolve a name before
             determining it cannot be resolved."
	--CONFIGURABLE
::= { usrDns 5 }
usrDnsTimeout OBJECT-TYPE
     SYNTAX   Integer32 (5..245)
     MAX-ACCESS   read-write
     STATUS   current
     DESCRIPTION
            "The number of seconds DNS will wait for a response from
             a name server before determining it is not coming.
             The minimum timeout value is 5 seconds.
             The maximum timeout value is twice the Internet MSL
             (Maximum Segment Lifetime) + the minimum = 245 secs."
     REFERENCE
             "RFC-1122 section 3.3"
	--CONFIGURABLE
::= { usrDns 6 }
usrDnsQueries OBJECT-TYPE
     SYNTAX   Counter32
     MAX-ACCESS   read-only
     STATUS   current
     DESCRIPTION
            "The total number of queries received by DNS"
::= { usrDns 7 }
usrDnsTotalResponses OBJECT-TYPE
     SYNTAX   Counter32
     MAX-ACCESS   read-only
     STATUS   current
     DESCRIPTION
            "The total number of responses sent by DNS"
::= { usrDns 8 }
usrDnsResponseOK OBJECT-TYPE
     SYNTAX   Counter32
     MAX-ACCESS   read-only
     STATUS   current
     DESCRIPTION
            "The number of success responses received by DNS"
::= { usrDns 9 }
usrDnsResponseFormat OBJECT-TYPE
     SYNTAX   Counter32
     MAX-ACCESS   read-only
     STATUS   current
     DESCRIPTION
            "The number of Format Error responses received by DNS"
::= { usrDns 10 }
usrDnsResponseServer OBJECT-TYPE
     SYNTAX   Counter32
     MAX-ACCESS   read-only
     STATUS   current
     DESCRIPTION
            "The number of Server Error responses received by DNS"
::= { usrDns 11 }
usrDnsResponseName OBJECT-TYPE
     SYNTAX   Counter32
     MAX-ACCESS   read-only
     STATUS   current
     DESCRIPTION
            "The number of No Such Name responses received by DNS"
::= { usrDns 12 }
usrDnsResponseNIY OBJECT-TYPE
     SYNTAX   Counter32
     MAX-ACCESS   read-only
     STATUS   current
     DESCRIPTION
            "The number of NIY responses sent by DNS.
	This indicates that the Server does not implement this operation"
::= { usrDns 13 }
usrDnsResponseRefused OBJECT-TYPE
     SYNTAX   Counter32
     MAX-ACCESS   read-only
     STATUS   current
     DESCRIPTION
            "The number of Refused responses sent by DNS.
	This indicates the Server refuses to perform the operation."
::= { usrDns 14 }
usrDnsResponsesLocal OBJECT-TYPE
     SYNTAX   Counter32
     MAX-ACCESS   read-only
     STATUS   current
     DESCRIPTION
            "The number of responses answered Locally by DNS"
::= { usrDns 15 }
usrDnsResponsesRemote OBJECT-TYPE
     SYNTAX   Counter32
     MAX-ACCESS   read-only
     STATUS   current
     DESCRIPTION
            "The number of responses received by DNS"
::= { usrDns 16 }
usrDnsResponseBadProt OBJECT-TYPE
     SYNTAX   Counter32
     MAX-ACCESS   read-only
     STATUS   current
     DESCRIPTION
            "The number of corrupted responses received by DNS"
::= { usrDns 17 }
usrDnsTimeOuts OBJECT-TYPE
     SYNTAX   Counter32
     MAX-ACCESS   read-only
     STATUS   current
     DESCRIPTION
            "The total number of timeouts on requests sent by DNS"
::= { usrDns 18 }
usrDnsResponseNotSent OBJECT-TYPE
     SYNTAX   Counter32
     MAX-ACCESS   read-only
     STATUS   current
     DESCRIPTION
            "The number of send failures on replies sent by DNS"
::= { usrDns 19 }
usrDnsErrorResponse OBJECT-TYPE
     SYNTAX   Counter32
     MAX-ACCESS   read-only
     STATUS   current
     DESCRIPTION
            "The number of failure  replies sent by DNS"
::= { usrDns 20 }
usrDnsHostTable OBJECT-TYPE
	SYNTAX SEQUENCE OF UsrDnsHostEntry
	MAX-ACCESS not-accessible
	STATUS current
	DESCRIPTION
		"The table of DNS Hosts. "
::= { usrDns 21 }
usrDnsHostEntry OBJECT-TYPE
	SYNTAX UsrDnsHostEntry
	MAX-ACCESS not-accessible
	STATUS current
	DESCRIPTION
		"A (conceptual) entry for one Dns Host."
	INDEX { usrDnsHostName }
::= { usrDnsHostTable 1 }
UsrDnsHostEntry ::= SEQUENCE {
	usrDnsHostName			DisplayString,
	usrDnsHostAddress		IpAddress,
	usrDnsHostStatus     	        RowStatus
	}
usrDnsHostName OBJECT-TYPE
	SYNTAX		DisplayString
	MAX-ACCESS		not-accessible
	STATUS		current
	DESCRIPTION
		"The logical identifier of the Host Table. "
::= { usrDnsHostEntry 1 }
usrDnsHostAddress OBJECT-TYPE
	SYNTAX		IpAddress
	MAX-ACCESS		read-write
	STATUS		current
	DESCRIPTION
		"The specified or resolved ip address of the named Host. "
	--CONFIGURABLE
::= { usrDnsHostEntry 2 }
usrDnsHostStatus OBJECT-TYPE
	SYNTAX		RowStatus
	MAX-ACCESS		read-write
	STATUS		current
	DESCRIPTION
		"The status of this row of the Host Table. "
	--CONFIGURABLE
::= { usrDnsHostEntry 3 }
usrDnsServerTable OBJECT-TYPE
	SYNTAX SEQUENCE OF UsrDnsServerEntry
	MAX-ACCESS not-accessible
	STATUS current
	DESCRIPTION
		"The table of DNS Servers. "
::= { usrDns 22 }
usrDnsServerEntry OBJECT-TYPE
	SYNTAX UsrDnsServerEntry
	MAX-ACCESS not-accessible
	STATUS current
	DESCRIPTION
		"A (conceptual) entry for one Dns Server."
	INDEX { usrDnsServerPreference }
::= { usrDnsServerTable 1 }
UsrDnsServerEntry ::= SEQUENCE {
	usrDnsServerPreference		Integer32,
	usrDnsServerName		DisplayString,
	usrDnsServerAddress		IpAddress,
	usrDnsServerStatus     	        RowStatus
	}
usrDnsServerPreference OBJECT-TYPE
	SYNTAX		Integer32
	MAX-ACCESS		not-accessible
	STATUS		current
	DESCRIPTION
		"The logical identifier of the Server Table. "
::= { usrDnsServerEntry 1 }
usrDnsServerName OBJECT-TYPE
	SYNTAX		DisplayString
	MAX-ACCESS		read-write
	STATUS		current
	DESCRIPTION
		"The specified name of the Server. "
	--CONFIGURABLE
::= { usrDnsServerEntry 2 }
usrDnsServerAddress OBJECT-TYPE
	SYNTAX		IpAddress
	MAX-ACCESS		read-write
	STATUS		current
	DESCRIPTION
		"The specified or resolved ip address of the named Server. "
	--CONFIGURABLE
::= { usrDnsServerEntry 3 }
usrDnsServerStatus OBJECT-TYPE
	SYNTAX		RowStatus
	MAX-ACCESS		read-write
	STATUS		current
	DESCRIPTION
		"The status of this row of the Server Table. "
	--CONFIGURABLE
::= { usrDnsServerEntry 4 }
usrDnsHostRotation OBJECT-TYPE
     SYNTAX   INTEGER { enabled(1), disabled(2) }
     MAX-ACCESS   read-write
     STATUS   current
     DESCRIPTION
            "Setting this object to a value of enabled(1) will enable
             the DNS host rotation feature. Setting this object to
             disabled(2) will disable the DNS Host Rotation feature."
     --CONFIGURABLE
::= { usrDns 23 }
-- Resolver Cache Table
usrDnsCacheTable OBJECT-TYPE
    SYNTAX      SEQUENCE OF UsrDnsCacheEntry
    MAX-ACCESS  not-accessible
    STATUS      current
    DESCRIPTION
           "This table contains information about all the resource
           records currently in the resolver's cache."
::= { usrDns 24 }
usrDnsRoundRobin OBJECT-TYPE
     SYNTAX   INTEGER { enabled(1), disabled(2) }
     MAX-ACCESS   read-write
     STATUS   current
     DESCRIPTION
            "Setting this object to a value of enabled(1) will enable
             the DNS round robin feature. Setting this object to
             disabled(2) will set the DNS into random."
     --CONFIGURABLE
::= { usrDns 26 }
usrDnsCacheEntry OBJECT-TYPE
    SYNTAX      UsrDnsCacheEntry
    MAX-ACCESS  not-accessible
    STATUS      current
    DESCRIPTION
           "An entry in the resolver's cache.  Rows may be created
           only by the resolver.  SNMP SET requests may be used to
           delete rows."
    INDEX     { usrDnsCacheRRIndex }
::= { usrDnsCacheTable 1 }
UsrDnsCacheEntry ::=
    SEQUENCE {
        usrDnsCacheRRIndex
            Integer32,
        usrDnsCacheRRClass
            DnsClass,
        usrDnsCacheRRType
            DnsType,
        usrDnsCacheRRTTL
            DnsTime,
        usrDnsCacheRRElapsedTTL
            DnsTime,
        usrDnsCacheRRSource
            IpAddress,
        usrDnsCacheRRData
            OCTET STRING,
        usrDnsCacheRRStatus
            RowStatus,
        usrDnsCacheRRPrettyName
            DnsName
    }
usrDnsCacheRRIndex OBJECT-TYPE
    SYNTAX      Integer32
    MAX-ACCESS  not-accessible
    STATUS      current
    DESCRIPTION
           "A value which makes entries in the table unique."
::= { usrDnsCacheEntry 1 }
usrDnsCacheRRClass OBJECT-TYPE
    SYNTAX      DnsClass
    MAX-ACCESS  read-only
    STATUS      current
    DESCRIPTION
           "DNS class of the Resource Record in the cache which is
           identified in this row of the table."
::= { usrDnsCacheEntry 2 }
usrDnsCacheRRType OBJECT-TYPE
    SYNTAX      DnsType
    MAX-ACCESS  read-only
    STATUS      current
    DESCRIPTION
           "DNS type of the Resource Record in the cache which is
           identified in this row of the table."
::= { usrDnsCacheEntry 3 }
usrDnsCacheRRTTL OBJECT-TYPE
    SYNTAX      DnsTime
    MAX-ACCESS  read-only
    STATUS      current
    DESCRIPTION
           "Time-To-Live of RR in DNS cache.  This is the initial
           TTL value which was received with the RR when it was
           originally received."
::= { usrDnsCacheEntry 4 }
usrDnsCacheRRElapsedTTL OBJECT-TYPE
    SYNTAX      DnsTime
    MAX-ACCESS  read-only
    STATUS      current
    DESCRIPTION
           "Elapsed seconds since RR was received."
::= { usrDnsCacheEntry 5 }
usrDnsCacheRRSource OBJECT-TYPE
    SYNTAX      IpAddress
    MAX-ACCESS  read-only
    STATUS      current
    DESCRIPTION
           "Host from which RR was received, 0.0.0.0 if unknown."
::= { usrDnsCacheEntry 6 }
usrDnsCacheRRData OBJECT-TYPE
    SYNTAX      OCTET STRING
    MAX-ACCESS  read-only
    STATUS      current
    DESCRIPTION
           "RDATA portion of a cached RR.  The value is in the
           format defined for the particular DNS class and type of
           the resource record."
    REFERENCE
           "RFC-1035 section 3.2.1."
::= { usrDnsCacheEntry 7 }
usrDnsCacheRRStatus OBJECT-TYPE
    SYNTAX      RowStatus
    MAX-ACCESS  read-write
    STATUS      current
    DESCRIPTION
           "Status column for the resolver cache table.  Since only
           the agent (DNS resolver) creates rows in this table, the
           only values that a manager may write to this variable
           are active(1) and destroy(6)."
::= { usrDnsCacheEntry 8 }
usrDnsCacheRRPrettyName OBJECT-TYPE
    SYNTAX      DnsName
    MAX-ACCESS  read-only
    STATUS      current
    DESCRIPTION
           "Name of the RR at this row in the table.  This is
           identical to the dnsResCacheRRName variable, except that
           character case is preserved in this variable, per DNS
           conventions."
    REFERENCE
           "RFC-1035 section 2.3.3."
::= { usrDnsCacheEntry 9 }
-- Resolver Negative Cache Table
usrDnsNCacheTable OBJECT-TYPE
    SYNTAX      SEQUENCE OF UsrDnsNCacheEntry
    MAX-ACCESS  not-accessible
    STATUS      current
    DESCRIPTION
           "The resolver's negative response cache.  This table
           contains information about authoritative errors that
           have been cached by the resolver."
::= { usrDns 25 }
usrDnsNCacheEntry OBJECT-TYPE
    SYNTAX      UsrDnsNCacheEntry
    MAX-ACCESS  not-accessible
    STATUS      current
    DESCRIPTION
           "An entry in the resolver's negative response cache
           table.  Only the resolver can create rows.  SNMP SET
           requests may be used to delete rows."
       INDEX     { usrDnsNCacheErrIndex }
::= { usrDnsNCacheTable 1 }
UsrDnsNCacheEntry ::=
    SEQUENCE {
        usrDnsNCacheErrIndex
            Integer32,
        usrDnsNCacheErrQClass
            DnsQClass,
        usrDnsNCacheErrQType
            DnsQType,
        usrDnsNCacheErrTTL
            DnsTime,
        usrDnsNCacheErrElapsedTTL
            DnsTime,
        usrDnsNCacheErrSource
            IpAddress,
        usrDnsNCacheErrCode
            INTEGER,
        usrDnsNCacheErrStatus
            RowStatus,
        usrDnsNCacheErrPrettyName
            DnsName
    }
usrDnsNCacheErrIndex OBJECT-TYPE
    SYNTAX      Integer32
    MAX-ACCESS  read-only
    STATUS      current
    DESCRIPTION
           "A value which makes entries in the table unique."
::= { usrDnsNCacheEntry 9 }
usrDnsNCacheErrQClass OBJECT-TYPE
    SYNTAX      DnsQClass
    MAX-ACCESS  read-only
    STATUS      current
    DESCRIPTION
           "DNS QCLASS associated with a cached authoritative
           error."
::= { usrDnsNCacheEntry 2 }
usrDnsNCacheErrQType OBJECT-TYPE
    SYNTAX      DnsQType
    MAX-ACCESS  read-only
    STATUS      current
    DESCRIPTION
           "DNS QTYPE associated with a cached authoritative error."
::= { usrDnsNCacheEntry 3 }
usrDnsNCacheErrTTL OBJECT-TYPE
    SYNTAX      DnsTime
    MAX-ACCESS  read-only
    STATUS      current
    DESCRIPTION
           "Time-To-Live of a cached authoritative error at the time
           of the error, it should not be decremented by the number
           of seconds since it was received.  This should be the
           TTL as copied from the MINIMUM field of the SOA that
           accompanied the authoritative error, or a smaller value
           if the resolver implements a ceiling on negative
           response cache TTLs."
    REFERENCE
           "RFC-1034 section 4.3.4."
::= { usrDnsNCacheEntry 4 }
usrDnsNCacheErrElapsedTTL OBJECT-TYPE
    SYNTAX      DnsTime
    MAX-ACCESS  read-only
    STATUS      current
    DESCRIPTION
           "Elapsed seconds since authoritative error was received."
::= { usrDnsNCacheEntry 5 }
usrDnsNCacheErrSource OBJECT-TYPE
    SYNTAX      IpAddress
    MAX-ACCESS  read-only
    STATUS      current
    DESCRIPTION
           "Host which sent the authoritative error, 0.0.0.0 if
           unknown."
::= { usrDnsNCacheEntry 6 }
usrDnsNCacheErrCode OBJECT-TYPE
    SYNTAX      INTEGER { nonexistantName(1), noData(2), other(3) }
    MAX-ACCESS  read-only
    STATUS      current
    DESCRIPTION
           "The authoritative error that has been cached:
           nonexistantName(1) indicates an authoritative name error
           (RCODE = 3).
           noData(2) indicates an authoritative response with no
           error (RCODE = 0) and no relevant data.
           other(3) indicates some other cached authoritative
           error.  At present, no such errors are known to exist."
::= { usrDnsNCacheEntry 7 }
usrDnsNCacheErrStatus OBJECT-TYPE
    SYNTAX      RowStatus
    MAX-ACCESS  read-write
    STATUS      current
    DESCRIPTION
           "Status column for the resolver negative response cache
           table.  Since only the agent (DNS resolver) creates rows
           in this table, the only values that a manager may write
           to this variable are active(1) and destroy(6)."
::= { usrDnsNCacheEntry 8 }
usrDnsNCacheErrPrettyName OBJECT-TYPE
    SYNTAX      DnsName
    MAX-ACCESS  read-only
    STATUS      current
    DESCRIPTION
           "QNAME associated with this row in the table.  This is
           identical to the dnsResNCacheErrQName variable, except
           that character case is preserved in this variable, per
           DNS conventions."
    REFERENCE
           "RFC-1035 section 2.3.3."
::= { usrDnsNCacheEntry 10 }
END         -- End USR-DNS-MIB definitions
