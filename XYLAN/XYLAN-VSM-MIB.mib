----------------------------------------
--      FILE:  <xylan-vsm.mib>
--
--                                Alcatel
--                   Architects Of An Internet World
--
--      This module provides authoritative enterprise-specific Simple Network
--      Management Protocol (SNMP) Management Information Base (MIB) definitions.
--
--      The right to make changes in specification and other information contained
--      in this document without prior notice is reserved.
--
--      No liability shall be assumed for any incidental, indirect, special, or
--      consequential damages whatsoever arising from or related to this document or
--      the information contained herein.
--
--      Vendors, end-users, and other interested parties are granted non-exclusive
--      license to use this specification in connection with management of the
--      products for which it is intended to be used.
--
--      Please consult with Customer Service to insure the most appropriate version
--      of this document is used with the products in question:
--
--                 Alcatel Internetworking, Incorporated
--                     (Formerly XYLAN Corporation)
--                         26801 West Agoura Road
--                          Calabasas, CA 91301
--                       United States Of America
--
--              Telephone: North America  800.995.2696
--                         Latin America  877.919.9526
--                         Europe         31.23.556.0100
--                         Asia           65.394.7933
--                         All Other      818.878.4507
--
--              Electronic Mail:                 support@ind.alcatel.com
--              World Wide Web:                  http://www.ind.alcatel.com
--              File Transfer Protocol:  ftp://ftp.ind.alcatel.com/pub/products/mibs
--
--     Copyright (C) 1995-2001 Alcatel Internetworking, Incorporated
--                     ALL RIGHTS RESERVED WORLDWIDE
----------------------------------------
--== Quick Reference: 
--==
--==
--==    .xylanVsmArch.1     = vsmNetworkGroup
--==    .xylanVsmArch.1.1   =   vsmVNTemplateTable
--==    .xylanVsmArch.1.2   =   vsmVNTmplH323GateKeeperPhoneGroupTable
--==    .xylanVsmArch.1.3   =   vsmVNCardTable
--==    .xylanVsmArch.1.4   =   vsmVNCardH323GateKeeperPhoneGroupTable
--==
--==    .xylanVsmArch.2     = vsmSignalingGroup
--==    .xylanVsmArch.2.1   =   vsmSignalingTemplateTable
--==    .xylanVsmArch.2.2   =   vsmSigTmplEmCommonTable
--==    .xylanVsmArch.2.3   =   vsmSigTmplEmDelayTable
--==    .xylanVsmArch.2.4   =   vsmSigTmplEmImmedTable
--==    .xylanVsmArch.2.5   =   vsmSigTmplEmWinkTable
--==    .xylanVsmArch.2.6   =   vsmSigTmplFxoGSTable
--==    .xylanVsmArch.2.7   =   vsmSigTmplFxoLSTable
--==    .xylanVsmArch.2.8   =   vsmSigTmplFxsGSTable
--==    .xylanVsmArch.2.9   =   vsmSigTmplFxsLSTable
--==    .xylanVsmArch.2.10  =   vsmSignalingChannelTable
--==    .xylanVsmArch.2.11  =   vsmSigChanEmCommonTable
--==    .xylanVsmArch.2.12  =   vsmSigChanEmDelayTable
--==    .xylanVsmArch.2.13  =   vsmSigChanEmImmedTable
--==    .xylanVsmArch.2.14  =   vsmSigChanEmWinkTable
--==    .xylanVsmArch.2.15  =   vsmSigChanFxoGSTable
--==    .xylanVsmArch.2.16  =   vsmSigChanFxoLSTable
--==    .xylanVsmArch.2.17  =   vsmSigChanFxsGSTable
--==    .xylanVsmArch.2.18  =   vsmSigChanFxsLSTable
--==
--==    .xylanVsmArch.3     = vsmCodingProfileGroup
--==    .xylanVsmArch.3.1   =   vsmCodingProfileTable
--==
--==    .xylanVsmArch.4     = vsmDialSchemeGroup
--==    .xylanVsmArch.4.1   =   vsmDestinationsTable
--==    .xylanVsmArch.4.2   =   vsmPhoneGroupTable
--==    .xylanVsmArch.4.3   =   vsmPGNumbersTable
--==    .xylanVsmArch.4.4   =   vsmNumPlanTable
--==    .xylanVsmArch.4.5   =   vsmNPPhoneGroupTable
--==    .xylanVsmArch.4.6   =   vsmNPDestinationsTable
--==
--==    .xylanVsmArch.5     = vsmPhysicalGroup
--==    .xylanVsmArch.5.1   =   vsmCardConfTable
--==    .xylanVsmArch.5.2   =   vsmPortConfTable
--==    .xylanVsmArch.5.3   =   vsmChanConfTable
--==    .xylanVsmArch.5.4   =   vsmAllowedCodingProfileTable
--==
--==    .xylanVsmArch.6     = vsmConfigControlGroup
--==
--== =======
--==  Note: the vsmStatsGroup is not supported in this release !
--== =======
--==    .xylanVsmArch.7     = vsmStatsGroup
--==    .xylanVsmArch.7.1   =   vsmTeleLevelTable
--==    .xylanVsmArch.7.2   =   vsmTeleStatsTable
--==    .xylanVsmArch.7.3   =   vsmDspVPStatsTable
--==    .xylanVsmArch.7.4   =   vsmDspRxTxStatsTable
--==    .xylanVsmArch.7.5   =   vsmDspVoiceErrorStatsTable
--==    .xylanVsmArch.7.6   =   vsmDspModemStatsTable
--==    .xylanVsmArch.7.7   =   vsmDspFaxStatsTable
--==    .xylanVsmArch.7.8   =   vsmISDNL2StatsTable
--==	.xylanVsmArch.7.9   =   vsmISDNTeleStatsTable

----------------------------------------

XYLAN-VSM-MIB DEFINITIONS ::= BEGIN

IMPORTS
        DisplayString
                FROM RFC1213-MIB
        OBJECT-TYPE
                FROM RFC-1212
        -- TimeTicks,
        IpAddress
                FROM RFC1155-SMI
        XylanModuleSubunit
                FROM CHASSIS-MIB
        xylanVsmArch
                FROM XYLAN-BASE-MIB;


-- Local Declares

--        Counter32 ::= INTEGER

        RowStatus ::= INTEGER {
                 active(1),
                 notInService(2),
                 notReady(3),
                 createAndGo(4),
                 createAndWait(5),
                 destroy(6)
                 }

        VsmEnableDisabled ::= INTEGER{
                 disabled(1),
                 enabled(2)
                 }

        VsmOnOff ::= INTEGER{
                 off(1),
                 on(2)
                 }

   VsmVoiceCodingType ::= INTEGER {
                aLawPcm                 (1),    --      8 bit A-law PCM  (G.711)
                muLawPcm                (2),    --      8 bit Mu-law PCM (G.711)
                ituG723-53              (3),    --      G.723.1 at 5.3 Kbps
                ituG723-63              (4),    --      G.723.1 at 6.3 Kbps
                ituG729AB               (5),    --      CS-ACELP internal VAD (G.729AB)
                t38-fax                 (6)     --              t.38 fax
                -- fax                     (7),    == This value is not supported in this release.
                -- ituG726-16              (8),    == This value is not supported in this release.
                -- ituG726-24              (9),    == This value is not supported in this release.
                -- ituG726-32              (10),   == This value is not supported in this release.
                -- ituG726-40              (11),   == This value is not supported in this release.
                -- ituG727-16              (12),   == This value is not supported in this release.
                -- ituG727-24              (13),   == This value is not supported in this release.
                -- ituG727-32              (14),   == This value is not supported in this release.
                -- ituG727-40              (15),   == This value is not supported in this release.
                -- clearChan               (16),   == This value is not supported in this release.
                -- pktSig                  (17),   == This value is not supported in this release.
                -- ituG728-16              (18) == This value is not supported in this release.
                }


--======================================================================

vsmNetworkGroup OBJECT IDENTIFIER ::= { xylanVsmArch 1 }
vsmSignalingGroup OBJECT IDENTIFIER ::= { xylanVsmArch 2 }
vsmCodingProfileGroup OBJECT IDENTIFIER ::= { xylanVsmArch 3 }
vsmDialSchemeGroup OBJECT IDENTIFIER ::= { xylanVsmArch 4 }
vsmPhysicalGroup  OBJECT IDENTIFIER ::= { xylanVsmArch 5 }
vsmConfigControlGroup  OBJECT IDENTIFIER ::= { xylanVsmArch 6 }
--== =======
--== Note: the vsmStatsGroup is not supported in this release !
--== =======
vsmStatsGroup OBJECT IDENTIFIER ::= { xylanVsmArch 7 }


--======================================================================
--
--      The Voice Switching Module MIB provides definitions for Xylan
--      private objects to be used exclusively for our architecture and
--      implementation.
--
--        One area of implementation are the profile definitions.  There
--      are four types of profiles:
--        -      Dialing Plan
--        -      Telephony Port Interfaces
--        -      Network Interfaces
--              -  Coding Profiles (these are defined in the voicex.mib)
--
--      These profiles are maintained in a global manner, and are
--      associated with various modules, ports, and channels via
--      configuration.
--
--======================================================================

--======================================================================
--
--      Voice Over IP Network Group
--
--======================================================================
--======================================================================

--======================================================================
--
--      Voice Network Template table
--
--      Any object description changed in this table must also be changed
--      in the vsmVNCardTable
--======================================================================
  vsmVNTemplateTable OBJECT-TYPE
          SYNTAX SEQUENCE OF VsmVNTemplateEntry
          ACCESS not-accessible
          STATUS mandatory
          DESCRIPTION
                 "This table is not supported"

          ::= { vsmNetworkGroup 1 }

  vsmVNTemplateEntry OBJECT-TYPE
          SYNTAX VsmVNTemplateEntry
          ACCESS not-accessible
          STATUS mandatory
          DESCRIPTION
                 "This is an entry in the vsmVNTemplateTable.  This table is not supported"

          INDEX { vsmVNTmplIndex }
          ::= { vsmVNTemplateTable 1 }

  VsmVNTemplateEntry ::=
          SEQUENCE {
                vsmVNTmplIndex                                             INTEGER,
                vsmVNTmplName                                              DisplayString,
--                vsmVNTmplH323DisplayName                                   DisplayString,
--                vsmVNTmplRTPPortMode                                       INTEGER,
--                vsmVNTmplRTPPortBase                                       INTEGER,
--                vsmVNTmplH323OutFastStart                                  VsmEnableDisabled,
--                vsmVNTmplH323InFastStart                                   VsmEnableDisabled,
--                vsmVNTmplH323GatekeeperCtrl                                VsmEnableDisabled,
--                vsmVNTmplH323GatekeeperMode                                INTEGER,
--                vsmVNTmplH323GatekeeperAddr                                IpAddress,
--                vsmVNTmplH323AllowCallsWithoutGatekeeper                   VsmEnableDisabled,
--                vsmVNTmplH323GatekeeperMaxRetries                          INTEGER,
--                vsmVNTmplH323EndpointRegType                               INTEGER,
--                vsmVNTmplH323Notification                                  VsmEnableDisabled,
               vsmVNTmplRowStatus                                         RowStatus
                }

  vsmVNTmplIndex OBJECT-TYPE
          SYNTAX INTEGER
          ACCESS read-write
          STATUS mandatory
          DESCRIPTION
                 "Integer index into this table.

                 For more information, please see the following CLI command:
                   [Note: There is NO equivalent command in the CLI.]
                 "
          ::= { vsmVNTemplateEntry 1 }

  vsmVNTmplName OBJECT-TYPE
          SYNTAX DisplayString
          ACCESS read-write
          STATUS deprecated
          DESCRIPTION
                 "This is not supported.

                  For more information, please see the following CLI command:
                     voice network template 'vsmNetworkTemplateName'
                  "
          ::= { vsmVNTemplateEntry 2 }
--                
-- ======================================================================
-- This Section is not supported
-- ======================================================================
--
--  vsmVNTmplH323DisplayName OBJECT-TYPE
--          SYNTAX DisplayString
--          ACCESS read-write
--          STATUS mandatory
--          DESCRIPTION
--                 "Specifies the display name information that is carried in the
--                 H.323 setup messages. The display-name string is inserted into
--                 the Q.931 display information field and in the sourceAddress
--                 field of the H.323 setup-UUIE. The string can be up to 64 bytes.
--
--                 For more information, please see the following CLI command:
--                    voice network template 'vsmNetworkTemplateName' h.323 display name 'string'
--                 "
--          ::= { vsmVNTemplateEntry 3 }
--
--  vsmVNTmplRTPPortMode OBJECT-TYPE
--          SYNTAX INTEGER {
--                                dynamic         (1),
--                                sequential      (2)
--                                }
--          ACCESS read-write
--          STATUS mandatory
--          DESCRIPTION
--                 "Selects the method of port number assignment for RTP and RTCP
--                 ports.
--
--                 For more information, please see the following CLI command:
--                    voice network template 'vsmNetworkTemplateName' h.323 rtp port mode dynamic
--                    voice network template 'vsmNetworkTemplateName' h.323 rtp port mode sequential
--                 "
--          DEFVAL { dynamic }
--          ::= { vsmVNTemplateEntry 4 }
--
--  vsmVNTmplRTPPortBase OBJECT-TYPE
--          SYNTAX INTEGER (1..65534)
--          ACCESS read-write
--          STATUS mandatory
--          DESCRIPTION
--                 "Selects the starting port number for assignment of RTP and RTCP
--                 ports. When H.323 calls are made an RTP or RTCP port is opened for
--                  each call. The H.323 specification states that the RTP port number
--                  should be even in value and the RTCP port number should be one
--                  greater than the RTP port value. In order to accomplish this sort
--                 of controlled allocation, the ports are assigned starting at the
--                  rtp-port-base value. CCB 0 will use ports numbered rtp-port-base
--                  and rtp-port-base + 1. CCB 1 will used the next two successive ports,
--                  etc.
-- 
--                  For more information, please see the following CLI command:
--                     voice network template 'vsmNetworkTemplateName' h.323 rtp port base value
--                  "
--                  DEFVAL { 30000 }
--           ::= { vsmVNTemplateEntry 5 }
-- 
--    vsmVNTmplH323OutFastStart OBJECT-TYPE
--             SYNTAX VsmEnableDisabled
--             ACCESS read-write
--             STATUS deprecated
--             DESCRIPTION
--                    "deprecated.  This command has moved to vsmCardH323OutFastStart."
--             DEFVAL { enabled }
--            ::= { vsmVNTemplateEntry 6 }
-- 
--     vsmVNTmplH323InFastStart OBJECT-TYPE
--             SYNTAX VsmEnableDisabled
--             ACCESS read-write
--             STATUS deprecated
--             DESCRIPTION
--                    "deprecated.  This command has moved to vsmCardH323InFastStart."
--             DEFVAL { enabled }
--             ::= { vsmVNTemplateEntry 7 }
-- 
--     vsmVNTmplH323GatekeeperCtrl OBJECT-TYPE
--           SYNTAX VsmEnableDisabled
--           ACCESS read-write
--           STATUS mandatory
--           DESCRIPTION
--                  "Specifies whether GateKeeper control is on or off.  If enabled, then
--                  the vsmVNTmplH323GatekeeperMode also needs to be specified.
-- 
--                  For more information, please see the following CLI command:
--                     voice network template 'vsmNetworkTemplateName' h.323 gatekeeper control on
--                     voice network template 'vsmNetworkTemplateName' h.323 gatekeeper control off
--                 "
--           DEFVAL { disabled }
--           ::= { vsmVNTemplateEntry 8 }
-- 
--   vsmVNTmplH323GatekeeperMode OBJECT-TYPE
--           SYNTAX INTEGER {
--                                 off     (1),
--                                manual  (2),
--                                 auto    (3)
--                          }
--           ACCESS read-write
--           STATUS mandatory
--           DESCRIPTION
--                  "Controls gatekeeper operation. Internally, the setting affects
--                  two different variables in the HSMU configuration: The HSMU
--                  configuration field use_GK controls gatekeeper operation being
--                  enabled or disabled. When enabled, the configuration field
--                  auto_GK_discovery determines automatic or manual discovery.
--                 These are collapsed into one command for convenience.
-- 
--                  Note: 'auto    (3)' is not suppoted in this release.
-- 
--                  For more information, please see the following CLI command:
--                                 voice network template 'vsmNetworkTemplateName' h.323 gatekeeper control off
--                     voice network template 'vsmNetworkTemplateName' h.323 gatekeeper mode manual
-- 
--                  Note: The following are not supported in this Release
--                                     voice network template 'vsmNetworkTemplateName' h.323 gatekeeper mode auto
--                  "
--          DEFVAL { manual }
--           ::= { vsmVNTemplateEntry 9 }
-- 
--   vsmVNTmplH323GatekeeperAddr OBJECT-TYPE
--           SYNTAX IpAddress
--           ACCESS read-write
--           STATUS mandatory
--          DESCRIPTION
--                  "Specifies the address of the gatekeeper when configured for
--                  manual mode. Only the IP address needs to be specified, as port
--                  1719 is used.
-- 
--                  For more information, please see the following CLI command:
--                     voice network template 'vsmNetworkTemplateName' h.323 gatekeeper address xxx.xxx.xxx.xxx
--                  "
--           ::= { vsmVNTemplateEntry 10 }
-- 
--   vsmVNTmplH323AllowCallsWithoutGatekeeper OBJECT-TYPE
--          SYNTAX VsmEnableDisabled
--           ACCESS read-write
--           STATUS mandatory
--           DESCRIPTION
--                  "This command is used to inform the H.323 stack to allow calls when
--                  the endpoint is not registered with a gatekeeper. The endpoint can
--                  remain unregistered for two reasons:
--                  1. The gatekeeper could not be found. (Auto discovery failed,
--                  an incorrect address was specified for manual mode, or the gatekeeper
--                  simply is not responding.)
--                  2. The gatekeeper was discovered but the registration was rejected.
--                 This could occur because of a policy implemented in the gatekeeper
--                  that is limiting registration of a particular endpoint.
--                  Enabled is true and disabled is false.
-- 
--                  For more information, please see the following CLI command:
--                     voice network template 'vsmNetworkTemplateName' h.323 allow calls without gatekeeper true
--                     voice network template 'vsmNetworkTemplateName' h.323 allow calls without gatekeeper false
--                 "
--           DEFVAL { enabled }
--           ::= { vsmVNTemplateEntry 11 }
-- 
--   vsmVNTmplH323GatekeeperMaxRetries OBJECT-TYPE
--           SYNTAX INTEGER
--           ACCESS read-write
--           STATUS mandatory
--           DESCRIPTION
--                  "Specifies how many registration attempts will be made before
--                  the endpoint considers itself to have failed registration. Once
--                 this number of unsuccessful attempts have been made, the endpoint
--                  will only be able to place calls if allow-calls-without-gatekeeper
--                  is true.
-- 
--                  For more information, please see the following CLI command:
--                     voice network template 'vsmNetworkTemplateName' h.323 gatekeeper maximum tries number
--                  "
--           DEFVAL { 4 }
--           ::= { vsmVNTemplateEntry 12 }
-- 
--   vsmVNTmplH323EndpointRegType OBJECT-TYPE
--          SYNTAX INTEGER {
--                                 gateway         (1),
--                                 terminal        (2)
--                          }
--           ACCESS read-write
--           STATUS mandatory
--           DESCRIPTION
--                 "Specifies the endpoint registration type. This should not be
--                  confused with the H.245 terminal type, although the two parameters
--                  should be programmed consistently. This parameter specifies how the
--                  endpoint will register itself with the gatekeeper, and has nothing
--                  to do with master/slave determination.
-- 
--                  For more information, please see the following CLI command:
--                     voice network template 'vsmNetworkTemplateName' h.323 endpoint registration type gateway
--                    voice network template 'vsmNetworkTemplateName' h.323 endpoint registration type terminal
--                 "
--          DEFVAL { gateway }
--          ::= { vsmVNTemplateEntry 13 }
--
--    vsmVNTmplH323Notification OBJECT-TYPE
--            SYNTAX VsmEnableDisabled
--            ACCESS read-write
--            STATUS deprecated
--            DESCRIPTION
--                 "This object is no longer supported."
--            DEFVAL { disabled }
--            ::= { vsmVNTemplateEntry 14 }

  vsmVNTmplRowStatus OBJECT-TYPE
          SYNTAX RowStatus
          ACCESS read-write
          STATUS mandatory
          DESCRIPTION
             "This object is the RowStatus (locking flag) for creating the
             vsmVNTemplateTable conceptual row. This table is not supported."

--           This table does not support
--           createAndWait.  vsmVNTmplname must be supplied in the request
--           to create a row, it is a required field.
--
--           For more information, please see the following CLI command:
--              voice no network template 'vsmNetworkTemplateName'
--          "
          ::= { vsmVNTemplateEntry 3 }

-- ======================================================================
--
--      Voice Network Template H323 GateKeeper Phone Group table 
--
-- ======================================================================

        vsmVNTmplH323GateKeeperPhoneGroupTable OBJECT-TYPE
                SYNTAX SEQUENCE OF VsmVNTmplH323GateKeeperPhoneGroupEntry
                ACCESS not-accessible
                STATUS mandatory
                DESCRIPTION
                        "This table is not supported."
                ::= { vsmNetworkGroup 2 }

        vsmVNTmplH323GateKeeperPhoneGroupEntry OBJECT-TYPE
                SYNTAX VsmVNTmplH323GateKeeperPhoneGroupEntry
                ACCESS not-accessible
                STATUS mandatory
                DESCRIPTION
                        "This is an entry in the vsmVNTemplateTable. This table is not supported.

                        "
                INDEX { vsmVNTmplName, vsmPhoneGroupName }
                ::= { vsmVNTmplH323GateKeeperPhoneGroupTable 1 }

        VsmVNTmplH323GateKeeperPhoneGroupEntry ::=
                SEQUENCE {
                        vsmVNTmplH323GateKeeperPhoneGroupRowStatus                      RowStatus
                        }

        vsmVNTmplH323GateKeeperPhoneGroupRowStatus OBJECT-TYPE
                SYNTAX RowStatus
                ACCESS read-write
                STATUS mandatory
                DESCRIPTION
                        "Note: destroy(6) is not supported in this release. 

                                                This table is not supported                        "

                ::= { vsmVNTmplH323GateKeeperPhoneGroupEntry 1 }




--======================================================================
--
--      Voice Network Card table
--
--      Any object description changed in this table, must also be
--      changed in vsmVNTemplateTable.
--======================================================================
  vsmVNCardTable OBJECT-TYPE
          SYNTAX SEQUENCE OF VsmVNCardEntry
          ACCESS not-accessible
          STATUS mandatory
          DESCRIPTION
                 "This table contains information for each network interface."
          ::= { vsmNetworkGroup 3 }

  vsmVNCardEntry OBJECT-TYPE
          SYNTAX VsmVNCardEntry
          ACCESS not-accessible
          STATUS mandatory
          DESCRIPTION
                 "This is an entry in the vsmVNCardTable. 

                  For more information, please see the following CLI command:
                    [Note: There is NO equivalent command in the CLI.]
                 "
          INDEX { vsmCardSlotIndex, vsmCardSubunitIndex }
          ::= { vsmVNCardTable 1 }

  VsmVNCardEntry ::=
          SEQUENCE {
                vsmVNCardH323DisplayName                                   DisplayString,
                vsmVNCardRTPPortMode                                       INTEGER,
                vsmVNCardRTPPortBase                                       INTEGER,
                vsmVNCardH323OutFastStart                                  VsmEnableDisabled,
                vsmVNCardH323InFastStart                                   VsmEnableDisabled,
                vsmVNCardH323GatekeeperCtrl                                VsmEnableDisabled,
                vsmVNCardH323GatekeeperMode                                INTEGER,
                vsmVNCardH323GatekeeperAddr                                IpAddress,
                vsmVNCardH323AllowCallsWithoutGatekeeper                   VsmEnableDisabled,
                vsmVNCardH323GatekeeperMaxRetries                          INTEGER,
                vsmVNCardH323EndpointRegType                               INTEGER,
                vsmVNCardH323Notification                                  VsmEnableDisabled
--                vsmVNCardAssignTmplName                                    DisplayString,
--                vsmVNCardAssignTmplStatus                                  INTEGER
                }

  vsmVNCardH323DisplayName OBJECT-TYPE
          SYNTAX DisplayString
          ACCESS read-write
          STATUS mandatory
          DESCRIPTION
                 "Specifies the display name information that is carried in the
                 H.323 setup messages. The display-name string is inserted into
                 the Q.931 display information field and in the sourceAddress
                 field of the H.323 setup-UUIE. The string can be up to 64 bytes.

                 For more information, please see the following CLI command:
                  voice network card slot/card h.323 display name 'string'
                 "
          ::= { vsmVNCardEntry 1 }

  vsmVNCardRTPPortMode OBJECT-TYPE
          SYNTAX INTEGER {
                                dynamic         (1),
                                sequential      (2)
                                }
          ACCESS read-write
          STATUS mandatory
          DESCRIPTION
                 "Selects the method of port number assignment for RTP and RTCP
                 ports.

                 For more information, please see the following CLI command:
                  voice network card slot/card h.323 rtp port mode dynamic
                  voice network card slot/card h.323 rtp port mode sequential
                 "
          DEFVAL { dynamic }
          ::= { vsmVNCardEntry 2 }

  vsmVNCardRTPPortBase OBJECT-TYPE
          SYNTAX INTEGER (1..65534)
          ACCESS read-write
          STATUS mandatory
          DESCRIPTION
                 "Selects the starting port number for assignment of RTP and RTCP
                 ports. When H.323 calls are made an RTP or RTCP port is opened for
                 each call. The H.323 specification states that the RTP port number
                 should be even in value and the RTCP port number should be one
                 greater than the RTP port value. In order to accomplish this sort
                 of controlled allocation, the ports are assigned starting at the
                 rtp-port-base value. CCB 0 will use ports numbered rtp-port-base
                 and rtp-port-base + 1. CCB 1 will used the next two successive ports,
                 etc.

                 For more information, please see the following CLI command:
                  voice network card slot/card h.323 rtp port base value
                 "
          DEFVAL { 30000 }
          ::= { vsmVNCardEntry 3 }

  vsmVNCardH323OutFastStart OBJECT-TYPE
          SYNTAX VsmEnableDisabled
          ACCESS read-write
          STATUS deprecated
          DESCRIPTION
                 "This command is used to select the H.323 Fast Start mode on
                 the outgoing side of the link.

                 For more information, please see the following CLI command:
                 voice daughter card slot/daughter_card_number h.323 out[going] fast start on
                 voice daughter card slot/daughter_card_number h.323 out[going] fast start off
                 "
          DEFVAL { enabled }
          ::= { vsmVNCardEntry 4 }

  vsmVNCardH323InFastStart OBJECT-TYPE
          SYNTAX VsmEnableDisabled
          ACCESS read-write
          STATUS mandatory
          DESCRIPTION
                 "This command is used to select the H.323 Fast Start mode on
                 the incoming side of the link.

                 For more information, please see the following CLI command:
                    voice daughter card slot/daughter_card_number h.323 in[coming] fast start on
                    voice daughter card slot/daughter_card_number h.323 in[coming] fast start off
                 "
          DEFVAL { enabled }
          ::= { vsmVNCardEntry 5 }

  vsmVNCardH323GatekeeperCtrl OBJECT-TYPE
          SYNTAX VsmEnableDisabled
          ACCESS read-write
          STATUS mandatory
          DESCRIPTION
                 "Specifies whether GateKeeper control is on or off. If enabled, then
                 the vsmVNTmplH323GatekeeperMode also needs to be specified.


                 For more information, please see the following CLI command:
                    voice network card slot/card h.323 gatekeeper control on
                    voice network card slot/card h.323 gatekeeper control off
                 "
          DEFVAL { disabled }
          ::= { vsmVNCardEntry 6 }

  vsmVNCardH323GatekeeperMode OBJECT-TYPE
          SYNTAX INTEGER {
                                off     (1),
                                manual  (2),
                                auto    (3)
                                }
          ACCESS read-write
          STATUS mandatory
          DESCRIPTION
                 "Controls gatekeeper operation. Internally, the setting affects
                 two different variables in the HSMU configuration: The HSMU
                 configuration field use_GK controls gatekeeper operation being
                 enabled or disabled. When enabled, the configuration field
                 auto_GK_discovery determines automatic or manual discovery.
                 These are collapsed into one command for convenience.

                 Note: 'auto    (3)' is not suppoted in this release.

                 For more information, please see the following CLI command:
                                          voice network card slot/card h.323 gatekeeper control off
                      voice network card slot/card h.323 gatekeeper mode manual

                 Note: The following are not supported in this Release
                     voice network card slot/card h.323 gatekeeper mode auto
                 "
          DEFVAL { manual }
          ::= { vsmVNCardEntry 7 }

  vsmVNCardH323GatekeeperAddr OBJECT-TYPE
          SYNTAX IpAddress
          ACCESS read-write
          STATUS mandatory
          DESCRIPTION
                 "Specifies the address of the gatekeeper when configured for
                 manual mode. Only the IP address needs to be specified, as port
                 1719 is used.

                 For more information, please see the following CLI command:
                  voice network card slot/card h.323 gatekeeper address xxx.xxx.xxx.xxx
                 "
          ::= { vsmVNCardEntry 8 }

  vsmVNCardH323AllowCallsWithoutGatekeeper OBJECT-TYPE
          SYNTAX VsmEnableDisabled
          ACCESS read-write
          STATUS mandatory
          DESCRIPTION
                 "This command is used to inform the H.323 stack to allow calls when
                 the endpoint is not registered with a gatekeeper. The endpoint can
                 remain unregistered for two reasons:
                1. The gatekeeper could not be found. (Auto discovery failed,
                an incorrect address was specified for manual mode, or the gatekeeper
                simply is not responding.)
                2. The gatekeeper was discovered but the registration was rejected.
                This could occur because of a policy implemented in the gatekeeper
                that is limiting registration of a particular endpoint.
                Enabled is true and disabled is false.

                For more information, please see the following CLI command:
                 voice network card slot/card h.323 allow calls without gatekeeper true
                 voice network card slot/card h.323 allow calls without gatekeeper false
                "
          DEFVAL { enabled }
          ::= { vsmVNCardEntry 9 }

  vsmVNCardH323GatekeeperMaxRetries OBJECT-TYPE
          SYNTAX INTEGER
          ACCESS read-write
          STATUS mandatory
          DESCRIPTION
                 "Specifies how many registration attempts will be made before
                 the endpoint considers itself to have failed registration. Once
                 this number of unsuccessful attempts have been made, the endpoint
                 will only be able to place calls if allow-calls-without-gatekeeper
                 is true.

                 For more information, please see the following CLI command:
                  voice network card slot/card h.323 gatekeeper maximum tries number
                 "
          DEFVAL { 4 }
          ::= { vsmVNCardEntry 10 }

  vsmVNCardH323EndpointRegType OBJECT-TYPE
          SYNTAX INTEGER {
                                gateway         (1),
                                terminal        (2)
                                }
          ACCESS read-write
          STATUS mandatory
          DESCRIPTION
                 "Specifies the endpoint registration type. This should not be
                 confused with the H.245 terminal type, although the two parameters
                 should be programmed consistently. This parameter specifies how the
                 endpoint will register itself with the gatekeeper, and has nothing
                 to do with master/slave determination.

                 For more information, please see the following CLI command:
                  voice network card slot/card h.323 endpoint registration type gateway
                  voice network card slot/card h.323 endpoint registration type terminal
                 "
          DEFVAL { gateway }
          ::= { vsmVNCardEntry 11 }

    vsmVNCardH323Notification OBJECT-TYPE
            SYNTAX VsmEnableDisabled
            ACCESS read-write
            STATUS deprecated
            DESCRIPTION
                 "This object is no longer supported."
            DEFVAL { enabled }
            ::= { vsmVNCardEntry 12 }

--  vsmVNCardAssignTmplName OBJECT-TYPE
--          SYNTAX DisplayString
--          ACCESS read-write
--          STATUS mandatory
--          DESCRIPTION
--                 "This object provides a name for a VN Template that can be assigned
--                 to this card.  See vsmVNCardTmpltAssignStatus for a complete
--                 description on how templates are assigned to rows in this table.
--                 Rows that have not been assigned to a template will have an
--                  value of 0.  Also once the status goes to invalid
--                 because of a change in either the template or in this card row,
--                 the vsmVNCardTmpltId will go to 0.
--
--                 For more information, please see the following CLI command:
--                  voice daughter card slot/daughter_card_number assign network template 'vsmProfileNetworkName'
--                 "
--          ::= { vsmVNCardEntry 13 }
--
--   vsmVNCardAssignTmplStatus OBJECT-TYPE
--          SYNTAX INTEGER {
--                                assign          (1),
--                                inactive        (2),
--                                active          (3)
--                                }
--          ACCESS read-write
--          STATUS mandatory
--          DESCRIPTION
--                 "This object forces a VN template to be assigned to this card.  When
--                 the template is assigned, all values in the template are copied into
--                 the specified row in this table.  Active means there is a template
--                 actively associated with this row.  Once either the template is
--                 changed or an object in this row is changed, the status goes to
--                 inactive, because there is no longer a template actively associated
--                 with this row.
--
--                 For more information, please see the following CLI command:
--                   [Note: There is NO equivalent command in the CLI.]
--                 "
--          ::= { vsmVNCardEntry 14 }
--
--
--======================================================================
--
--      Voice Network Card H323 GateKeeper Phone Group table 
--
--======================================================================

        vsmVNCardH323GateKeeperPhoneGroupTable OBJECT-TYPE
                SYNTAX SEQUENCE OF VsmVNCardH323GateKeeperPhoneGroupEntry
                ACCESS not-accessible
                STATUS mandatory
                DESCRIPTION
                        "This table contains arrays of Phone Group that are
                        associated with the gatekeeper.
                        "
                ::= { vsmNetworkGroup 4 }

        vsmVNCardH323GateKeeperPhoneGroupEntry OBJECT-TYPE
                SYNTAX VsmVNCardH323GateKeeperPhoneGroupEntry
                ACCESS not-accessible
                STATUS mandatory
                DESCRIPTION
                        "This is an entry in the vsmVNCardTable.

                        For more information, please see the following CLI command:
                        voice network card slot/card h.323 gatekeeper associate phone group 'phoneGrpName'
                        voice network card slot/card h.323 gatekeeper disassociate phone group 'phoneGrpName'

                        "
                INDEX { vsmCardSlotIndex,
                        vsmCardSubunitIndex, vsmPhoneGroupName }
                ::= { vsmVNCardH323GateKeeperPhoneGroupTable 1 }

        VsmVNCardH323GateKeeperPhoneGroupEntry ::=
                SEQUENCE {
                        vsmVNCardH323GateKeeperPhoneGroupRowStatus                      RowStatus
                        }

        vsmVNCardH323GateKeeperPhoneGroupRowStatus OBJECT-TYPE
                SYNTAX RowStatus
                ACCESS read-write
                STATUS mandatory
                DESCRIPTION
                        "Note: destroy(6) is not supported in this release. 

                        For more information, please see the following CLI command:
                        voice network card slot/card h.323 gatekeeper associate phone group 'phoneGrpName'
                        voice network card slot/card h.323 gatekeeper disassociate phone group 'phoneGrpName'
                        "
                ::= { vsmVNCardH323GateKeeperPhoneGroupEntry 1 }



--======================================================================
--======================================================================
--==
--== The Signaling Group
--==
--======================================================================
--== Note: vsmSignalingGroup OBJECT IDENTIFIER ::= { xylanVsmArch 2 }
--======================================================================

--======================================================================
--
--       Signaling Template Table
--
--      This table specifies the name of the template as well as the type
--      of signaling being used.  The index to all other signaling related
--      tables are indexed using the index to this table.
--
--======================================================================
  vsmSignalingTemplateTable OBJECT-TYPE
          SYNTAX SEQUENCE OF VsmSignalingTemplateEntry
          ACCESS not-accessible
          STATUS mandatory
          DESCRIPTION
                 "This table contains information for each telephony signaling
                 interface template. This table is not supported
                 "
          ::= { vsmSignalingGroup 1 }

  vsmSignalingTemplateEntry OBJECT-TYPE
          SYNTAX VsmSignalingTemplateEntry
          ACCESS not-accessible
          STATUS mandatory
          DESCRIPTION
                 "This is an entry in the vsmSignalingTemplateTable.  This table is not supported

                 For more information, please see the following CLI command:
                   [Note: There is NO equivalent command in the CLI.]
                 "
          INDEX { vsmSigTmplIndex }
          ::= { vsmSignalingTemplateTable 1 }

  VsmSignalingTemplateEntry ::=
          SEQUENCE {
                vsmSigTmplIndex                                  INTEGER,
                vsmSigTmplName                                   DisplayString,
--                vsmSigTmplProtocol                               INTEGER,
--                vsmSigTmplCallerIdName                           INTEGER,
--                vsmSigTmplCallerIdNameStr                        DisplayString,
--                vsmSigTmplCallerIdNumber                         INTEGER,
--                vsmSigTmplCallerIdNumberStr                      DisplayString,
--                vsmSigTmplToneTable                              INTEGER,
--                vsmSigTmplOutDialType                            INTEGER,
--                vsmSigTmplOutWait                                INTEGER,
--                vsmSigTmplOutToneDigitDur                        INTEGER,
--                vsmSigTmplOutToneInterDigitDur                   INTEGER,
--                vsmSigTmplUnused                                 INTEGER,
--                vsmSigTmplCallLimitCtrl                          VsmEnableDisabled,
--                vsmSigTmplCallLimit                              INTEGER,
--                vsmSigTmplAnswerWaitLimitCtrl                    VsmEnableDisabled,
--                vsmSigTmplAnswerWaitLimit                        INTEGER,
--                vsmSigTmplHangupWaitLimitCtrl                    VsmEnableDisabled,
--                vsmSigTmplHangupWaitLimit                        INTEGER,
--                vsmSigTmplFaxHoldoverDelay                       INTEGER,
--                vsmSigTmplCompanding                             INTEGER,
--                vsmSigTmplReceiveGain                            INTEGER,
--                vsmSigTmplTransmitGain                           INTEGER,
--                vsmSigTmplIdleNoise                              INTEGER,
--                vsmSigTmplOverrideInBandCallProgressTones        VsmEnableDisabled,
--                vsmSigTmplOverrideInBandCodecSwitching           VsmEnableDisabled,
--                vsmSigTmplOverridePSUCodecSwitching              VsmEnableDisabled,
--                vsmSigTmplOverrideNetworkOverlapDialing          VsmEnableDisabled,
--                vsmSigTmplOverrideFullCallProgressTones          VsmEnableDisabled,
--                vsmSigTmplOverrideRingBack                       VsmEnableDisabled,
--                vsmSigTmplOverrideInfoElementTransport           VsmEnableDisabled,
--                vsmSigTmplOverrideQSIGInfoElementTransport       VsmEnableDisabled,
--                vsmSigTmplOverrideDataSetup                               VsmOnOff,
--                vsmSigTmplOverrideVoiceSetup                             VsmOnOff,
--                vsmSigTmplOverrideFAXSetup                               VsmOnOff,
--                vsmSigTmplOverrideModemSetup                             VsmOnOff,
--                vsmSigTmplCallProgressToneDetControl     INTEGER,
--                vsmSigTmplCallProgressToneDetCfg         INTEGER,
--                vsmSigTmplAcousticEchoCanOper            INTEGER,
--                vsmSigTmplV18ToneDetThHangTime                   INTEGER,
--                vsmSigTmplV18ToneDetThLevel                      INTEGER,
--                vsmSigTmplV18ToneDetThFraction                   INTEGER,
--                vsmSigTmplSinFreqToneDetThLev                    INTEGER,
--                vsmSigTmplSinFreqToneDetThTime                   INTEGER,
--                vsmSigTmplEchoCancelNonSens                      INTEGER,
--                vsmSigTmplAcousticEchoCancellerMode              VsmEnableDisabled,
--                vsmSigTmplAcouEchoCanNonProc                     VsmEnableDisabled,
--                vsmSigTmplAcEchoCanSetSpGain                     INTEGER,
--                vsmSigTmplAcEchoCanFreeSpGain                    INTEGER,
--                                vsmSigTmplFxsLSCadenceCoefficient                                INTEGER,
--                                vsmSigTmplFxsLSRingId                                                    INTEGER,
--                                vsmSigTmplFxsGSCadenceCoefficient                                INTEGER,
--                                vsmSigTmplFxsGSRingId                                                    INTEGER,
                vsmSigTmplRowStatus                              RowStatus
                }

  vsmSigTmplIndex OBJECT-TYPE
          SYNTAX INTEGER
          ACCESS read-write
          STATUS mandatory
          DESCRIPTION
                 "Integer index into this table. This table is not supported
--                  For more information, please see the following CLI command:
--                   [Note: There is NO equivalent command in the CLI.]
                 "
          ::= { vsmSignalingTemplateEntry 1 }

  vsmSigTmplName OBJECT-TYPE
          SYNTAX DisplayString
          ACCESS read-write
          STATUS deprecated
          DESCRIPTION
                 "This is not supported.

                  For more information, please see the following CLI command:
                   voice signaling template 'signalingTemplateName'
                  "
          ::= { vsmSignalingTemplateEntry 2 }
--                
-- ======================================================================
-- This Section is not supported
-- ======================================================================
--
--  vsmSigTmplProtocol OBJECT-TYPE
--          SYNTAX INTEGER {
--                                 emDelayStart           (1),
--                                 emImmedStart           (2),
--                                 emWinkStart            (3),
--                                 fxoGroundStart         (4),
--                                 fxsGroundStart         (5),
--                                 fxoLoopStart           (6),
--                                 fxsLoopStart           (7),
--                                 isdn                   (8)
--                                         }
--          ACCESS read-write
--          STATUS mandatory
--          DESCRIPTION
--                "The signaling protocol this template has been set up to perform.
--
--                For more information, please see the following CLI command:
--                 voice signaling template 'signalingTemplateName' protocol fxs ls
--                 voice signaling template 'signalingTemplateName' protocol fxo ls
--                 voice signaling template 'signalingTemplateName' protocol fxs gs
--                 voice signaling template 'signalingTemplateName' protocol fxo gs
--                 voice signaling template 'signalingTemplateName' protocol emi
--                 voice signaling template 'signalingTemplateName' protocol emd
--                 voice signaling template 'signalingTemplateName' protocol emw
--                 voice signaling template 'signalingTemplateName' protocol ISDN
--                 "
--          DEFVAL { emWinkStart }
--          ::= { vsmSignalingTemplateEntry 3 }
--
--  vsmSigTmplCallerIdName OBJECT-TYPE
--           SYNTAX INTEGER {
--                                        private         (1),
--                                        unavailable (2),
--                                        available       (3)
--                                        }
--           ACCESS  read-write
--           STATUS mandatory
--           DESCRIPTION
--                "The originating name to transmit may be private, unavailable
--                or available.
--
--                For more information, please see the following CLI command:
--                 voice signaling template 'signalingTemplateName' caller id name private
--                 voice signaling template 'signalingTemplateName' caller id name unavailable
--                 "
--           DEFVAL { unavailable }
--           ::= { vsmSignalingTemplateEntry 4 }
--
--  vsmSigTmplCallerIdNameStr OBJECT-TYPE
--           SYNTAX DisplayString
--           ACCESS  read-write
--           STATUS mandatory
--           DESCRIPTION
--                "The caller Id name is only meaningful if the
--                vsmSigTmplCallerIdName is set to available.
--
--                For more information, please see the following CLI command:
--                 voice signaling template 'signalingTemplateName' caller id name 'callerIdName'
--                 "
--           ::= { vsmSignalingTemplateEntry 5 }
--
--  vsmSigTmplCallerIdNumber OBJECT-TYPE
--           SYNTAX INTEGER {
--                                        private         (1),
--                                        unavailable (2),
--                                        available       (3)
--                                        }
--           ACCESS  read-write
--           STATUS mandatory
--           DESCRIPTION
--                "The originating phone number to transmit may be private,
--                unavailable or available.
--
--                For more information, please see the following CLI command:
--                 voice signaling template 'signalingTemplateName' caller id number private
--                 voice signaling template 'signalingTemplateName' caller id number unavailable
--                "
--           DEFVAL { unavailable }
--           ::= { vsmSignalingTemplateEntry 6 }
--
--  vsmSigTmplCallerIdNumberStr OBJECT-TYPE
--           SYNTAX DisplayString
--           ACCESS  read-write
--           STATUS mandatory
--           DESCRIPTION
--                "The originating telephone number to transmit is only meaningful
--                if vsmSigTmplCallerIdNumber is set to available.
--
--                For more information, please see the following CLI command:
--                 voice signaling template 'signalingTemplateName' caller id number 'callerIdNumber'
--                "
--           ::= { vsmSignalingTemplateEntry 7 }
--
--  vsmSigTmplToneTable OBJECT-TYPE
--                        SYNTAX INTEGER {
--                                ringing   (1),
--                                silence  (2)
--                                        }
--                        ACCESS read-write
--                        STATUS mandatory
--                        DESCRIPTION
--                        "
--                        This command is used to select the Tone Table for a TCID. Tone table
--                        to use. (In the future, this parameter will probably be changed to a
--                        VSx daughter card parameter.)
--
--                        Value Description
--                        ===== ===========
--                        ringing  Default.  Typically set for a normal ringback sound
--                        silence Typically set for a silent ringback.
--
--                        For more information, please see the following CLI command:
--                            voice signaling template 'signalingTemplateName' tone table ringing
--                            voice signaling template 'signalingTemplateName' tone table silence
--                        "
--                        DEFVAL { ringing }
--                        ::= { vsmSignalingTemplateEntry 8 }
--
--        vsmSigTmplOutDialType OBJECT-TYPE
--        SYNTAX INTEGER {
--                        tone (1),
--                        pulse (2)
--                        }
--        ACCESS read-write
--        STATUS mandatory
--        DESCRIPTION
--        "
--        This command is used to select the out dialing characteristic of the channels
--                on the specified port.
--
--        Value Description
--        ===== ===========
--        Tone  Default. Indicates use of tone (Dual Tone Multi-frequency) dialing.
--        Pulse Indicates use of pulse dialing.
--
--        For more information, please see the following CLI command:
--            voice signaling template 'signalingTemplateName' out dialing type tone
--            voice signaling template 'signalingTemplateName' out dialing type pulse
--        "
--        DEFVAL { tone }
--        ::= { vsmSignalingTemplateEntry 9 }
--
--
--   vsmSigTmplOutWait OBJECT-TYPE
--          SYNTAX INTEGER ( 0..20000 )
--          UNITS "milliseconds"
--          ACCESS read-write
--          STATUS mandatory
--          DESCRIPTION
--                 "The time to delay after going off-hook, before generating the
--                 first outbound dial digit(s).
--
--                 For more information, please see the following CLI command:
--                  voice signaling template 'signalingTemplateName' out wait (0..20000)
--                 "
--          DEFVAL { 400 }
--          ::= { vsmSignalingTemplateEntry 10 }
--
--   vsmSigTmplOutToneDigitDur OBJECT-TYPE
--          SYNTAX INTEGER (25..2000)
--          UNITS      "milliseconds"
--          ACCESS read-write
--          STATUS mandatory
--          DESCRIPTION
--                 "This is the duration, in milliseconds, of a tone that
--                  is generated when tone dialing is used.
--
--                  For more information, please see the following CLI command:
--                   voice signaling template 'signalingTemplateName' out tone digit duration (25..2000)
--                  "
--          DEFVAL { 200 }
--          ::= { vsmSignalingTemplateEntry 11 }
--
--   vsmSigTmplOutToneInterDigitDur OBJECT-TYPE
--          SYNTAX INTEGER (25..2000)
--          UNITS      "milliseconds"
--          ACCESS read-write
--          STATUS mandatory
--          DESCRIPTION
--                 "This is the duration, in milliseconds, of the inter digit
--                  gap when tone dialing is used.
--
--                  For more information, please see the following CLI command:
--                   voice signaling template 'signalingTemplateName' out tone interdigit duration (25..2000)
--                  "
--          DEFVAL { 200 }
--          ::= { vsmSignalingTemplateEntry 12 }
--
--   vsmSigTmplUnused OBJECT-TYPE
--          SYNTAX INTEGER (0..0)
--          ACCESS read-write
--          STATUS deprecated
--          DESCRIPTION
--                 "This object is no longer supported. Was vsmSigTmplOutToneAmplitude."
--          ::= { vsmSignalingTemplateEntry 13 }
--
--   vsmSigTmplCallLimitCtrl OBJECT-TYPE
--          SYNTAX VsmEnableDisabled
--          ACCESS read-write
--          STATUS mandatory
--          DESCRIPTION
--                 "Enables or Disables call timing limit duration
--                 (vsmSigTmplCallLimit).
--
--                 For more information, please see the following CLI command:
--                    voice signaling template 'signalingTemplateName' no call duration limit
--                 "
--          DEFVAL { disabled }
--          ::= { vsmSignalingTemplateEntry 14 }
--
--   vsmSigTmplCallLimit OBJECT-TYPE
--          SYNTAX INTEGER (0..65534)
--          UNITS      "seconds"
--          ACCESS read-write
--          STATUS mandatory
--          DESCRIPTION
--                 "The call duration limit. If the call length is exceeded,
--                 the call is automatically terminated.
--
--                 For more information, please see the following CLI command:
--                    voice signaling template 'signalingTemplateName' call duration limit (0..65534)
--                 "
--          DEFVAL { 65534 }
--          ::= { vsmSignalingTemplateEntry 15 }
--
--   vsmSigTmplAnswerWaitLimitCtrl OBJECT-TYPE
--          SYNTAX VsmEnableDisabled
--          ACCESS read-write
--          STATUS mandatory
--          DESCRIPTION
--                 "Enables or Disables call answer limit timing
--                 (vsmSigTmplAnswerWaitLimit).
--
--                 For more information, please see the following CLI command:
--                    voice signaling template 'signalingTemplateName' no answer wait limit
--                 "
--          DEFVAL { disabled }
--          ::= { vsmSignalingTemplateEntry 16 }
--
--        vsmSigTmplAnswerWaitLimit OBJECT-TYPE
--          SYNTAX INTEGER (0..65534)
--          UNITS      "seconds"
--          ACCESS read-write
--          STATUS mandatory
--          DESCRIPTION
--                 "The wait-for-answer time limit. If the call destination does not
--                 answer within this period, the call is automatically terminated.
--
--                 For more information, please see the following CLI command:
--                    voice signaling template 'signalingTemplateName' answer wait limit (0..65534)                 
--                 "
--          DEFVAL { 65534 }
--          ::= { vsmSignalingTemplateEntry 17 }
--
--   vsmSigTmplHangupWaitLimitCtrl OBJECT-TYPE
--          SYNTAX VsmEnableDisabled
--          ACCESS read-write
--          STATUS mandatory
--          DESCRIPTION
--                 "Enables or Disables call hangup limit timing
--                 (vsmSigTmplHangupWaitLimit).
--
--                 For more information, please see the following CLI command:
--                    voice signaling template 'signalingTemplateName' no hang up wait limit
--                 "
--          DEFVAL { disabled }
--          ::= { vsmSignalingTemplateEntry 18 }
--
--        vsmSigTmplHangupWaitLimit OBJECT-TYPE
--          SYNTAX INTEGER (0..65534)
--          UNITS      "seconds"
--          ACCESS read-write
--          STATUS mandatory
--          DESCRIPTION
--                 "The wait-for-hang-up time limit. If
--                 the call originator does not hang up within this time period
--                 after the destination has hung up, the call is automatically
--                 terminated.
--
--                 For more information, please see the following CLI command:
--                    voice signaling template 'signalingTemplateName' hang up wait limit (0..65534)
--                 "
--          DEFVAL { 65534 }
--          ::= { vsmSignalingTemplateEntry 19 }
--
--   vsmSigTmplFaxHoldoverDelay OBJECT-TYPE
--          SYNTAX INTEGER (0..65534)
--          UNITS      "milliseconds"
--          ACCESS read-write
--          STATUS mandatory
--          DESCRIPTION
--                 "The Fax holdover delay. This
--                 is the time the system will delay after detecting on-hook during
--                 fax mode operation, before generating a call clear.
--
--                 For more information, please see the following CLI command:
--                    voice signaling template 'signalingTemplateName' fax holdover (0..65534)
--                 "
--          DEFVAL { 2000 }
--          ::= { vsmSignalingTemplateEntry 20 }
--
--   vsmSigTmplCompanding OBJECT-TYPE
--          SYNTAX INTEGER {
--                                alaw            (1),
--                                mulaw           (2)
--                                }
--          ACCESS read-write
--          STATUS mandatory
--          DESCRIPTION
--                 "Select the companding used at the DSP's PCM interface.
--
--                 For more information, please see the following CLI command:
--                 voice signaling template 'signalingTemplateName' companding alaw
--                 voice signaling template 'signalingTemplateName' companding mulaw
--                 "
--          DEFVAL { mulaw }
--          ::= { vsmSignalingTemplateEntry 21 }
--
--   vsmSigTmplReceiveGain OBJECT-TYPE
--          SYNTAX INTEGER (-14..14)
--          UNITS      "dB"
--          ACCESS read-write
--          STATUS mandatory
--          DESCRIPTION
--                 "The Receive (Rx) Gain, in dB. The reference to Rx gain is from the
--                 perspective of the Micro software. The Micro interprets receive (Rx)
--                 gain as PCM interface-to-packet network.
--
--                 For more information, please see the following CLI command:
--                  voice signaling template 'signalingTemplateName' receive gain (-14...14)
--                 "
--          DEFVAL { 0 }
--          ::= { vsmSignalingTemplateEntry 22 }
--
--   vsmSigTmplTransmitGain OBJECT-TYPE
--          SYNTAX INTEGER (-14..14)
--          UNITS      "dB"
--          ACCESS read-write
--          STATUS mandatory
--          DESCRIPTION
--                 "The Transmit (Tx) Gain, in dB. The reference to Tx gain is from
--                 the perspective of the Micro software. The Micro interprets
--                 transmit (Tx) gain as packet network-to-PCM interface.
--
--                 For more information, please see the following CLI command:
--                  voice signaling template 'signalingTemplateName' transmit gain (-14...14)
--                 "
--          DEFVAL { 0 }
--          ::= { vsmSignalingTemplateEntry 23 }
--
--   vsmSigTmplIdleNoise OBJECT-TYPE
--          SYNTAX INTEGER (-7000..7000)
--          UNITS      ".01 dBm"
--          ACCESS read-write
--          STATUS mandatory
--          DESCRIPTION
--                 "The Idle Noise level (also known as comfort noise), in 0.01dBm.
--                 a value of -5000 means -50 dbm.
--
--                 For more information, please see the following CLI command:
--                  voice signaling template 'signalingTemplateName' idle noise (-7000..7000)
--                 "
--          DEFVAL { 7000 }
--          ::= { vsmSignalingTemplateEntry 24 }
--
--   vsmSigTmplOverrideInBandCallProgressTones OBJECT-TYPE
--          SYNTAX VsmEnableDisabled
--          ACCESS read-write
--          STATUS mandatory
--          DESCRIPTION
--                 "Enables or Disables support for passing call progress
--                 tones in band (ie, call progress tones are carried as voice)
--                 This object should only be used under the supervision of trained personnel.
--
--                 For more information, please see the following CLI command:
--                    voice signaling template 'signalingTemplateName' no override in band call progress tones
--                    voice signaling template 'signalingTemplateName' override in band call progress tones on
--                    voice signaling template 'signalingTemplateName' override in band call progress tones off
--                 "
--          DEFVAL { disabled }
--          ::= { vsmSignalingTemplateEntry 25 }
--
--   vsmSigTmplOverrideInBandCodecSwitching OBJECT-TYPE
--          SYNTAX VsmEnableDisabled
--          ACCESS read-write
--          STATUS mandatory
--          DESCRIPTION
--                 "Enables or Disables capability of the call to switch from one
--                 codec to another in band (in voice mode) by detecting change
--                 in payload type of the packets
--                 This object should only be used under the supervision of trained personnel.
--
--                 For more information, please see the following CLI command:
--                  voice signaling template 'signalingTemplateName' override in band codec switching on
--                  voice signaling template 'signalingTemplateName' override in band codec switching off
--                  voice signaling template 'signalingTemplateName' no override in band codec switching
--                 "
--          DEFVAL { disabled }
--          ::= { vsmSignalingTemplateEntry 26 }
--
--   vsmSigTmplOverridePSUCodecSwitching OBJECT-TYPE
--          SYNTAX VsmEnableDisabled
--          ACCESS read-write
--          STATUS mandatory
--          DESCRIPTION
--                 "Enables or Disables Coding switchover in the Signaling band. In
--                 the PSU this is accomplished by using the Set-Coding API. This
--                 happens after the Net-Connect stage.
--                 This object should only be used under the supervision of trained personnel.
--
--                 For more information, please see the following CLI command:
--                    voice signaling template 'signalingTemplateName' no override PSU codec switching
--                    voice signaling template 'signalingTemplateName' override PSU codec switching on
--                    voice signaling template 'signalingTemplateName' override PSU codec switching off
--                 "
--          DEFVAL { disabled }
--          ::= { vsmSignalingTemplateEntry 27 }
--
--   vsmSigTmplOverrideNetworkOverlapDialing OBJECT-TYPE
--          SYNTAX VsmEnableDisabled
--          ACCESS read-write
--          STATUS mandatory
--          DESCRIPTION
--                 "Enables or Disables support for Network overlap dialing. The
--                 Net connect happens even if all the digits have not been collected.
--                 The call moves to Call progress when the dialing is completed.
--                 This object should only be used under the supervision of trained personnel.
--
--                 For more information, please see the following CLI command:
--                    voice signaling template 'signalingTemplateName' no override network overlap dialing
--                    voice signaling template 'signalingTemplateName' override network overlap dialing on
--                    voice signaling template 'signalingTemplateName' override network overlap dialing off
--                 "
--          DEFVAL { disabled }
--          ::= { vsmSignalingTemplateEntry 28 }
--
--   vsmSigTmplOverrideFullCallProgressTones OBJECT-TYPE
--          SYNTAX VsmEnableDisabled
--          ACCESS read-write
--          STATUS mandatory
--          DESCRIPTION
--                 "Enables or Disables support for full call progress tones in
--                 signaling band. Call progress indications are sent as information
--                 type packets. The call progress tones include Ringback, Busy etc.
--                 This object should only be used under the supervision of trained personnel.
--
--                 For more information, please see the following CLI command:
--                  voice signaling template 'signalingTemplateName' override full call progress tones on
--                  voice signaling template 'signalingTemplateName' override full call progress tones off
--                  voice signaling template 'signalingTemplateName' no override full call progress tones
--                 "
--          DEFVAL { disabled }
--          ::= { vsmSignalingTemplateEntry 29 }
--
--   vsmSigTmplOverrideRingBack OBJECT-TYPE
--          SYNTAX VsmEnableDisabled
--          ACCESS read-write
--          STATUS mandatory
--          DESCRIPTION
--                 "Enables or Disables ring back detection.
--                 This object should only be used under the supervision of trained personnel.
--
--                 For more information, please see the following CLI command:
--                  voice signaling template 'signalingTemplateName' override ring back on
--                  voice signaling template 'signalingTemplateName' override ring back off
--                  voice signaling template 'signalingTemplateName' no override ring back
--                 "
--          DEFVAL { disabled }
--          ::= { vsmSignalingTemplateEntry 30 }
--
--   vsmSigTmplOverrideInfoElementTransport OBJECT-TYPE
--          SYNTAX VsmEnableDisabled
--          ACCESS read-write
--          STATUS mandatory
--          DESCRIPTION
--                 "Enables or Disables general user to user Information Element  (IE)
--                 packet passing support.  This means that the call is capable of
--                 transporting IEs from user to user.
--                 This object should only be used under the supervision of trained personnel.
--
--                 For more information, please see the following CLI command:
--                 voice signaling template 'signalingTemplateName' override information element transport on
--                 voice signaling template 'signalingTemplateName' override information element transport off
--                 voice signaling template 'signalingTemplateName' no override information element transport
--                 "
--          DEFVAL { disabled }
--          ::= { vsmSignalingTemplateEntry 31 }
--
--   vsmSigTmplOverrideQSIGInfoElementTransport OBJECT-TYPE
--          SYNTAX VsmEnableDisabled
--          ACCESS read-write
--          STATUS mandatory
--          DESCRIPTION
--                 "Enables or Disables QSIG Information Element  (IE)
--                 packet passing support.
--                 This object should only be used under the supervision of trained personnel.
--
--                 For more information, please see the following CLI command:
--                 voice signaling template 'signalingTemplateName' override QSIG information element transport on
--                 voice signaling template 'signalingTemplateName' override QSIG information element transport off
--                 voice signaling template 'signalingTemplateName' no override QSIG information element transport
--                 "
--          DEFVAL { disabled }
--          ::= { vsmSignalingTemplateEntry 32 }
--
--   vsmSigTmplOverrideDataSetup OBJECT-TYPE
--          SYNTAX VsmOnOff
--          ACCESS read-write
--          STATUS mandatory
--          DESCRIPTION
--                 "Enables or Disables identification that this is a data call.
--                 One of the following objects must be on, vsmSigTmplDataSetup,
--                 vsmSigTmplVoiceSetup, vsmSigTmplFAXSetup, or
--                 vsmSigTmplModemSetup.
--                 This object should only be used under the supervision of trained personnel.
--
--                 For more information, please see the following CLI command:
--                 voice signaling template 'signalingTemplateName' override data setup on
--                 voice signaling template 'signalingTemplateName' override data setup off
--                 voice signaling template 'signalingTemplateName' no override data setup
--                 "
--          DEFVAL { off }
--          ::= { vsmSignalingTemplateEntry 33 }
--
--   vsmSigTmplOverrideVoiceSetup OBJECT-TYPE
--          SYNTAX VsmOnOff
--          ACCESS read-write
--          STATUS mandatory
--          DESCRIPTION
--                 "Enables or Disables identification that this is a voice call.
--                 One of the following objects must be on, vsmSigTmplDataSetup,
--                 vsmSigTmplVoiceSetup, vsmSigTmplFAXSetup, or
--                 vsmSigTmplModemSetup.
--                 This object should only be used under the supervision of trained personnel.
--
--                 For more information, please see the following CLI command:
--                 voice signaling template 'signalingTemplateName' override      voice setup on
--                 voice signaling template 'signalingTemplateName' override      voice setup off
--                 voice signaling template 'signalingTemplateName' no override voice setup
--                 "
--          DEFVAL { off }
--          ::= { vsmSignalingTemplateEntry 34 }
--
--   vsmSigTmplOverrideFAXSetup OBJECT-TYPE
--          SYNTAX VsmOnOff
--          ACCESS read-write
--          STATUS mandatory
--          DESCRIPTION
--                 "Enables or Disables identification that this is a FAX call.
--                 One of the following objects must be on, vsmSigTmplDataSetup,
--                 vsmSigTmplVoiceSetup, vsmSigTmplFAXSetup, or
--                 vsmSigTmplModemSetup.
--                 This object should only be used under the supervision of trained personnel.
--
--                 For more information, please see the following CLI command:
--                 voice signaling template 'signalingTemplateName' override fax setup on
--                 voice signaling template 'signalingTemplateName' override fax setup off
--                 voice signaling template 'signalingTemplateName' no override fax setup
--                 "
--          DEFVAL { off }
--          ::= { vsmSignalingTemplateEntry 35 }
--
--   vsmSigTmplOverrideModemSetup OBJECT-TYPE
--          SYNTAX VsmOnOff
--          ACCESS read-write
--          STATUS mandatory
--          DESCRIPTION
--                 "Enables or Disables identification that this is a modem call.
--                 One of the following objects must be on, vsmSigTmplDataSetup,
--                 vsmSigTmplVoiceSetup, vsmSigTmplFAXSetup, or
--                 vsmSigTmplModemSetup.
--                 This object should only be used under the supervision of trained personnel.
--
--                 For more information, please see the following CLI command:
--                 voice signaling template 'signalingTemplateName' override modem setup on
--                 voice signaling template 'signalingTemplateName' override modem setup off
--                 voice signaling template 'signalingTemplateName' no override modem setup
--                 "
--          DEFVAL { off }
--          ::= { vsmSignalingTemplateEntry 36 }
--
--        vsmSigTmplCallProgressToneDetControl OBJECT-TYPE
--        SYNTAX INTEGER {
--                        off (1),
--                        on (2),
--                        relative (3)
--                        }
--        ACCESS read-write
--        STATUS mandatory
--        DESCRIPTION
--            "This command is used to control the detection of call progress tones.
--            
--            Value       Description 
--            =====      =========== 
--            off        Disable call progress detection.
--            on         Enable call progress detection.
--            relative   Enable/disable call progress detection according to the Call
--                         progress tone detection parameter in the coding profile that
--                         is currently loaded.       
--
--             For more information, please see the following CLI command:
--                voice signaling template 'signalingTemplateName' call progress tone detection control off
--                voice signaling template 'signalingTemplateName' call progress tone detection control on
--                voice signaling template 'signalingTemplateName' call progress tone detection control relative
--        "
--        DEFVAL { off }
--        ::= { vsmSignalingTemplateEntry 37 }
--
--   vsmSigTmplCallProgressToneDetCfg OBJECT-TYPE
--          SYNTAX INTEGER {
--                                default                 (1),
--                                alternate               (2)
--                                }
--          ACCESS read-write
--          STATUS mandatory
--          DESCRIPTION
--                 "This command is used to specify which configuration will be
--                 used for call progress tone detection.  Each  configuration
--                 contains filter configuration information (threshold and filter
--                 coefficients), and a table containing cadence information of all
--                 the call progress tones that are to be detected.       Two
--                 configurations are provided at this time – default and alternate.
--
--                 Both  default and alternate have a      filter configuration for
--                 dial tone, ring back (3 different cadences are supported), bust,
--                 and congestion.
--
--                 If alternate is selected, tone detection processing will be
--                 limited to busy tone only. However other tones will be detected
--                 and ignored.
--
--                 For more information, please see the following CLI command:
--                    voice signaling template 'signalingTemplateName' call progress tone detection configuration default
--                    voice signaling template 'signalingTemplateName' call progress tone detection configuration alternate
--                 "
--          DEFVAL { default }
--          ::= { vsmSignalingTemplateEntry 38 }
--
--  vsmSigTmplAcousticEchoCanOper OBJECT-TYPE
--          SYNTAX INTEGER {
--                                handset                 (1),
--                                handsfree               (2)
--                                }
--          ACCESS read-write
--          STATUS mandatory
--          DESCRIPTION
--                 "new leaf for 2.2f parser
--
--                 For more information, please see the following CLI command:
--                  voice signaling template 'signalingTemplateName' acoustic echo canceller operation handset
--                  voice signaling template 'signalingTemplateName' acoustic echo canceller operation hands free
--                 "
--          DEFVAL { handsfree }
--          ::= { vsmSignalingTemplateEntry 39 }
--
--    vsmSigTmplV18ToneDetThHangTime OBJECT-TYPE
--        SYNTAX INTEGER (5..32767)
--        ACCESS read-write
--        STATUS mandatory
--        DESCRIPTION
--        "
--        This command sets the signal duration threshold for V18 tone detection.
--
--        For more information, please see the following CLI command:
--            voice signaling template 'signalingTemplateName' v.18 tone detection threshold hang time (5 ... 32767)
--        "
--        DEFVAL { 50 }
--        ::= { vsmSignalingTemplateEntry 40 }
--
--    vsmSigTmplV18ToneDetThLevel OBJECT-TYPE
--        SYNTAX INTEGER (-50..-15)
--        ACCESS read-write
--        STATUS mandatory
--        DESCRIPTION
--        "
--        This command sets the signal strength threshold for V18 tone detection.
--
--        For more information, please see the following CLI command:
--            voice signaling template 'signalingTemplateName' v.18 tone detection threshold Level (-50 ... -15)
--        "
--        DEFVAL { -40 }
--        ::= { vsmSignalingTemplateEntry 41 }
--
--    vsmSigTmplV18ToneDetThFraction OBJECT-TYPE
--        SYNTAX INTEGER (1..32767)
--        ACCESS read-write
--        STATUS mandatory
--        DESCRIPTION
--        "
--        This command sets the signal fraction threshold for V18 tone detection.
--
--        For more information, please see the following CLI command:
--            voice signaling template 'signalingTemplateName' v.18 tone detection threshold fraction (1 ... 32767)
--        "
--        DEFVAL { 10 }
--        ::= { vsmSignalingTemplateEntry 42 }
--
--    vsmSigTmplSinFreqToneDetThLev OBJECT-TYPE
--        SYNTAX INTEGER (-50..-15)
--        ACCESS read-write
--        STATUS mandatory
--        DESCRIPTION
--        "
--        This command sets the signal strength threshold for SF {single frequency } tone detection.
--
--        For more information, please see the following CLI command:
--            voice signaling template 'signalingTemplateName' single frequency tone detection threshold level (-50 ... -15)
--        "
--        DEFVAL {  -40 }
--        ::= { vsmSignalingTemplateEntry 43 }
--
--    vsmSigTmplSinFreqToneDetThTime OBJECT-TYPE
--        SYNTAX INTEGER (0..65535)
--        ACCESS read-write
--        STATUS mandatory
--        DESCRIPTION
--        "
--        This command sets the time threshold level for SF {single frequency } tone detection.
--
--        For more information, please see the following CLI command:
--            voice signaling template 'signalingTemplateName' single frequency tone detection threshold time (0 ... 65535)
--        "
--        DEFVAL { 50 }
--        ::= { vsmSignalingTemplateEntry 44 }
--
--    vsmSigTmplEchoCancelNonSens OBJECT-TYPE
--        SYNTAX INTEGER (0..32767)
--        ACCESS read-write
--        STATUS mandatory
--        DESCRIPTION
--        "
--        This command sets the sensitivity of the echo canceller non-linear processor.
--
--        For more information, please see the following CLI command:
--            voice signaling template 'signalingTemplateName' echo canceller non-linear sensitivity (0 ... 32767)
--        "
--        DEFVAL { 327 }
--        ::= { vsmSignalingTemplateEntry 45 }
--
--    vsmSigTmplAcousticEchoCancellerMode OBJECT-TYPE
--        SYNTAX VsmEnableDisabled
--        ACCESS read-write
--        STATUS mandatory
--        DESCRIPTION
--        "
--        This command selects whether the line of the Acoustic Echo Canceller (EC) is started on channel startup.
--
--        For more information, please see the following CLI command:
--            voice signaling template 'signalingTemplateName' acoustic echo canceller mode on
--            voice signaling template 'signalingTemplateName' acoustic echo canceller mode off
--        "
--        DEFVAL { disabled }
--        ::= { vsmSignalingTemplateEntry 46 }
--
--   vsmSigTmplAcouEchoCanNonProc OBJECT-TYPE
--        SYNTAX VsmEnableDisabled
--        ACCESS read-write
--        STATUS mandatory
--        DESCRIPTION
--        "
--        This command enables or disables the (TBD: acoustic echo canceller non-linear processor or
--                comfort noise level generator)
--
--        For more information, please see the following CLI command:
--            voice signaling template 'signalingTemplateName' acoustic echo canceller non-linear processor on
--            voice signaling template 'signalingTemplateName' acoustic echo canceller non-linear processor off
--        "
--        DEFVAL { disabled }
--        ::= { vsmSignalingTemplateEntry 47 }
--
--    vsmSigTmplAcEchoCanSetSpGain OBJECT-TYPE
--        SYNTAX INTEGER (0..31)
--        ACCESS read-write
--        STATUS mandatory
--        DESCRIPTION
--        "
--        This command sets the Handset (HS) specker gain.
--
--        For more information, please see the following CLI command:
--            voice signaling template 'signalingTemplateName' acoustic echo canceller handset speaker gain (0 ... 31)
--        "
--        DEFVAL {10}
--        ::= { vsmSignalingTemplateEntry 48 }
--
--    vsmSigTmplAcEchoCanFreeSpGain OBJECT-TYPE
--        SYNTAX INTEGER (0..31)
--        ACCESS read-write
--        STATUS mandatory
--        DESCRIPTION
--        "
--        This command sets the Hands Free (HF) specker gain.
--
--        For more information, please see the following CLI command:
--            voice signaling template 'signalingTemplateName' acoustic echo canceller hands free speaker gain (0 ... 31)
--        "
--        DEFVAL { 0 }
--        ::= { vsmSignalingTemplateEntry 49 }
--
--
--  vsmSigTmplFxsLSCadenceCoefficient OBJECT-TYPE
--          SYNTAX INTEGER {
--                                northAmerica           (1),
--                                europe                         (2)
--                         }
--          ACCESS read-write
--          STATUS mandatory
--          DESCRIPTION
--                 "This command selects the fxs cadence coefficient on this channel.
--
--                 For more information, please see the following CLI command:
--                  voice signaling template 'signalingTemplateName' fxs ls cadence coefficient North America
--                  voice signaling template 'signalingTemplateName' fxs ls cadence coefficient Europe
--                 "
--          DEFVAL { northAmerica }
--          ::= { vsmSignalingTemplateEntry 50 }
--
--
--  vsmSigTmplFxsLSRingId OBJECT-TYPE
--          SYNTAX INTEGER {
--                                default         (1),
--                                zero            (2),
--                                                                one                     (3),
--                                                                two                     (4),
--                                                                three           (5),
--                                                                four            (6),
--                                                                five            (7),
--                                                                six                     (8),
--                                                                seven           (9)
--                         }
--          ACCESS read-write
--          STATUS mandatory
--          DESCRIPTION
--                 "This command selects the ring id for the specific fxs cadence 
--                                 coefficient on this channel.
--
--                 For more information, please see the following CLI command:
--                  voice signaling template 'signalingTemplateName' fxs ls ring id default
--                  voice signaling template 'signalingTemplateName' fxs ls ring id zero
--                                  voice signaling template 'signalingTemplateName' fxs ls ring id one
--                                  voice signaling template 'signalingTemplateName' fxs ls ring id two
--                                  voice signaling template 'signalingTemplateName' fxs ls ring id three
--                                  voice signaling template 'signalingTemplateName' fxs ls ring id four
--                                  voice signaling template 'signalingTemplateName' fxs ls ring id five
--                                  voice signaling template 'signalingTemplateName' fxs ls ring id six
--                                  voice signaling template 'signalingTemplateName' fxs ls ring id seven
--                 "
--          DEFVAL { default }
--          ::= { vsmSignalingTemplateEntry 51 }
--
--
--  vsmSigTmplFxsGSCadenceCoefficient OBJECT-TYPE
--          SYNTAX INTEGER {
--                                northAmerica           (1),
--                                europe                         (2)
--                         }
--          ACCESS read-write
--          STATUS mandatory
--          DESCRIPTION
--                 "This command selects the fxs cadence coefficient on this channel.
--
--                 For more information, please see the following CLI command:
--                  voice signaling template 'signalingTemplateName' fxs gs cadence coefficient North America
--                  voice signaling template 'signalingTemplateName' fxs gs cadence coefficient Europe
--                 "
--          DEFVAL { northAmerica }
--          ::= { vsmSignalingTemplateEntry 52 }
--
--
--  vsmSigTmplFxsGSRingId OBJECT-TYPE
--          SYNTAX INTEGER {
--                                default         (1),
--                                zero            (2),
--                                                                one                     (3),
--                                                                two                     (4),
--                                                                three           (5),
--                                                                four            (6),
--                                                                five            (7),
--                                                                six                     (8),
--                                                                seven           (9)
--                         }
--          ACCESS read-write
--          STATUS mandatory
--          DESCRIPTION
--                 "This command selects the ring id for the specific fxs cadence 
--                                 coefficient on this channel.
--
--                 For more information, please see the following CLI command:
--                  voice signaling template 'signalingTemplateName' fxs gs ring id default
--                  voice signaling template 'signalingTemplateName' fxs gs ring id zero
--                                  voice signaling template 'signalingTemplateName' fxs gs ring id one
--                                  voice signaling template 'signalingTemplateName' fxs gs ring id two
--                                  voice signaling template 'signalingTemplateName' fxs gs ring id three
--                                  voice signaling template 'signalingTemplateName' fxs gs ring id four
--                                  voice signaling template 'signalingTemplateName' fxs gs ring id five
--                                  voice signaling template 'signalingTemplateName' fxs gs ring id six
--                                  voice signaling template 'signalingTemplateName' fxs gs ring id seven
--                 "
--          DEFVAL { default }
--          ::= { vsmSignalingTemplateEntry 53 }
--

  vsmSigTmplRowStatus OBJECT-TYPE
          SYNTAX RowStatus
          ACCESS read-write
          STATUS mandatory
          DESCRIPTION
                 "This object is the RowStatus (locking flag) for creating the
           vsm Signaling Template Table conceptual row.  This table is not supported.
--                 CreateAndWait is
--           not supported with this table.  In order to do a createAndGo,
--           the required fields to create a row must be passed in the PDU.

--           For more information, please see the following CLI command:
--              voice no signaling template 'signalingTemplateName'
           "
          ::= { vsmSignalingTemplateEntry 3 }





--======================================================================
--
-- E&M Common Signaling Template Table
--
-- This table provides information that is used for all types of E&M
-- signaling.
--
--======================================================================

   vsmSigTmplEmCommonTable OBJECT-TYPE
          SYNTAX SEQUENCE OF VsmSigTmplEmCommonEntry
          ACCESS not-accessible
          STATUS mandatory
          DESCRIPTION
                  "This table contains information that is used for all
                   E&M type signaling protocols. This table is not supported.
                    "

          ::= { vsmSignalingGroup 2 }

   vsmSigTmplEmCommonEntry OBJECT-TYPE
           SYNTAX VsmSigTmplEmCommonEntry
           ACCESS not-accessible
           STATUS mandatory
           DESCRIPTION
                 "This is an entry in the E&M Common Signaling Table. This is not supported.

                  For more information, please see the following CLI command:
                    [Note: There is NO equivalent command in the CLI.]
                  "
           INDEX { vsmSigTmplIndex }
           ::= { vsmSigTmplEmCommonTable 1 }

   VsmSigTmplEmCommonEntry ::=
          SEQUENCE {
                   vsmSigTmplEmCommonOffHookDebounce               INTEGER
--                                 ,
--                  vsmSigTmplEmCommonOnHookDebounce                INTEGER,
--                  vsmSigTmplEmCommonSeizeDetect                   INTEGER,
--                  vsmSigTmplEmCommonClearDetect                   INTEGER,
--                  vsmSigTmplEmCommonClearConfDetect               INTEGER,
--                  vsmSigTmplEmCommonClearConfWaitMax              INTEGER,
--                  vsmSigTmplEmCommonGuardAll                      INTEGER,
--                  vsmSigTmplEmCommonGuardOut                      INTEGER,
--                  vsmSigTmplEmCommonDialTone                      VsmEnableDisabled,
--                  vsmSigTmplEmCommonMinConnectTime                INTEGER,
--                  vsmSigTmplEmCommonHangUpWait                    INTEGER
          }

     vsmSigTmplEmCommonOffHookDebounce OBJECT-TYPE
        SYNTAX INTEGER (5..1000)
--        UNITS "milliseconds"
        ACCESS read-write
        STATUS deprecated
        DESCRIPTION
               "The time, in milliseconds, to allow to de-bounce
                a transition to an offhook state. This is not supported

--                For more information, please see the following CLI command:
--                 voice signaling template 'signalingTemplateName' em off hook debounce (5..1000)
                "
        DEFVAL { 50 }
        ::= { vsmSigTmplEmCommonEntry 1 }
--                
-- ======================================================================
-- This Section is not supported
-- ======================================================================
--
--  vsmSigTmplEmCommonOnHookDebounce OBJECT-TYPE
--         SYNTAX INTEGER (5..1000)
--         UNITS "milliseconds"
--         ACCESS read-write
--         STATUS mandatory
--         DESCRIPTION
--                "The time, in milliseconds, to allow to de-bounce
--                 a transition to an onhook state.
--
--                 For more information, please see the following CLI command:
--                  voice signaling template 'signalingTemplateName' em on hook debounce (5..1000)
--
--                 "
--         DEFVAL { 50 }
--         ::= { vsmSigTmplEmCommonEntry 2 }
--
--  vsmSigTmplEmCommonSeizeDetect OBJECT-TYPE
--         SYNTAX INTEGER (5..5000)
--         UNITS "milliseconds"
--         ACCESS read-write
--         STATUS mandatory
--         DESCRIPTION
--                "The time to wait, in milliseconds, before
--                 declaring an off-hook condition after the M-lead has
--                 transitioned to the active state.
--
--                 For more information, please see the following CLI command:
--                   voice signaling template 'signalingTemplateName' em seize detect (5..5000)
--                 "
--         DEFVAL { 150 }
--         ::= { vsmSigTmplEmCommonEntry 3 }
--
--  vsmSigTmplEmCommonClearDetect OBJECT-TYPE
--         SYNTAX INTEGER (5..5000)
--         UNITS "milliseconds"
--         ACCESS read-write
--         STATUS mandatory
--         DESCRIPTION
--                "The minimum time to wait, in milliseconds,
--                 before declaring an on-hook condition after the M-lead
--                 transitions to the inactive state and the interface was
--                 off-hook.
--
--                 For more information, please see the following CLI command:
--                                  voice signaling template 'signalingTemplateName' em clear detect (5..5000)
--
--                 "
--          DEFVAL { 400 }
--         ::= { vsmSigTmplEmCommonEntry 4 }
--
--  vsmSigTmplEmCommonClearConfDetect OBJECT-TYPE
--         SYNTAX INTEGER (5..5000)
--         UNITS "milliseconds"
--         ACCESS read-write
--         STATUS mandatory
--         DESCRIPTION
--                "The amount of time, in milliseconds, that an
--                 on-hook must be detected on the M-lead after going on-hook
--                 on the E-lead.
--
--                 For more information, please see the following CLI command:
--                  voice signaling template 'signalingTemplateName' em clear confirm detect (5..5000)
--                 "
--         DEFVAL { 5000 }
--         ::= { vsmSigTmplEmCommonEntry 5 }
--
--  vsmSigTmplEmCommonClearConfWaitMax OBJECT-TYPE
--         SYNTAX INTEGER (1..60000)
--         UNITS "seconds "
--         ACCESS read-write
--         STATUS mandatory
--         DESCRIPTION
--                 "Defines the maximum time, in seconds, to wait
--                  for an on-hook indication following a clearing indication.
--
--                  For more information, please see the following CLI command:
--                   voice signaling template 'signalingTemplateName' em clear confirm wait maximum (1..60000)
--                  "
--          DEFVAL { 60000 }
--         ::= { vsmSigTmplEmCommonEntry 6 }
--
--  vsmSigTmplEmCommonGuardAll OBJECT-TYPE
--         SYNTAX INTEGER (0..60000)
--         UNITS "milliseconds"
--         ACCESS read-write
--         STATUS mandatory
--         DESCRIPTION
--                "The period, in milliseconds, after an aborted
--                call when neither no incoming calls will be accepted nor outgoing
--                calls initiated. In other words, this is the duration of time that
--                the channel is out of service after a call is aborted.
--
--                For more information, please see the following CLI command:
--                 voice signaling template 'signalingTemplateName' em guard all (0..60000)
--                "
--         DEFVAL { 400 }
--         ::= { vsmSigTmplEmCommonEntry 7 }
--
--  vsmSigTmplEmCommonGuardOut OBJECT-TYPE
--         SYNTAX INTEGER (5..60000)
--         UNITS "milliseconds"
--         ACCESS read-write
--         STATUS mandatory
--         DESCRIPTION
--           "This specifies an additional period of time, in milliseconds, after
--           guard-all when incoming calls will be accepted but outgoing calls
--           will not be initiated for aborted calls.
--
--           For more information, please see the following CLI command:
--            voice signaling template 'signalingTemplateName' em guard out (0..60000)
--           "
--         DEFVAL { 400 }
--         ::= { vsmSigTmplEmCommonEntry 8 }
--
--vsmSigTmplEmCommonDialTone OBJECT-TYPE
--         SYNTAX VsmEnableDisabled
--         ACCESS read-write
--         STATUS mandatory
--         DESCRIPTION
--           "Specifies whether dial tone should be generated on
--           incoming calls.
--
--           For more information, please see the following CLI command:
--            voice signaling template 'signalingTemplateName' em dial tone on
--            voice signaling template 'signalingTemplateName' em dial tone off
--           "
--         DEFVAL { enabled }
--         ::= { vsmSigTmplEmCommonEntry 9 }
--
--vsmSigTmplEmCommonMinConnectTime OBJECT-TYPE
--         SYNTAX INTEGER (0..20000)
--         UNITS "milliseconds"
--         ACCESS read-write
--         STATUS mandatory
--         DESCRIPTION
--           "The minimum period of time, in milliseconds, that
--           a connection will be maintained. If the remote end disconnects during
--           this interval, the disconnect will be acknowledged only at the end of
--           this time interval.
--
--           For more information, please see the following CLI command:
--            voice signaling template 'signalingTemplateName' em minimum connect time (0..20000)
--           "
--         DEFVAL { 2000 }
--         ::= { vsmSigTmplEmCommonEntry 10 }
--
--vsmSigTmplEmCommonHangUpWait OBJECT-TYPE
--         SYNTAX INTEGER (5..60000)
--         UNITS "milliseconds"
--         ACCESS read-write
--         STATUS mandatory
--         DESCRIPTION
--           "The time period, in milliseconds, a port will wait
--           after hanging up a call before signaling that it is in a disabled
--           state.

--           For more information, please see the following CLI command:
--            voice signaling template 'signalingTemplateName' em hang up wait (5..60000)
--           "
--         DEFVAL { 2000 }
--         ::= { vsmSigTmplEmCommonEntry 11 }


--====================================================================
--
-- E&M Delayed Start Signaling Template Table
--
-- This table provides information for control of E&M delay start
-- signaling.
--
--======================================================================

  vsmSigTmplEmDelayTable OBJECT-TYPE
          SYNTAX SEQUENCE OF VsmSigTmplEmDelayEntry
          ACCESS not-accessible
          STATUS mandatory
          DESCRIPTION
                 "This table contains entries that specify how to perform
                  E&M Delay signaling on the port indicated. This is not supported"
          ::= { vsmSignalingGroup 3 }

  vsmSigTmplEmDelayEntry OBJECT-TYPE
           SYNTAX VsmSigTmplEmDelayEntry
           ACCESS not-accessible
           STATUS mandatory
           DESCRIPTION
                 "This is an entry in the E&M Delay Signaling Table. This is not supported.

--                  For more information, please see the following CLI command:
--                    [Note: There is NO equivalent command in the CLI.]
                 "
           INDEX { vsmSigTmplIndex }
           ::= { vsmSigTmplEmDelayTable 1 }

  VsmSigTmplEmDelayEntry ::=
          SEQUENCE {
                  vsmSigTmplEmDelayInDelayDurMin                 INTEGER
--                  ,
--                  vsmSigTmplEmDelayInDelayDurMax                 INTEGER,
--                  vsmSigTmplEmDelayInDigitIgnore                 INTEGER,
--                  vsmSigTmplEmDelayOutDelayDurMin                INTEGER,
--                  vsmSigTmplEmDelayOutDelayDurMax                INTEGER,
--                  vsmSigTmplEmDelayOutIntegrityChk               VsmEnableDisabled,
--                  vsmSigTmplEmDelayOutDelayChk                   INTEGER
          }


   vsmSigTmplEmDelayInDelayDurMin OBJECT-TYPE
          SYNTAX INTEGER (5..60000)
          ACCESS read-write
          STATUS deprecated
          DESCRIPTION
                "The minimum duration, in milliseconds,
                of the delay signal response to the seize detect (of incoming calls)
                on the M-lead. This is not supported.

--                For more information, please see the following CLI command:
--                 voice signaling template 'signalingTemplateName' emd in delay minimum (5..60000)
                 "
          DEFVAL { 200 }
          ::= { vsmSigTmplEmDelayEntry 1 }
--                
-- ======================================================================
-- This Section is not supported
-- ======================================================================
--
--   vsmSigTmplEmDelayInDelayDurMax OBJECT-TYPE
--          SYNTAX INTEGER (5..60000)
--          ACCESS read-write
--          STATUS mandatory
--          DESCRIPTION
--                "The maximum duration, in milliseconds, of the delay
--                signal response to the Seize Detect (of incoming calls) on the
--                M-lead.
--
--                For more information, please see the following CLI command:
--                 voice signaling template 'signalingTemplateName' emd in delay maximum (5..60000)
--                "
--          DEFVAL { 2500 }
--          ::= { vsmSigTmplEmDelayEntry 2 }
--
--   vsmSigTmplEmDelayInDigitIgnore OBJECT-TYPE
--          SYNTAX INTEGER (5..60000)
--          ACCESS read-write
--          STATUS mandatory
--          DESCRIPTION
--                "The period of time in milliseconds, after completing
--                the delay signal, before the digits will be accepted on incoming
--                calls.
--
--                For more information, please see the following CLI command:
--                 voice signaling template 'signalingTemplateName' emd in digit ignore (5..60000)
--                "
--          DEFVAL { 30 }
--          ::= { vsmSigTmplEmDelayEntry 3 }
--
--   vsmSigTmplEmDelayOutDelayDurMin OBJECT-TYPE
--          SYNTAX INTEGER (5..60000)
--          ACCESS read-write
--          STATUS mandatory
--          DESCRIPTION
--                "The minimum duration, in milliseconds, of the delay
--                signal response on the M-lead for it to be detected on outgoing
--                calls.
--
--                For more information, please see the following CLI command:
--                 voice signaling template 'signalingTemplateName' emd out delay duration minimum (5..60000)
--                "
--          DEFVAL { 100 }
--          ::= { vsmSigTmplEmDelayEntry 4 }
--
--   vsmSigTmplEmDelayOutDelayDurMax OBJECT-TYPE
--          SYNTAX INTEGER (5..60000)
--          ACCESS read-write
--          STATUS mandatory
--          DESCRIPTION
--                "The maximum duration, in milliseconds, of the delay
--                signal response on the M-lead for it to be declared as a glare
--                condition by the TSG on outgoing calls.
--
--                For more information, please see the following CLI command:
--                 voice signaling template 'signalingTemplateName' emd out delay duration maximum (5..60000)
--                "
--          DEFVAL { 8000 }
--          ::= { vsmSigTmplEmDelayEntry 5 }
--
--   vsmSigTmplEmDelayOutIntegrityChk OBJECT-TYPE
--          SYNTAX VsmEnableDisabled
--          ACCESS read-write
--          STATUS mandatory
--          DESCRIPTION
--                 "Enables or disables the Integrity Check mode.
--                 If on, the delay signal response is required from the PBX
--                 for outgoing calls. If off, no Integrity check is performed.
--
--                 For more information, please see the following CLI command:
--                  voice signaling template 'signalingTemplateName' emd out integrity check on
--                  voice signaling template 'signalingTemplateName' emd out integrity check off
--                  "
--          DEFVAL { disabled }
--          ::= { vsmSigTmplEmDelayEntry 6 }
--
--   vsmSigTmplEmDelayOutDelayChk OBJECT-TYPE
--          SYNTAX INTEGER (5..60000)
--          ACCESS read-write
--          STATUS mandatory
--          DESCRIPTION
--                "The wait period for outgoing calls with the
--                Integrity Check set to off; the period of time, in milliseconds,
--                after going off-hook on the E-lead before checking the M-lead for
--                the delay signal response. If the response is not seen at this time,
--                the call setup process will continue immediately.
--
--                For more information, please see the following CLI command:
--                 voice signaling template 'signalingTemplateName' emd out delay check (5..60000)
--                "
--          DEFVAL { 170 }
--          ::= { vsmSigTmplEmDelayEntry 7 }

--===================================================================
--
-- E&M Immediate Start Signaling Template Table
--
-- This table provides information for control of E&M immediate start
-- signaling.
--
--=======================================================================

   vsmSigTmplEmImmedTable OBJECT-TYPE
          SYNTAX SEQUENCE OF VsmSigTmplEmImmedEntry
          ACCESS not-accessible
          STATUS mandatory
          DESCRIPTION
                 "This table contains entries that specify how to perform
                  E&M Immediate signaling on the telephone channel. This is not supported.
                   "
          ::= { vsmSignalingGroup 4 }

   vsmSigTmplEmImmedEntry OBJECT-TYPE
           SYNTAX VsmSigTmplEmImmedEntry
           ACCESS not-accessible
           STATUS mandatory
           DESCRIPTION
                 "This is an entry in the E&M Immediate Signaling Table.
                                 This table is not supported.

--                  For more information, please see the following CLI command:
--                   [Note: There is NO equivalent command in the CLI.]
                  "
           INDEX { vsmSigTmplIndex }
           ::= { vsmSigTmplEmImmedTable 1 }

   VsmSigTmplEmImmedEntry ::=
          SEQUENCE {
                  vsmSigTmplEmImmedGlareReport   INTEGER
--                                ,
--                  vsmSigTmplEmImmedDigitWait     INTEGER
          }


   vsmSigTmplEmImmedGlareReport OBJECT-TYPE
          SYNTAX INTEGER (0..60000)
--          UNITS "milliseconds"
          ACCESS read-write
          STATUS deprecated
          DESCRIPTION
                "Specifies, how long, in milliseconds, the interface should remain
                 off hook after detecting a glare condition to indicate congestion.
                                 This is not supported.

--                 For more information, please see the following CLI command:
--                  voice signaling template 'signalingTemplateName' emi glare report (0..60000)
                 "
          DEFVAL { 5000 }
          ::= { vsmSigTmplEmImmedEntry 1 }
--                
-- ======================================================================
-- This Section is not supported
-- ======================================================================
--
--   vsmSigTmplEmImmedDigitWait OBJECT-TYPE
--          SYNTAX INTEGER
--          UNITS "milliseconds"
--          ACCESS read-write
--          STATUS deprecated
--          DESCRIPTION
--                "Specifies how long, in milliseconds, to wait before digit
--                 collection can be enabled.
--
--                 For more information, please see the following CLI command:
--                  voice signaling template 'signalingTemplateName' emi digit wait (0..60000)
--                 "
--          DEFVAL { 200 }
--          ::= { vsmSigTmplEmImmedEntry 2 }
--

--===================================================================
--
-- E&M Wink Start Signaling Template Table
--
-- This table provides information for control of E&M wink start
-- signaling.
--
--======================================================================

  vsmSigTmplEmWinkTable OBJECT-TYPE
          SYNTAX SEQUENCE OF VsmSigTmplEmWinkEntry
          ACCESS not-accessible
          STATUS mandatory
          DESCRIPTION
                 "This table contains entries that specify how to perform
                  E&M Wink signaling on the channel indicated.
                                  This is not supported."
          ::= { vsmSignalingGroup 5 }

  vsmSigTmplEmWinkEntry OBJECT-TYPE
           SYNTAX VsmSigTmplEmWinkEntry
           ACCESS not-accessible
           STATUS mandatory
           DESCRIPTION
                 "This is an entry in the E&M Wink Signaling Table.
                                 This is not supported.

--                  For more information, please see the following CLI command:
--                    [Note: There is NO equivalent command in the CLI.]
                 "
           INDEX { vsmSigTmplIndex }
           ::= { vsmSigTmplEmWinkTable 1 }

  VsmSigTmplEmWinkEntry ::=
          SEQUENCE {
                  vsmSigTmplEmWinkInWinkWaitMin    INTEGER
--                   ,
--                  vsmSigTmplEmWinkInWinkWaitMax    INTEGER,
--                  vsmSigTmplEmWinkInWinkDur        INTEGER,
--                  vsmSigTmplEmWinkInDigitIgnore    INTEGER,
--                  vsmSigTmplEmWinkOutWinkWaitMax   INTEGER,
--                  vsmSigTmplEmWinkOutWinkDurMin    INTEGER,
--                  vsmSigTmplEmWinkOutWinkDurMax    INTEGER
          }


   vsmSigTmplEmWinkInWinkWaitMin OBJECT-TYPE
          SYNTAX INTEGER (5..60000)
--          UNITS "milliseconds"
          ACCESS read-write
          STATUS deprecated
          DESCRIPTION
                 "Specifies the minimum delay, in milliseconds,
                  before beginning the wink on the E-lead after detecting a
                  line seizure on the M-lead during an incoming call. This is not supported.

--                  For more information, please see the following CLI command:
--                     voice signaling template 'signalingTemplateName' emw in wink wait minimum (5..60000)
                  "
          DEFVAL { 150 }
          ::= { vsmSigTmplEmWinkEntry 1 }
--                
-- ======================================================================
-- This Section is not supported
-- ======================================================================
--
--   vsmSigTmplEmWinkInWinkWaitMax OBJECT-TYPE
--          SYNTAX INTEGER (5..60000)
--          UNITS "milliseconds"
--          ACCESS read-write
--          STATUS mandatory
--          DESCRIPTION
--                 "Specifies the maximum delay, in milliseconds,
--                  before beginning the wink on the E-lead after detecting a
--                  line seizure on the M-lead during an incoming call.
--
--                  For more information, please see the following CLI command:
--                     voice signaling template 'signalingTemplateName' emw in wink wait maximum (5..60000)
--                  "
--          DEFVAL { 290 }
--          ::= { vsmSigTmplEmWinkEntry 2 }
--
--   vsmSigTmplEmWinkInWinkDur OBJECT-TYPE
--          SYNTAX INTEGER (5..60000)
--          UNITS "milliseconds"
--          ACCESS read-write
--          STATUS mandatory
--          DESCRIPTION
--                 "Specifies the duration of the wink signal on the E-lead
--                 for incoming calls.
--
--                 For more information, please see the following CLI command:
--                    voice signaling template 'signalingTemplateName' emw in wink duration (5..60000)
--                 "
--          DEFVAL { 200 }
--          ::= { vsmSigTmplEmWinkEntry 3 }
--
--   vsmSigTmplEmWinkInDigitIgnore OBJECT-TYPE
--          SYNTAX INTEGER (5..1000)
--          UNITS "milliseconds"
--          ACCESS read-write
--          STATUS mandatory
--          DESCRIPTION
--                 "Specifies how long in milliseconds, after
--                  generating the wink signal on the E-lead, incoming digits
--                  will be ignored.
--
--                  For more information, please see the following CLI command:
--                     voice signaling template 'signalingTemplateName' emw in wink digit ignore (5..1000)
--                  "
--          DEFVAL { 30 }
--          ::= { vsmSigTmplEmWinkEntry 4 }
--
--   vsmSigTmplEmWinkOutWinkWaitMax OBJECT-TYPE
--          SYNTAX INTEGER (5..60000)
--          UNITS "milliseconds"
--          ACCESS read-write
--          STATUS mandatory
--          DESCRIPTION
--                "Specifies the time, in milliseconds, to wait
--                to detect a wink of the M-lead after seizure of the E-lead
--                during an outgoing call. If the wink signal is not
--                received within this time period, it is considered an
--                error and the call will not connect.
--
--                For more information, please see the following CLI command:
--                   voice signaling template 'signalingTemplateName' emw out wink wait maximum (5..60000)
--                "
--          DEFVAL { 8000 }
--          ::= { vsmSigTmplEmWinkEntry 5 }
--
--   vsmSigTmplEmWinkOutWinkDurMin OBJECT-TYPE
--          SYNTAX INTEGER (5..60000)
--          UNITS "milliseconds"
--          ACCESS read-write
--          STATUS mandatory
--          DESCRIPTION
--                 "Specifies the minimum duration, in milliseconds,
--                  of the wink on the M-lead during the processing of an
--                  outgoing call.
--
--                  For more information, please see the following CLI command:
--                         voice signaling template 'signalingTemplateName' emw out wink duration minimum (5..60000)
--                        
--                  "
--          DEFVAL { 100 }
--          ::= { vsmSigTmplEmWinkEntry 6 }
--
--   vsmSigTmplEmWinkOutWinkDurMax OBJECT-TYPE
--          SYNTAX INTEGER (5..60000)
--          UNITS "milliseconds"
--          ACCESS read-write
--          STATUS mandatory
--          DESCRIPTION
--                 "Specifies the maximum duration of the wink response on
--                 the M-lead before it is to be declared as a glare condition for
--                 outgoing calls. A glare condition occurs when both ends of a
--                 channel are seized at the same time.  This command reduces the
--                 chance of deadlock.
--
--                 For more information, please see the following CLI command:
--                    voice signaling template 'signalingTemplateName' emw out wink duration maximum (5..60000)                   
--                 "
--          DEFVAL { 800 }
--          ::= { vsmSigTmplEmWinkEntry 7 }

--======================================================================
--
-- Foreign Exchange Office (Fxo) Ground Start Table
--
-- This table provides information for control of FXO ground start
-- signaling.
--
--======================================================================

  vsmSigTmplFxoGSTable OBJECT-TYPE
          SYNTAX SEQUENCE OF VsmSigTmplFxoGSEntry
          ACCESS not-accessible
          STATUS mandatory
          DESCRIPTION
                 "This table contains entries that specify how to perform
                  Foreign Exchange Office (FXO) ground start signaling on the
                  port indicated. This is not supported.
                  "
          ::= { vsmSignalingGroup 6 }

  vsmSigTmplFxoGSEntry OBJECT-TYPE
           SYNTAX VsmSigTmplFxoGSEntry
           ACCESS not-accessible
           STATUS mandatory
           DESCRIPTION
                 "This is an entry in the FXO ground start Signaling Table.
                                 This is not supported.

--                  For more information, please see the following CLI command:
--                    [Note: There is NO equivalent command in the CLI.]
                 "
           INDEX { vsmSigTmplIndex }
           ::= { vsmSigTmplFxoGSTable 1 }

  VsmSigTmplFxoGSEntry ::=
          SEQUENCE {
                vsmSigTmplFxoGSConnectionLoopOpenDebounce                        INTEGER
--                ,
--                vsmSigTmplFxoGSMaxTipGroundWait                                  INTEGER,
--                vsmSigTmplFxoGSTipGroundDebounce                                 INTEGER,
--                vsmSigTmplFxoGSRingingDebounce                                   INTEGER,
--                vsmSigTmplFxoGSRingingInterCycle                                 INTEGER,
--                vsmSigTmplFxoGSRingingInterPulse                                 INTEGER,
--                vsmSigTmplFxoGSCallerIdDetect                                    VsmEnableDisabled,
--                vsmSigTmplFxoGSAnswerAfterRings                                  INTEGER,
--                vsmSigTmplFxoGSLoopCurrentDebounce                               INTEGER,
--                vsmSigTmplFxoGSBattReversalDebounce                              INTEGER
                 }
--
      vsmSigTmplFxoGSConnectionLoopOpenDebounce OBJECT-TYPE
          SYNTAX INTEGER (1..6000)
--          UNITS "milliseconds"
          ACCESS read-write
          STATUS deprecated
          DESCRIPTION
                "Debounce interval for loop open detection for an existing
                conection. This is not supported.

--                For more information, please see the following CLI command:
--                 voice signaling template 'signalingTemplateName' fxo gs connection loop open debounce (1..60000)
                "
          DEFVAL { 150 }
        ::= { vsmSigTmplFxoGSEntry 1 }
--                
-- ======================================================================
-- This Section is not supported
-- ======================================================================
--
--vsmSigTmplFxoGSMaxTipGroundWait OBJECT-TYPE
--          SYNTAX INTEGER (1..60000)
--          UNITS "milliseconds"
--          ACCESS read-write
--          STATUS mandatory
--          DESCRIPTION
--                "Maximum time the interface will wait after ring ground is asserted
--                                for a tip ground receive.
--
--                 For more information, please see the following CLI command:
--                  voice signaling template 'signalingTemplateName' fxo gs maximum tip ground wait (1..60000)
--                 "
--          DEFVAL { 30 }
--        ::= { vsmSigTmplFxoGSEntry 2 }
--
--vsmSigTmplFxoGSTipGroundDebounce OBJECT-TYPE
--          SYNTAX INTEGER (1..1000)
--          UNITS "milliseconds"
--          ACCESS read-write
--          STATUS mandatory
--          DESCRIPTION
--                "Time, in milliseconds, to be used as a de-bouncer interval for debouncing
--                the tip ground detector.
--
--                For more information, please see the following CLI command:
--                 voice signaling template 'signalingTemplateName' fxo gs tip ground debounce (1..1000)
--                "
--          DEFVAL { 20 }
--        ::= { vsmSigTmplFxoGSEntry 3 }
--
--vsmSigTmplFxoGSRingingDebounce OBJECT-TYPE
--          SYNTAX INTEGER (1..1000)
--          UNITS "milliseconds"
--          ACCESS read-write
--          STATUS mandatory
--          DESCRIPTION
--                "When a ring signal is modulated by the ringing frequency,
--                the debouncer is used to debounce the incoming ring signal.
--
--                For more information, please see the following CLI command:
--                 voice signaling template 'signalingTemplateName' fxo gs ringing debounce (1..1000)
--                "
--          DEFVAL { 50 }
--        ::= { vsmSigTmplFxoGSEntry 4 }
--
--vsmSigTmplFxoGSRingingInterCycle OBJECT-TYPE
--          SYNTAX INTEGER (1..60000)
--          UNITS "milliseconds"
--          ACCESS read-write
--          STATUS mandatory
--          DESCRIPTION
--                "Specifies the time between consecutive ring cycles,
--                in milliseconds. It is used to detect ringing.
--
--                For more information, please see the following CLI command:
--                 voice signaling template 'signalingTemplateName' fxo gs ringing inter cycle (1..60000)
--                "
--          DEFVAL { 5000 }
--          ::= { vsmSigTmplFxoGSEntry 5 }
--
--vsmSigTmplFxoGSRingingInterPulse OBJECT-TYPE
--          SYNTAX INTEGER (1..60000)
--          UNITS "milliseconds"
--          ACCESS read-write
--          STATUS mandatory
--          DESCRIPTION
--                "Specifies the time between consecutive
--                ring pulses in the same ring cycle, in milliseconds. It is used
--                to detect ringing.
--
--                For more information, please see the following CLI command:
--                 voice signaling template 'signalingTemplateName' fxo gs ringing inter pulse (1..60000)
--                "
--          DEFVAL { 550 }
--          ::= { vsmSigTmplFxoGSEntry 6 }
--
--vsmSigTmplFxoGSCallerIdDetect OBJECT-TYPE
--          SYNTAX VsmEnableDisabled
--          ACCESS read-write
--          STATUS mandatory
--          DESCRIPTION
--                "If enabled, Caller ID will be detected.
--
--                For more information, please see the following CLI command:
--                 voice signaling template 'signalingTemplateName' fxo gs caller id detection on
--                 voice signaling template 'signalingTemplateName' fxo gs caller id detection off
--                "
--          DEFVAL { disabled }
--          ::= { vsmSigTmplFxoGSEntry 7 }
--
--vsmSigTmplFxoGSAnswerAfterRings OBJECT-TYPE
--          SYNTAX INTEGER (1..65535)
--          ACCESS read-write
--          STATUS mandatory
--          DESCRIPTION
--                "Specifies the number of rings to elapse before answering an
--                 incoming call.
--
--                 For more information, please see the following CLI command:
--                 voice signaling template 'signalingTemplateName' fxo gs answer after (1..65535)
--                 "
--          DEFVAL { 2 }
--          ::= { vsmSigTmplFxoGSEntry 8 }
--
--vsmSigTmplFxoGSLoopCurrentDebounce OBJECT-TYPE
--          SYNTAX INTEGER (0..1000)
--          UNITS "milliseconds"
--          ACCESS read-write
--          STATUS mandatory
--          DESCRIPTION
--                "Time, in milliseconds, to use as a de-bouncer interval for debouncing
--                 the loop current detector.
--
--                 For more information, please see the following CLI command:
--                 voice signaling template 'signalingTemplateName' fxo gs loop current debounce (0..1000)
--                 "
--          DEFVAL { 20 }
--          ::= { vsmSigTmplFxoGSEntry 9 }
--
--vsmSigTmplFxoGSBattReversalDebounce OBJECT-TYPE
--          SYNTAX INTEGER (1..1000)
--          UNITS "milliseconds"
--          ACCESS read-write
--          STATUS mandatory
--          DESCRIPTION
--                "Time, in milliseconds, to use as a de-bouncer interval for debouncing
--                 the battery reversal detector.
--
--                For more information, please see the following CLI command:
--                 voice signaling template 'signalingTemplateName' fxo gs battery reversal debounce (1..1000)
--                 "
--          DEFVAL { 20 }
--          ::= { vsmSigTmplFxoGSEntry 10 }
--

--======================================================================
--
-- Foreign Exchange Office (Fxo) Loop Start Signaling Tempalte Table
--
-- This table provides information for control of FXO loop start
-- signaling.
--
--======================================================================

  vsmSigTmplFxoLSTable OBJECT-TYPE
          SYNTAX SEQUENCE OF VsmSigTmplFxoLSEntry
          ACCESS not-accessible
          STATUS mandatory
          DESCRIPTION
                 "This table contains entries that specify how to perform
                  FXO Loop start signaling on the port indicated.
                                  This is not supported.
                  "
          ::= { vsmSignalingGroup 7 }

  vsmSigTmplFxoLSEntry OBJECT-TYPE
           SYNTAX VsmSigTmplFxoLSEntry
           ACCESS not-accessible
           STATUS mandatory
           DESCRIPTION
                 "This is an entry in the FXO Loop start Signaling Table.
                                 This is not supported.

                  For more information, please see the following CLI command:
                    [Note: There is NO equivalent command in the CLI.]
                 "
           INDEX { vsmSigTmplIndex }
           ::= { vsmSigTmplFxoLSTable 1 }

  VsmSigTmplFxoLSEntry ::=
          SEQUENCE {
                vsmSigTmplFxoLSRingingDebounce                   INTEGER
--                              ,
--                vsmSigTmplFxoLSCPCDetectCtrl                     VsmEnableDisabled,
--                vsmSigTmplFxoLSCPCDetect                         INTEGER,
--                vsmSigTmplFxoLSGuardOut                          INTEGER,
--                vsmSigTmplFxoLSRingingInterCycle                 INTEGER,
--                vsmSigTmplFxoLSRingingInterPulse                 INTEGER,
--                vsmSigTmplFxoLSCallerIdDetect                    VsmEnableDisabled,
--                vsmSigTmplFxoLSAnswerAfterRings                  INTEGER,
--                vsmSigTmplFxoLSLoopCurrentDebounce               INTEGER,
--                vsmSigTmplFxoLSBattReversalDebounce              INTEGER
               }
--
vsmSigTmplFxoLSRingingDebounce OBJECT-TYPE
          SYNTAX INTEGER (1..1000)
--          UNITS "milliseconds"
          ACCESS read-write
          STATUS deprecated
          DESCRIPTION
                "When a ring signal is modulated by the ringing frequency,
                the debouncer is used to debounce the incoming ring signal. This is not supported.

--                For more information, please see the following CLI command:
--                 voice signaling template 'signalingTemplateName' fxo ls ringing debounce (1..1000)
                               "
          DEFVAL { 50 }
::= { vsmSigTmplFxoLSEntry 1 }

--vsmSigTmplFxoLSCPCDetectCtrl OBJECT-TYPE
--          SYNTAX VsmEnableDisabled
--          ACCESS read-write
--          STATUS mandatory
--          DESCRIPTION
--                "This command is used to enable or disable detection of a
--                CPC (supervisory disconnect) signal (vsmSigTmplFxoLSCPCDetect)
--
--                For more information, please see the following CLI command:
--                   voice signaling template 'signalingTemplateName' fxo ls supervisory disconnect detection on
--                   voice signaling template 'signalingTemplateName' fxo ls supervisory disconnect detection off
--                "
--          DEFVAL { enabled }
--::= { vsmSigTmplFxoLSEntry 2 }
--
--vsmSigTmplFxoLSCPCDetect OBJECT-TYPE
--          SYNTAX INTEGER (1..60000)
--          UNITS "milliseconds"
--          ACCESS read-write
--          STATUS mandatory
--          DESCRIPTION
--                "The expected duration of the CPC (supervisory disconnect) signal
--                in milliseconds. If the loop current drops for a time period
--                shorter than indicated, it is not regarded as a supervisory
--                disconnect.  This object is only valid if
--                vsmSigTmplFxoLSCPCDetectCtrl is enabled.
--
--                For more information, please see the following CLI command:
--                   voice signaling template 'signalingTemplateName' fxo ls supervisory disconnect detect (1..60000 )
--                "
--          DEFVAL { 600 }
--          ::= { vsmSigTmplFxoLSEntry 3 }
--
--vsmSigTmplFxoLSGuardOut OBJECT-TYPE
--          SYNTAX INTEGER (1..60000)
--          UNITS "milliseconds"
--          ACCESS read-write
--          STATUS mandatory
--          DESCRIPTION
--                "After the call, the period of time where the channel
--                 does not originate a call, but will receive a call.
--
--                 For more information, please see the following CLI command:
--                  voice signaling template 'signalingTemplateName' fxo ls guard out (1..60000)
--                 "
--          DEFVAL { 2000 }
--          ::= { vsmSigTmplFxoLSEntry 4 }
--
--vsmSigTmplFxoLSRingingInterCycle OBJECT-TYPE
--          SYNTAX INTEGER (1..60000)
--          UNITS "milliseconds"
--          ACCESS read-write
--          STATUS mandatory
--          DESCRIPTION
--                "The time between ring cycles (ringing pulse plus time between
--                ring pulses) in milliseconds. It is used to detect ringing.
--
--                For more information, please see the following CLI command:
--                 voice signaling template 'signalingTemplateName' fxo ls ringing inter cycle (1..60000)
--                 "
--          DEFVAL { 5000 }
--          ::= { vsmSigTmplFxoLSEntry 5 }
--
--vsmSigTmplFxoLSRingingInterPulse OBJECT-TYPE
--          SYNTAX INTEGER (1..60000)
--          UNITS "milliseconds"
--          ACCESS read-write
--          STATUS mandatory
--          DESCRIPTION
--                "The time between ring pulses in milliseconds. It is used
--                to detect ringing.
--
--                For more information, please see the following CLI command:
--                 voice signaling template 'signalingTemplateName' fxo ls ringing inter pulse (1..60000)
--                "
--          DEFVAL { 550 }
--          ::= { vsmSigTmplFxoLSEntry 6 }
--
--vsmSigTmplFxoLSCallerIdDetect OBJECT-TYPE
--          SYNTAX VsmEnableDisabled
--          ACCESS read-write
--          STATUS mandatory
--          DESCRIPTION
--                "If enabled, Caller ID will be detected.
--
--                For more information, please see the following CLI command:
--                 voice signaling template 'signalingTemplateName' fxo ls caller id detection on
--                 voice signaling template 'signalingTemplateName' fxo ls caller id detection off
--                "
--          DEFVAL { enabled }
--          ::= { vsmSigTmplFxoLSEntry 7 }
--
--vsmSigTmplFxoLSAnswerAfterRings OBJECT-TYPE
--          SYNTAX INTEGER (1..65535)
--          ACCESS read-write
--          STATUS mandatory
--          DESCRIPTION
--                "Specifies the number of rings to elapse before answering an
--                 incoming call.
--
--                 For more information, please see the following CLI command:
--                  voice signaling template 'signalingTemplateName' fxo ls answer after (1..65535)
--                 "
--          DEFVAL { 2 }
--          ::= { vsmSigTmplFxoLSEntry 8 }
--
--vsmSigTmplFxoLSLoopCurrentDebounce OBJECT-TYPE
--          SYNTAX INTEGER (1..6000)
--          UNITS "milliseconds"
--          ACCESS read-write
--          STATUS mandatory
--          DESCRIPTION
--                "Time, in milliseconds, to use as a de-bouncer interval for debouncing
--                 the loop current detector.
--
--                 For more information, please see the following CLI command:
--                  voice signaling template 'signalingTemplateName' fxo ls loop current debounce (0..60000)
--                 "
--          DEFVAL { 20 }
--          ::= { vsmSigTmplFxoLSEntry 9 }
--
--vsmSigTmplFxoLSBattReversalDebounce OBJECT-TYPE
--          SYNTAX INTEGER (0..6000)
--          UNITS "milliseconds"
--          ACCESS read-write
--          STATUS mandatory
--          DESCRIPTION
--                "Time, in milliseconds, to use as a de-bouncer interval for debouncing
--                 the battery reversal detector.
--
--                For more information, please see the following CLI command:
--                   voice signaling template 'signalingTemplateName' fxo ls battery reversal debounce (0..60000)
--                 "
--          DEFVAL { 20 }
--          ::= { vsmSigTmplFxoLSEntry 10 }
--

--===================================================================
--
-- Foreign Exchange Station (Fxs) Ground Start
-- Signaling Template Table
--
-- This table provides information for control of FXS ground start
-- signaling.
--
--======================================================================

  vsmSigTmplFxsGSTable OBJECT-TYPE
          SYNTAX SEQUENCE OF VsmSigTmplFxsGSEntry
          ACCESS not-accessible
          STATUS mandatory
          DESCRIPTION
                 "This table contains entries that specify how to perform
                  Foreign Exchange Station (FXS) ground start signaling on
                  the port indicated. 
                                  This is not supported.
                  "
          ::= { vsmSignalingGroup 8 }

  vsmSigTmplFxsGSEntry OBJECT-TYPE
           SYNTAX VsmSigTmplFxsGSEntry
           ACCESS not-accessible
           STATUS mandatory
           DESCRIPTION
                 "This is an entry in the FXS ground start signaling Table.
                                 This is not supported.

--                  For more information, please see the following CLI command:
--                    [Note: There is NO equivalent command in the CLI.]
                 "
           INDEX { vsmSigTmplIndex }
           ::= { vsmSigTmplFxsGSTable 1 }

  VsmSigTmplFxsGSEntry ::=
          SEQUENCE {
                vsmSigTmplFxsGSSeizeDetect               INTEGER
--                              ,
--                vsmSigTmplFxsGSOnHookDebounce            INTEGER,
--                vsmSigTmplFxsGSOrigClearDetect           INTEGER,
--                vsmSigTmplFxsGSAnswClearDetect           INTEGER,
--                vsmSigTmplFxsGSMinRingGround             INTEGER,
--                vsmSigTmplFxsGSMaxWaitLoop               INTEGER,
--                vsmSigTmplFxsGSMinLoopOpen               INTEGER,
--                vsmSigTmplFxsGSGenerateCallerId          VsmEnableDisabled,
--                vsmSigTmplFxsGSOffHookDebounce           INTEGER,
--                vsmSigTmplFxsGSRingGroundDebounce        INTEGER
                }

vsmSigTmplFxsGSSeizeDetect OBJECT-TYPE
           SYNTAX INTEGER (1..5000)
--          UNITS      "milliseconds"
           ACCESS  read-write
           STATUS  deprecated
           DESCRIPTION
                "The time to wait before an off-hook condition is declared.

--                For more information, please see the following CLI command:
--                 voice signaling template 'signalingTemplateName' fxs gs seize detect (1..5000)
                "
           DEFVAL { 150 }
           ::= { vsmSigTmplFxsGSEntry 1 }

--vsmSigTmplFxsGSOnHookDebounce OBJECT-TYPE
--           SYNTAX INTEGER (1..1000)
--          UNITS      "milliseconds"
--           ACCESS  read-write
--           STATUS mandatory
--           DESCRIPTION
--                "Debounce interval to onhook transition.
--
--                For more information, please see the following CLI command:
--                 voice signaling template 'signalingTemplateName' fxs gs on hook debounce (1..1000)
--                "
--           DEFVAL { 20 }
--           ::= { vsmSigTmplFxsGSEntry 2 }
--
--vsmSigTmplFxsGSOrigClearDetect OBJECT-TYPE
--           SYNTAX INTEGER (1..60000)
--          UNITS      "milliseconds"
--           ACCESS  read-write
--           STATUS mandatory
--           DESCRIPTION
--                "The minimum time to wait if the originator drops the
--                line before declaring onhook.
--
--                For more information, please see the following CLI command:
--                 voice signaling template 'signalingTemplateName' fxs gs originate clear detect (1..60000)
--                "
--           DEFVAL { 200 }
--           ::= { vsmSigTmplFxsGSEntry 3 }
--
--vsmSigTmplFxsGSAnswClearDetect OBJECT-TYPE
--           SYNTAX INTEGER (1..60000)
--          UNITS      "milliseconds"
--           ACCESS  read-write
--           STATUS mandatory
--           DESCRIPTION
--                "Minimum time to wait when the answering party drops the
--                line before declaring onhook.
--
--                For more information, please see the following CLI command:
--                 voice signaling template 'signalingTemplateName' fxs gs answer clear detect (1..60000)
--                "
--           DEFVAL { 100 }
--           ::= { vsmSigTmplFxsGSEntry 4 }
--
--vsmSigTmplFxsGSMinRingGround OBJECT-TYPE
--           SYNTAX INTEGER (0..65535)
--          UNITS      "milliseconds"
--           ACCESS  read-write
--           STATUS mandatory
--           DESCRIPTION
--                "The minimum time for the ring lead to be grounded before
--                                it is considered a valid seizure
--
--                For more information, please see the following CLI command:
--                 voice signaling template 'signalingTemplateName' fxs gs minimum ring ground (0..65535)
--                "
--           DEFVAL { 100 }
--           ::= { vsmSigTmplFxsGSEntry 5 }
--
--vsmSigTmplFxsGSMaxWaitLoop OBJECT-TYPE
--           SYNTAX INTEGER (0..65565)
--          UNITS      "milliseconds"
--           ACCESS  read-write
--           STATUS mandatory
--           DESCRIPTION
--                "Specifies the maximum time to allow for the loop to close,
--                after a ring ground is detected and the tip is grounded, before
--                the interface will disconnect.
--
--                For more information, please see the following CLI command:
--                 voice signaling template 'signalingTemplateName' fxs gs maximum wait loop (0..65535)
--                "
--           DEFVAL { 100 }
--           ::= { vsmSigTmplFxsGSEntry 6 }
--
--vsmSigTmplFxsGSMinLoopOpen OBJECT-TYPE
--           SYNTAX INTEGER (0..65535)
--          UNITS      "milliseconds"
--           ACCESS  read-write
--           STATUS mandatory
--           DESCRIPTION
--                "Specifies the minimum time the interface
--                waits after detecting an open loop condition, before returning
--                to an idle state.
--
--                For more information, please see the following CLI command:
--                 voice signaling template 'signalingTemplateName' fxs gs minimum loop open (0..65535)
--                "
--           DEFVAL { 100 }
--           ::= { vsmSigTmplFxsGSEntry 7 }
--
--vsmSigTmplFxsGSGenerateCallerId OBJECT-TYPE
--           SYNTAX VsmEnableDisabled
--           ACCESS  read-write
--           STATUS mandatory
--           DESCRIPTION
--                "If enabled, Caller ID will be generated.
--
--                For more information, please see the following CLI command:
--                 voice signaling template 'signalingTemplateName' fxs gs generate caller id on
--                 voice signaling template 'signalingTemplateName' fxs gs generate caller id off
--                "
--           DEFVAL { disabled }
--           ::= { vsmSigTmplFxsGSEntry 8 }
--
--vsmSigTmplFxsGSOffHookDebounce OBJECT-TYPE
--           SYNTAX INTEGER (1..1000)
--          UNITS      "milliseconds"
--           ACCESS  read-write
--           STATUS mandatory
--           DESCRIPTION
--                "Specifies the time, in milliseconds, to be used as de-bouncer
--                interval for off-hook transition.
--
--                For more information, please see the following CLI command:
--                 voice signaling template 'signalingTemplateName' fxs gs off hook debounce (1..1000)
--                "
--           DEFVAL { 20 }
--           ::= { vsmSigTmplFxsGSEntry 9 }
--
--vsmSigTmplFxsGSRingGroundDebounce OBJECT-TYPE
--           SYNTAX INTEGER (1..1000)
--          UNITS      "milliseconds"
--           ACCESS  read-write
--           STATUS mandatory
--           DESCRIPTION
--                "Time, in milliseconds, to be used as de-bouncer interval for debouncing
--                the ring ground detector.
--
--                For more information, please see the following CLI command:
--                 voice signaling template 'signalingTemplateName' fxs gs ring ground debounce (1..1000)
--                "
--           DEFVAL { 20 }
--           ::= { vsmSigTmplFxsGSEntry 10 }
--

--===================================================================
--
-- Foreign Exchange Station (Fxs) Loop Start
-- Signaling TemplateTable
--
-- This table provides information for control of FXS loop start
-- signaling.
--
--======================================================================

  vsmSigTmplFxsLSTable OBJECT-TYPE
          SYNTAX SEQUENCE OF VsmSigTmplFxsLSEntry
          ACCESS not-accessible
          STATUS mandatory
          DESCRIPTION
                 "This table contains entries that specify how to perform
                  Foreign Exchange Station (FXS) Loop signaling on the port
                  indicated
                                  This is not supported.
                  "
          ::= { vsmSignalingGroup 9 }

  vsmSigTmplFxsLSEntry OBJECT-TYPE
           SYNTAX VsmSigTmplFxsLSEntry
           ACCESS not-accessible
           STATUS mandatory
           DESCRIPTION
                 "This is an entry in the FXS Loop Signaling Table.
                                 This is not supported.

--                  For more information, please see the following CLI command:
--                    [Note: There is NO equivalent command in the CLI.]
                 "
           INDEX { vsmSigTmplIndex }
           ::= { vsmSigTmplFxsLSTable 1 }

  VsmSigTmplFxsLSEntry ::=
          SEQUENCE {
                vsmSigTmplFxsLSOffHookDebounce           INTEGER
--                              ,
--                vsmSigTmplFxsLSOnHookDebounce            INTEGER,
--                vsmSigTmplFxsLSSeizeDetect               INTEGER,
--                vsmSigTmplFxsLSOrigClearDetect           INTEGER,
--                vsmSigTmplFxsLSAnswClearDetect           INTEGER,
--                vsmSigTmplFxsLSCPCWait                   INTEGER,
--                vsmSigTmplFxsLSCPCDur                    INTEGER,
--                vsmSigTmplFxsLSGenerateCallerId          VsmEnableDisabled
                }
 
vsmSigTmplFxsLSOffHookDebounce OBJECT-TYPE
           SYNTAX INTEGER (1..1000)
--          UNITS      "milliseconds"
           ACCESS  read-write
           STATUS deprecated
           DESCRIPTION
                "Debounce interval to offhook transition. This is not supported.

--                For more information, please see the following CLI command:
--                   voice signaling template 'signalingTemplateName' fxs ls off hook debounce (1..1000)
                "
           DEFVAL { 20 }
           ::= { vsmSigTmplFxsLSEntry 1 }

--vsmSigTmplFxsLSOnHookDebounce OBJECT-TYPE
--           SYNTAX INTEGER (1..1000)
--          UNITS      "milliseconds"
--           ACCESS  read-write
--           STATUS mandatory
--           DESCRIPTION
--                "Debounce interval to onhook transition.
--
--                For more information, please see the following CLI command:
--                   voice signaling template 'signalingTemplateName' fxs ls on hook debounce (1..1000)
--                "
--           DEFVAL { 20 }
--           ::= { vsmSigTmplFxsLSEntry 2 }
--
--vsmSigTmplFxsLSSeizeDetect OBJECT-TYPE
--           SYNTAX INTEGER (1..5000)
--          UNITS      "milliseconds"
--           ACCESS  read-write
--           STATUS  mandatory
--           DESCRIPTION
--                "The time to wait before an off-hook condition is declared.
--
--                For more information, please see the following CLI command:
--                   voice signaling template 'signalingTemplateName' fxs ls seize detect (1..5000)
--                "
--           DEFVAL { 150 }
--           ::= { vsmSigTmplFxsLSEntry 3 }
--
--vsmSigTmplFxsLSOrigClearDetect OBJECT-TYPE
--           SYNTAX INTEGER (1..1000)
--          UNITS      "milliseconds"
--           ACCESS  read-write
--           STATUS mandatory
--           DESCRIPTION
--                "The minimum time to wait if the originator drops the
--                line before declaring onhook.
--
--                For more information, please see the following CLI command:
--                   voice signaling template 'signalingTemplateName' fxs ls originate clear detect (1..60000)
--                "
--           DEFVAL { 300 }
--           ::= { vsmSigTmplFxsLSEntry 4 }
--
--vsmSigTmplFxsLSAnswClearDetect OBJECT-TYPE
--           SYNTAX INTEGER (1..60000)
--          UNITS      "milliseconds"
--           ACCESS  read-write
--           STATUS mandatory
--           DESCRIPTION
--                "Minimum time to wait when the answering party drops the
--                line before declaring onhook.
--
--                For more information, please see the following CLI command:
--                   voice signaling template 'signalingTemplateName' fxs ls answer clear detect (1..60000)
--                "
--           DEFVAL { 300 }
--           ::= { vsmSigTmplFxsLSEntry 5 }
--
--vsmSigTmplFxsLSCPCWait OBJECT-TYPE
--           SYNTAX INTEGER (1..60000)
--          UNITS      "milliseconds"
--           ACCESS  read-write
--           STATUS mandatory
--           DESCRIPTION
--                "Time to wait after a Supervisory Disconnect (CPC) signal
--                 is received before declaring on hook.
--
--                 For more information, please see the following CLI command:
--                   voice signaling template 'signalingTemplateName' fxs ls supervisory disconnect wait (1..60000)
--                 "
--           DEFVAL { 200 }
--           ::= { vsmSigTmplFxsLSEntry 6 }
--
--vsmSigTmplFxsLSCPCDur OBJECT-TYPE
--           SYNTAX INTEGER (1..60000)
--          UNITS      "milliseconds"
--           ACCESS  read-write
--           STATUS mandatory
--           DESCRIPTION
--                "If zero, then do not generate Supervisory Disconnect (CPC).
--
--                For more information, please see the following CLI command:
--                   voice signaling template 'signalingTemplateName' fxs ls supervisory disconnect duration (1..60000)
--                "
--           DEFVAL { 850 }
--           ::= { vsmSigTmplFxsLSEntry 7 }
--
--vsmSigTmplFxsLSGenerateCallerId OBJECT-TYPE
--           SYNTAX VsmEnableDisabled
--           ACCESS  read-write
--           STATUS mandatory
--           DESCRIPTION
--                "If enabled, Caller ID will be generated.
--
--                For more information, please see the following CLI command:
--                   voice signaling template 'signalingTemplateName' fxs ls generate caller id { on | off }
--                "
--           DEFVAL { enabled }
--           ::= { vsmSigTmplFxsLSEntry 8 }

--======================================================================
--
--       Signaling Channel Table
--
--      This table specifies signaling parameters per channel.
--
--======================================================================
  vsmSignalingChannelTable OBJECT-TYPE
          SYNTAX SEQUENCE OF VsmSignalingChannelEntry
          ACCESS not-accessible
          STATUS mandatory
          DESCRIPTION
                 "This table contains information for each telephony signaling
                 interface.
                 "
          ::= { vsmSignalingGroup 10 }

  vsmSignalingChannelEntry OBJECT-TYPE
          SYNTAX VsmSignalingChannelEntry
          ACCESS not-accessible
          STATUS mandatory
          DESCRIPTION
                 "This is an entry in the vsmSignalingChannelTable.

                  For more information, please see the following CLI command:
                    [Note: There is NO equivalent command in the CLI.]
                 "
          INDEX {
                        vsmChanSlotIndex,
                        vsmChanPortIndex,
                        vsmChanIndex
                        }
          ::= { vsmSignalingChannelTable 1 }

  VsmSignalingChannelEntry ::=
          SEQUENCE {
                        vsmSigChanProtocol                      INTEGER,
                vsmSigChanCallerIdName                          INTEGER,
                vsmSigChanCallerIdNameStr                       DisplayString,
                vsmSigChanCallerIdNumber                        INTEGER,
                vsmSigChanCallerIdNumberStr                     DisplayString,
                vsmSigChanToneTable                             INTEGER,
                vsmSigChanOutWait                               INTEGER,
                vsmSigChanOutToneDigitDur                       INTEGER,
                vsmSigChanOutToneInterDigitDur                  INTEGER,
                vsmSigChanUnused                                INTEGER,
                vsmSigChanCallLimitCtrl                 VsmEnableDisabled,
                vsmSigChanCallLimit                             INTEGER,
                vsmSigChanAnswerWaitLimitCtrl           VsmEnableDisabled,
                vsmSigChanAnswerWaitLimit                       INTEGER,
                vsmSigChanHangupWaitLimitCtrl           VsmEnableDisabled,
                vsmSigChanHangupWaitLimit                       INTEGER,
                vsmSigChanFaxHoldoverDelay                      INTEGER,
                vsmSigChanCompanding                            INTEGER,
                vsmSigChanReceiveGain                           INTEGER,
                vsmSigChanTransmitGain                          INTEGER,
                vsmSigChanIdleNoise                             INTEGER,
                vsmSigChanOverrideInBandCallProgressTones       VsmEnableDisabled,
                vsmSigChanOverrideInBandCodecSwitching          VsmEnableDisabled,
                vsmSigChanOverridePSUCodecSwitching             VsmEnableDisabled,
                vsmSigChanOverrideNetworkOverlapDialing         VsmEnableDisabled,
                vsmSigChanOverrideFullCallProgressTones         VsmEnableDisabled,
                vsmSigChanOverrideRingBack                      VsmEnableDisabled,
                vsmSigChanOverrideInfoElementTransport          VsmEnableDisabled,
                vsmSigChanOverrideQSIGInfoElementTransport      VsmEnableDisabled,
                vsmSigChanOverrideDataSetup                              VsmOnOff,
                vsmSigChanOverrideVoiceSetup                             VsmOnOff,
                vsmSigChanOverrideFAXSetup                               VsmOnOff,
                vsmSigChanOverrideModemSetup                             VsmOnOff,
                vsmSigChanCallProgressToneDetControl               INTEGER,
                vsmSigChanCallProgressToneDetCfg                INTEGER,
                vsmSigChanAssignTmplName                        DisplayString,
                vsmSigChanAssignTmplStatus                      INTEGER,
                vsmSigChanOutDialType                                    INTEGER,
                vsmSigChanV18ToneDetThHangTime                   INTEGER,
                vsmSigChanV18ToneDetThLevel                              INTEGER,
                vsmSigChanV18ToneDetThFraction                   INTEGER,
                vsmSigChanSinFreqToneDetThLev                    INTEGER,
                vsmSigChanSinFreqToneDetThTime                   INTEGER,
                vsmSigChanEchoCancelNonSens                              INTEGER,
                vsmSigChanAcousticEchoCancellerMode              VsmEnableDisabled,
                vsmSigChanAcouEchoCanNonProc                     VsmEnableDisabled,
                vsmSigChanAcEchoCanSetSpGain                     INTEGER,
                vsmSigChanAcEchoCanFreeSpGain                    INTEGER,
                vsmSigChanAcousticEchoCanOper                    INTEGER,
                                vsmSigChanFxsLSCadenceCoefficient                                INTEGER,
                                vsmSigChanFxsLSRingId                                                    INTEGER,
                                vsmSigChanFxsGSCadenceCoefficient                                INTEGER,
                                vsmSigChanFxsGSRingId                                                    INTEGER
                }

  vsmSigChanProtocol OBJECT-TYPE
          SYNTAX INTEGER {
                                 emDelayStart           (1),
                                 emImmedStart           (2),
                                 emWinkStart            (3),
                                 fxoGroundStart         (4),
                                 fxsGroundStart         (5),
                                 fxoLoopStart           (6),
                                 fxsLoopStart           (7),
                                 isdn                   (8)
                                         }
          ACCESS read-write
          STATUS mandatory
          DESCRIPTION
                 "The signaling protocol this template has been set up to perform.

                For more information, please see the following CLI command:
                 voice signaling channel slot/port/startChannel-endChannel protocol fxs ls
                 voice signaling channel slot/port/startChannel-endChannel protocol fxo ls
                 voice signaling channel slot/port/startChannel-endChannel protocol fxs gs
                 voice signaling channel slot/port/startChannel-endChannel protocol fxo gs
                 voice signaling channel slot/port/startChannel-endChannel protocol emi
                 voice signaling channel slot/port/startChannel-endChannel protocol emd
                 voice signaling channel slot/port/startChannel-endChannel protocol emw
                 voice signaling channel slot/port/startChannel-endChannel protocol ISDN
                 "
          DEFVAL { emWinkStart }
          ::= { vsmSignalingChannelEntry 1 }

  vsmSigChanCallerIdName OBJECT-TYPE
           SYNTAX INTEGER {
                                        private         (1),
                                        unavailable (2),
                                        available       (3)
                                        }
           ACCESS  read-write
           STATUS mandatory
           DESCRIPTION
                "The originating name to transmit may be private, unavailable
                or available.

                For more information, please see the following CLI command:
                 voice signaling channel slot/port/startChannel-endChannel caller id name private
                 voice signaling channel slot/port/startChannel-endChannel caller id name unavailable
                "
           DEFVAL { unavailable }
           ::= { vsmSignalingChannelEntry 2 }

  vsmSigChanCallerIdNameStr OBJECT-TYPE
           SYNTAX DisplayString
           ACCESS  read-write
           STATUS mandatory
           DESCRIPTION
                "The caller Id name is meaningful if the
                vsmSigChanCallerIdType is set to available.

                For more information, please see the following CLI command:
                 voice signaling channel slot/port/startChannel-endChannel caller id name 'callerIdName'
                "
           ::= { vsmSignalingChannelEntry 3 }

  vsmSigChanCallerIdNumber OBJECT-TYPE
           SYNTAX INTEGER {
                private         (1),
                unavailable     (2),
                available       (3)
                                        }
           ACCESS  read-write
           STATUS mandatory
           DESCRIPTION
                "The originating phone number to transmit may be private,
                unavailable or available.

                For more information, please see the following CLI command:
                 voice signaling channel slot/port/startChannel-endChannel caller id number private
                 voice signaling channel slot/port/startChannel-endChannel caller id number unavailable
                "
           DEFVAL { unavailable }
           ::= { vsmSignalingChannelEntry 4 }

  vsmSigChanCallerIdNumberStr OBJECT-TYPE
           SYNTAX DisplayString
           ACCESS  read-write
           STATUS mandatory
           DESCRIPTION
                "The originating telephone number to transmit is only
                meaningful if vsmSigChanCallerIdNumberType is set to
                available.

                For more information, please see the following CLI command:
                 voice signaling channel slot/port/startChannel-endChannel caller id number 'callerIdNumber'
                "
           ::= { vsmSignalingChannelEntry 5 }

        vsmSigChanToneTable OBJECT-TYPE
        SYNTAX INTEGER {
                        ringing   (1),
                        silence  (2)
                        }
        ACCESS read-write
        STATUS mandatory
        DESCRIPTION
        "
        This command is used to select the Tone Table for a TCID. Tone table
        to use. (In the future, this parameter will probably be changed to a
        VSx daughter card parameter.)

        Value Description
        ===== ===========
        ringing  Default.  Typically set for a normal ringback sound
        silence Typically set for a silent ringback.

        For more information, please see the following CLI command:
            voice signaling channel slot/port/startChannel-endChannel tone table ringing
            voice signaling channel slot/port/startChannel-endChannel tone table silence
        "
        DEFVAL { ringing }
        ::= { vsmSignalingChannelEntry 6 }


   vsmSigChanOutWait OBJECT-TYPE
          SYNTAX INTEGER ( 0..20000 )
--          UNITS "milliseconds"
          ACCESS read-write
          STATUS mandatory
          DESCRIPTION
                 "The time to delay after going off-hook, before generating the
                 first outbound dial digit(s).

                 For more information, please see the following CLI command:
                  voice signaling channel slot/port/startChannel-endChannel out wait (0..20000)
                 "
          DEFVAL { 400 }
          ::= { vsmSignalingChannelEntry 7}

   vsmSigChanOutToneDigitDur OBJECT-TYPE
          SYNTAX INTEGER (25..2000)
--          UNITS      "milliseconds"
          ACCESS read-write
          STATUS mandatory
          DESCRIPTION
                 "This is the duration, in milliseconds, of a tone that
                  is generated when tone dialing is used.

                  For more information, please see the following CLI command:
                   voice signaling channel slot/port/startChannel-endChannel out tone digit duration (25..2000)
                  "
          DEFVAL { 200 }
          ::= { vsmSignalingChannelEntry 8 }

   vsmSigChanOutToneInterDigitDur OBJECT-TYPE
          SYNTAX INTEGER (25..2000)
--          UNITS      "milliseconds"
          ACCESS read-write
          STATUS mandatory
          DESCRIPTION
                 "This is the duration, in milliseconds, of the inter digit
                  gap when tone dialing is used.

                  For more information, please see the following CLI command:
                   voice signaling channel slot/port/startChannel-endChannel out tone interdigit duration (25..2000)

                  "
          DEFVAL { 200 }
          ::= { vsmSignalingChannelEntry 9 }

   vsmSigChanUnused OBJECT-TYPE
          SYNTAX INTEGER (0..0)
          ACCESS read-write
          STATUS deprecated
          DESCRIPTION
                 "This object is no longer supported. Was vsmSigTmplOutToneAmplitude."
          ::= { vsmSignalingChannelEntry 10 }

   vsmSigChanCallLimitCtrl OBJECT-TYPE
          SYNTAX VsmEnableDisabled
          ACCESS read-write
          STATUS mandatory
          DESCRIPTION
                 "Enables or Disables call timing limit duration
                 (vsmSigChanCallLimit).

                 For more information, please see the following CLI command:
                    voice signaling channel slot/port/startChannel-endChannel no call duration limit
                 "
          DEFVAL { disabled }
          ::= { vsmSignalingChannelEntry 11 }

   vsmSigChanCallLimit OBJECT-TYPE
          SYNTAX INTEGER (0..65534)
--          UNITS      "seconds"
          ACCESS read-write
          STATUS mandatory
          DESCRIPTION
                 "The call duration limit. If the call length is exceeded,
                 the call is automatically terminated.

                 For more information, please see the following CLI command:
                    voice signaling channel slot/port/startChannel-endChannel call duration limit (0..65534)
                                "
          DEFVAL { 65534 }
          ::= { vsmSignalingChannelEntry 12 }

   vsmSigChanAnswerWaitLimitCtrl OBJECT-TYPE
          SYNTAX VsmEnableDisabled
          ACCESS read-write
          STATUS mandatory
          DESCRIPTION
                 "Enables or Disables call answer limit timing
                 (vsmSigChanAnswerWaitLimit).

                 For more information, please see the following CLI command:
                  voice signaling channel slot/port/startChannel-endChannel no answer wait limit
                 "
          DEFVAL { disabled }
          ::= { vsmSignalingChannelEntry 13 }

   vsmSigChanAnswerWaitLimit OBJECT-TYPE
          SYNTAX INTEGER (0..65534)
--          UNITS      "seconds"
          ACCESS read-write
          STATUS mandatory
          DESCRIPTION
                 "The wait-for-answer time limit. If the call destination does not
                 answer within this period, the call is automatically terminated.

                 For more information, please see the following CLI command:
                  voice signaling channel slot/port/startChannel-endChannel answer wait limit (0..65534)
                 "
          DEFVAL { 65534 }
          ::= { vsmSignalingChannelEntry 14 }

   vsmSigChanHangupWaitLimitCtrl OBJECT-TYPE
          SYNTAX VsmEnableDisabled
          ACCESS read-write
          STATUS mandatory
          DESCRIPTION
                 "Enables or Disables call hangup limit timing
                 (vsmSigChanHangupWaitLimit).

                 For more information, please see the following CLI command:
                    voice signaling channel slot/port/startChannel-endChannel no hang up wait limit
                 "
          DEFVAL { disabled }
          ::= { vsmSignalingChannelEntry 15 }

   vsmSigChanHangupWaitLimit OBJECT-TYPE
          SYNTAX INTEGER (0..65534)
--          UNITS      "seconds"
          ACCESS read-write
          STATUS mandatory
          DESCRIPTION
                 "The wait-for-hang-up time limit. If
                 the call originator does not hang up within this time period
                 after the destination has hung up, the call is automatically
                 terminated.

                 For more information, please see the following CLI command:
                    voice signaling channel slot/port/startChannel-endChannel hang up wait limit (0..65534)
                 "
          DEFVAL { 65534 }
          ::= { vsmSignalingChannelEntry 16 }

   vsmSigChanFaxHoldoverDelay OBJECT-TYPE
          SYNTAX INTEGER (0..65534)
--          UNITS      "milliseconds"
          ACCESS read-write
          STATUS mandatory
          DESCRIPTION
                 "The Fax holdover delay. This
                 is the time the system will delay after detecting on-hook during
                 fax mode operation, before generating a call clear.

                 For more information, please see the following CLI command:
                    voice signaling channel slot/port/startChannel-endChannel fax holdover (0..65534)
                 "
          DEFVAL { 2000 }
          ::= { vsmSignalingChannelEntry 17 }

   vsmSigChanCompanding OBJECT-TYPE
          SYNTAX INTEGER {
                                alaw            (1),
                                mulaw           (2)
                                }
          ACCESS read-write
          STATUS mandatory
          DESCRIPTION
                 "Select the companding used at the DSP's PCM interface.

                 For more information, please see the following CLI command:
                 voice signaling channel slot/port/startChannel-endChannel companding alaw
                 voice signaling channel slot/port/startChannel-endChannel companding mulaw
                 "
          DEFVAL { mulaw }
          ::= { vsmSignalingChannelEntry 18 }

   vsmSigChanReceiveGain OBJECT-TYPE
          SYNTAX INTEGER (-14..14)
--          UNITS      "dB"
          ACCESS read-write
          STATUS mandatory
          DESCRIPTION
                 "The Receive (Rx) Gain, in dB. The reference to Rx gain is from the
                 perspective of the Micro software. The Micro interprets receive (Rx)
                 gain as PCM interface-to-packet network.

                 For more information, please see the following CLI command:
                         voice signaling channel slot/port/startChannel-endChannel receive gain 0
                         voice signaling channel slot/port/startChannel-endChannel receive gain -14
                         voice signaling channel slot/port/startChannel-endChannel receive gain -13
                         voice signaling channel slot/port/startChannel-endChannel receive gain -12
                         voice signaling channel slot/port/startChannel-endChannel receive gain -11
                         voice signaling channel slot/port/startChannel-endChannel receive gain -10
                         voice signaling channel slot/port/startChannel-endChannel receive gain -9
                         voice signaling channel slot/port/startChannel-endChannel receive gain -8
                         voice signaling channel slot/port/startChannel-endChannel receive gain -7
                         voice signaling channel slot/port/startChannel-endChannel receive gain -6
                         voice signaling channel slot/port/startChannel-endChannel receive gain -5
                         voice signaling channel slot/port/startChannel-endChannel receive gain -4
                         voice signaling channel slot/port/startChannel-endChannel receive gain -3
                         voice signaling channel slot/port/startChannel-endChannel receive gain -2
                         voice signaling channel slot/port/startChannel-endChannel receive gain -1
                         voice signaling channel slot/port/startChannel-endChannel receive gain 14
                         voice signaling channel slot/port/startChannel-endChannel receive gain 13
                         voice signaling channel slot/port/startChannel-endChannel receive gain 12
                         voice signaling channel slot/port/startChannel-endChannel receive gain 11
                         voice signaling channel slot/port/startChannel-endChannel receive gain 10
                         voice signaling channel slot/port/startChannel-endChannel receive gain 9
                         voice signaling channel slot/port/startChannel-endChannel receive gain 8
                         voice signaling channel slot/port/startChannel-endChannel receive gain 7
                         voice signaling channel slot/port/startChannel-endChannel receive gain 6
                         voice signaling channel slot/port/startChannel-endChannel receive gain 5
                         voice signaling channel slot/port/startChannel-endChannel receive gain 4
                         voice signaling channel slot/port/startChannel-endChannel receive gain 3
                         voice signaling channel slot/port/startChannel-endChannel receive gain 2
                         voice signaling channel slot/port/startChannel-endChannel receive gain 1
                                         "
          DEFVAL { 0 }
          ::= { vsmSignalingChannelEntry 19 }

   vsmSigChanTransmitGain OBJECT-TYPE
          SYNTAX INTEGER (-14..14)
--          UNITS      "dB"
          ACCESS read-write
          STATUS mandatory
          DESCRIPTION
                 "The Transmit (Tx) Gain, in dB. The reference to Tx gain is from
                 the perspective of the Micro software. The Micro interprets
                 transmit (Tx) gain as packet network-to-PCM interface.

                 For more information, please see the following CLI command:
                         voice signaling channel slot/port/startChannel-endChannel transmit gain 0
                         voice signaling channel slot/port/startChannel-endChannel transmit gain -14
                         voice signaling channel slot/port/startChannel-endChannel transmit gain -13
                         voice signaling channel slot/port/startChannel-endChannel transmit gain -12
                         voice signaling channel slot/port/startChannel-endChannel transmit gain -11
                         voice signaling channel slot/port/startChannel-endChannel transmit gain -10
                         voice signaling channel slot/port/startChannel-endChannel transmit gain -9
                         voice signaling channel slot/port/startChannel-endChannel transmit gain -8
                         voice signaling channel slot/port/startChannel-endChannel transmit gain -7
                         voice signaling channel slot/port/startChannel-endChannel transmit gain -6
                         voice signaling channel slot/port/startChannel-endChannel transmit gain -5
                         voice signaling channel slot/port/startChannel-endChannel transmit gain -4
                         voice signaling channel slot/port/startChannel-endChannel transmit gain -3
                         voice signaling channel slot/port/startChannel-endChannel transmit gain -2
                         voice signaling channel slot/port/startChannel-endChannel transmit gain -1
                         voice signaling channel slot/port/startChannel-endChannel transmit gain 14
                         voice signaling channel slot/port/startChannel-endChannel transmit gain 13
                         voice signaling channel slot/port/startChannel-endChannel transmit gain 12
                         voice signaling channel slot/port/startChannel-endChannel transmit gain 11
                         voice signaling channel slot/port/startChannel-endChannel transmit gain 10
                         voice signaling channel slot/port/startChannel-endChannel transmit gain 9
                         voice signaling channel slot/port/startChannel-endChannel transmit gain 8
                         voice signaling channel slot/port/startChannel-endChannel transmit gain 7
                         voice signaling channel slot/port/startChannel-endChannel transmit gain 6
                         voice signaling channel slot/port/startChannel-endChannel transmit gain 5
                         voice signaling channel slot/port/startChannel-endChannel transmit gain 4
                         voice signaling channel slot/port/startChannel-endChannel transmit gain 3
                         voice signaling channel slot/port/startChannel-endChannel transmit gain 2
                         voice signaling channel slot/port/startChannel-endChannel transmit gain 1
                 "
          DEFVAL { 0 }
          ::= { vsmSignalingChannelEntry 20 }

   vsmSigChanIdleNoise OBJECT-TYPE
          SYNTAX INTEGER (-7000..7000)
--          UNITS      ".01 dBm"
          ACCESS read-write
          STATUS mandatory
          DESCRIPTION
                 "The Idle Noise level (also known as comfort noise), in 0.01dBm.
                 a value of -5000 means -50 dbm.

                 For more information, please see the following CLI command:
                  voice signaling channel slot/port/startChannel-endChannel idle noise (-7000..7000)
                 "
          DEFVAL { 7000 }
          ::= { vsmSignalingChannelEntry 21 }

   vsmSigChanOverrideInBandCallProgressTones OBJECT-TYPE
          SYNTAX VsmEnableDisabled
          ACCESS read-write
          STATUS mandatory
          DESCRIPTION
                 "Enables or Disables support for passing call progress
                 tones in band (ie, call progress tones are carried as voice)
                 This object should only be used under the supervision of trained personnel.

                 For more information, please see the following CLI command:
                  voice signaling  channel slot/port/startChannel-endChannel no override in band call progress tones
                  voice signaling  channel slot/port/startChannel-endChannel override in band call progress tones on
                  voice signaling  channel slot/port/startChannel-endChannel override in band call progress tones off
                 "
          DEFVAL { disabled }
          ::= { vsmSignalingChannelEntry 22 }

   vsmSigChanOverrideInBandCodecSwitching OBJECT-TYPE
          SYNTAX VsmEnableDisabled
          ACCESS read-write
          STATUS mandatory
          DESCRIPTION
                 "Enables or Disables capability of the call to switch from one
                 codec to another in band (in voice mode) by detecting change
                 in payload type of the packets
                 This object should only be used under the supervision of trained personnel.

                 For more information, please see the following CLI command:
                  voice signaling channel slot/port/startChannel-endChannel no override in band codec switching
                 "
          DEFVAL { disabled }
          ::= { vsmSignalingChannelEntry 23 }

   vsmSigChanOverridePSUCodecSwitching OBJECT-TYPE
          SYNTAX VsmEnableDisabled
          ACCESS read-write
          STATUS mandatory
          DESCRIPTION
                 "Enables or Disables Coding switchover in the Signaling band. In
                 the PSU this is accomplished by using the Set-Coding API. This
                 happens after the Net-Connect stage.
                 This object should only be used under the supervision of trained personnel.

                 For more information, please see the following CLI command:
                 voice signaling channel slot/port/startChannel-endChannel override PSU codec switching on
                 voice signaling channel slot/port/startChannel-endChannel override PSU codec switching off
                 voice signaling channel slot/port/startChannel-endChannel no override PSU codec switching
                 "
          DEFVAL { disabled }
          ::= { vsmSignalingChannelEntry 24 }

   vsmSigChanOverrideNetworkOverlapDialing OBJECT-TYPE
          SYNTAX VsmEnableDisabled
          ACCESS read-write
          STATUS mandatory
          DESCRIPTION
                 "Enables or Disables support for Network overlap dialing. The
                 Net connect happens even if all the digits have not been collected.
                 The call moves to Call progress when the dialing is completed.
                 This object should only be used under the supervision of trained personnel.

                 For more information, please see the following CLI command:
                    voice signaling channel slot/port/startChannel-endChannel override network overlap dialing on
                    voice signaling channel slot/port/startChannel-endChannel override network overlap dialing off
                    voice signaling channel slot/port/startChannel-endChannel no override network overlap dialing
                 "
          DEFVAL { disabled }
          ::= { vsmSignalingChannelEntry 25 }

   vsmSigChanOverrideFullCallProgressTones OBJECT-TYPE
          SYNTAX VsmEnableDisabled
          ACCESS read-write
          STATUS mandatory
          DESCRIPTION
                 "Enables or Disables support for full call progress tones in
                 signaling band. Call progress indications are sent as information
                 type packets. The call progress tones include Ringback, Busy etc. 
                 This object should only be used under the supervision of trained personnel.

                 For more information, please see the following CLI command:
                    voice signaling channel slot/port/startChannel-endChannel no override full call progress tones
                 "
          DEFVAL { disabled }
          ::= { vsmSignalingChannelEntry 26 }

   vsmSigChanOverrideRingBack OBJECT-TYPE
          SYNTAX VsmEnableDisabled
          ACCESS read-write
          STATUS mandatory
          DESCRIPTION
                 "Enables or Disables ring back detection.  
                 This object should only be used under the supervision of trained personnel.

                 For more information, please see the following CLI command:
                  voice signaling channel slot/port/startChannel-endChannel no override ring back
                 "
          DEFVAL { disabled }
          ::= { vsmSignalingChannelEntry 27 }

   vsmSigChanOverrideInfoElementTransport OBJECT-TYPE
          SYNTAX VsmEnableDisabled
          ACCESS read-write
          STATUS mandatory
          DESCRIPTION
                 "Enables or Disables general user to user Information Element  (IE)
                 packet passing support.  This means that the call is capable of
                 transporting IEs from user to user.

                 For more information, please see the following CLI command:
                  voice signaling channel slot/port/startChannel-endChannel no override information element transport
                 "
          DEFVAL { disabled }
          ::= { vsmSignalingChannelEntry 28 }

   vsmSigChanOverrideQSIGInfoElementTransport OBJECT-TYPE
          SYNTAX VsmEnableDisabled
          ACCESS read-write
          STATUS mandatory
          DESCRIPTION
                 "Enables or Disables QSIG Information Element  (IE)
                 packet passing support.
                 This object should only be used under the supervision of trained personnel.

                 For more information, please see the following CLI command:
                    voice signaling channel slot/port/startChannel-endChannel no override QSIG information element transport
                 "
          DEFVAL { disabled }
          ::= { vsmSignalingChannelEntry 29 }

   vsmSigChanOverrideDataSetup OBJECT-TYPE
          SYNTAX VsmOnOff
          ACCESS read-write
          STATUS mandatory
          DESCRIPTION
                 "Enables or Disables identification that this is a data call.
                 Only one of the following objects should be enabled:
                 vsmSigChanHangupWaitLimit, vsmSigChanVoiceSetup,
                 vsmSigChanFAXSetup, or vsmSigChanModemSetup
                 This object should only be used under the supervision of trained personnel.

                 For more information, please see the following CLI command:
                  voice signaling channel slot/port/startChannel-endChannel no override data setup
                 "
          DEFVAL { off }
          ::= { vsmSignalingChannelEntry 30 }

   vsmSigChanOverrideVoiceSetup OBJECT-TYPE
          SYNTAX VsmOnOff
          ACCESS read-write
          STATUS mandatory
          DESCRIPTION
                 "Enables or Disables identification that this is a voice call.
                 Only one of the following objects should be enabled:
                 vsmSigChanHangupWaitLimit, vsmSigChanVoiceSetup,
                 vsmSigChanFAXSetup, or vsmSigChanModemSetup
                 This object should only be used under the supervision of trained personnel.

                 For more information, please see the following CLI command:
                  voice signaling channel slot/port/startChannel-endChannel no override voice setup
                  voice signaling channel slot/port/startChannel-endChannel override voice setup on
                  voice signaling channel slot/port/startChannel-endChannel override voice setup off
                 "
          DEFVAL { off }
          ::= { vsmSignalingChannelEntry 31 }

   vsmSigChanOverrideFAXSetup OBJECT-TYPE
          SYNTAX VsmOnOff
          ACCESS read-write
          STATUS mandatory
          DESCRIPTION
                 "Enables or Disables identification that this is a FAX call.
                 Only one of the following objects should be enabled:
                 vsmSigChanHangupWaitLimit, vsmSigChanVoiceSetup,
                 vsmSigChanFAXSetup, or vsmSigChanModemSetup
                 This object should only be used under the supervision of trained personnel.

                 For more information, please see the following CLI command:
                  voice signaling channel slot/port/startChannel-endChannel no override fax setup
                 "
          DEFVAL { off }
          ::= { vsmSignalingChannelEntry 32 }

   vsmSigChanOverrideModemSetup OBJECT-TYPE
          SYNTAX VsmOnOff
          ACCESS read-write
          STATUS mandatory
          DESCRIPTION
                 "Enables or Disables identification that this is a modem call.
                 Only one of the following objects should be enabled:
                 vsmSigChanHangupWaitLimit, vsmSigChanVoiceSetup,
                 vsmSigChanFAXSetup, or vsmSigChanModemSetup
                 This object should only be used under the supervision of trained personnel.

                 For more information, please see the following CLI command:
                  voice signaling channel slot/port/startChannel-endChannel no override modem setup
                 "
          DEFVAL { off }
          ::= { vsmSignalingChannelEntry 33 }

    vsmSigChanCallProgressToneDetControl OBJECT-TYPE
        SYNTAX INTEGER {
                        off (1),
                        on (2),
                        relative (3)
                        }
        ACCESS read-write
        STATUS mandatory
        DESCRIPTION
           "This command is used to control the detection of call progress tones.

            Value     Description
            =====     ===========
            off       Disable call progress detection.
            on        Enable call progress detection.
            relative  Enable/disable call progress detection according to the Call
                        progress tone detection parameter in the coding profile that
                        is currently loaded.

            For more information, please see the following CLI command:
               voice signaling channel slot/port/startChannel-endChannel call progress tone detection control off
               voice signaling channel slot/port/startChannel-endChannel call progress tone detection control on
               voice signaling channel slot/port/startChannel-endChannel call progress tone detection control relative
            "
        DEFVAL { off }
        ::= { vsmSignalingChannelEntry 34 }


   vsmSigChanCallProgressToneDetCfg OBJECT-TYPE
          SYNTAX INTEGER {
                                default                 (1),
                                alternate               (2)
                                }
          ACCESS read-write
          STATUS mandatory
          DESCRIPTION
                 "Specifies which configuration will be used for call progress tone
                 detection.  A configuration includes filter configuration information
                 (threshold and filter coefficients), and a table containing cadence
                 information of all the call progress tones that are to be detected.
                 Two sample configurations are provided - default and alternate.  Both
                 of the configurations currently use the default filter
                 configuration  - dial tone, ring back,
                 (3 different cadences are supported), bust, and congestion.
                 The alternate configuration allows for the detection of the busy
                 tone only.

                 For more information, please see the following CLI command:
                  voice signaling channel slot/port/startChannel-endChannel call progress tone detection configuration default
                  voice signaling channel slot/port/startChannel-endChannel call progress tone detection configuration alternate
                 "
          DEFVAL { default }
          ::= { vsmSignalingChannelEntry 35 }

vsmSigChanAssignTmplName OBJECT-TYPE
          SYNTAX DisplayString
          ACCESS read-write
          STATUS mandatory
          DESCRIPTION
                 "This object specifies the ID of the Signaling template to
                 assign to this channel.

                 For more information, please see the following CLI command:
                  voice channel slot/port/startChannel-endChannel assign signaling template 'signalingTemplateName'
                 "
          ::= { vsmSignalingChannelEntry 36 }

vsmSigChanAssignTmplStatus OBJECT-TYPE
          SYNTAX INTEGER {
                        assign          (1)
                                }
          ACCESS write-only
          STATUS mandatory
          DESCRIPTION
                 "Causes the vsmSigChanAssignTmplName to be assigned.

                 For more information, please see the following CLI command:
                  voice channel slot/port/startChannel-endChannel assign signaling template 'signalingTemplateName'
                 "
          DEFVAL { assign }
          ::= { vsmSignalingChannelEntry 37 }


        vsmSigChanOutDialType OBJECT-TYPE
        SYNTAX INTEGER {
                        tone (1),
                        pulse (2)
                        }

        ACCESS read-write
        STATUS mandatory
        DESCRIPTION

        "
        This command is used to select the out dialing characteristic of the channels
                on the specified port.

        Value Description
        ===== ===========
        Tone  Default. Indicates use of tone (Dual Tone Multi-frequency) dialing.
        Pulse Indicates use of pulse dialing.

        For more information, please see the following CLI command:
            voice signaling channel slot/port/startChannel-endChannel out dialing type tone
            voice signaling channel slot/port/startChannel-endChannel out dialing type pulse

        "

        DEFVAL { tone }
        ::= { vsmSignalingChannelEntry 38 }


        vsmSigChanV18ToneDetThHangTime OBJECT-TYPE
        SYNTAX INTEGER (5..32767)
        ACCESS read-write
        STATUS mandatory
        DESCRIPTION
        "
        This command sets the signal duration threshold for V18 tone detection.

        For more information, please see the following CLI command:
            voice signaling channel slot/port/startChannel-endChannel v.18 tone detection threshold hang time (5 ... 32767)

        "
        DEFVAL { 50 }
        ::= { vsmSignalingChannelEntry 39 }


        vsmSigChanV18ToneDetThLevel OBJECT-TYPE
        SYNTAX INTEGER (-50..-15)
        ACCESS read-write
        STATUS mandatory
        DESCRIPTION
        "
        This command sets the signal strength threshold for V18 tone detection.
        For more information, please see the following CLI command:
            voice signaling channel slot/port/startChannel-endChannel v.18 tone detection threshold Level (-50 ... -15)

        "
        DEFVAL {-40}
        ::= { vsmSignalingChannelEntry 40 }


        vsmSigChanV18ToneDetThFraction OBJECT-TYPE
        SYNTAX INTEGER (1..32767)
        ACCESS read-write
        STATUS mandatory
        DESCRIPTION
        "
        This command sets the signal fraction threshold for V18 tone detection.
        For more information, please see the following CLI command:
            voice signaling channel slot/port/startChannel-endChannel v.18 tone detection threshold fraction (1 ... 32767)

        "
        DEFVAL { 10 }
        ::= { vsmSignalingChannelEntry 41 }

        vsmSigChanSinFreqToneDetThLev OBJECT-TYPE
        SYNTAX INTEGER (-50..-15)
        ACCESS read-write
        STATUS mandatory
        DESCRIPTION
        "
        This command sets the signal strength threshold for SF {single frequency } tone detection.

        For more information, please see the following CLI command:
            voice signaling channel slot/port/startChannel-endChannel single frequency tone detection
                   threshold level (-50 ... -15)

        "
        DEFVAL { -40 }
        ::= { vsmSignalingChannelEntry 42 }


        vsmSigChanSinFreqToneDetThTime OBJECT-TYPE
        SYNTAX INTEGER (0..65535)
        ACCESS read-write
        STATUS mandatory
        DESCRIPTION
        "
        This command sets the time threshold level for SF {single frequency } tone detection.

        For more information, please see the following CLI command:
            voice signaling channel slot/port/startChannel-endChannel single frequency tone detection
                   threshold time (0 ... 65535)

        "
        DEFVAL { 50 }
        ::= { vsmSignalingChannelEntry 43 }


        vsmSigChanEchoCancelNonSens OBJECT-TYPE
        SYNTAX INTEGER (0..32767)
        ACCESS read-write
        STATUS mandatory
        DESCRIPTION
        "
        This command sets the sensitivity of the echo canceller non-linear processor.

        For more information, please see the following CLI command:
            voice signaling channel slot/port/startChannel-endChannel echo canceller non-linear sensitivity (0 ... 32767)

        "
        DEFVAL {327}
        ::= { vsmSignalingChannelEntry 44 }


        vsmSigChanAcousticEchoCancellerMode OBJECT-TYPE
        SYNTAX VsmEnableDisabled
        ACCESS read-write
        STATUS mandatory
        DESCRIPTION
        "
        This command selects whether the line of the Acoustic Echo Canceller (EC) is started on channel startup.

        For more information, please see the following CLI command:
            voice signaling channel slot/port/startChannel-endChannel acoustic echo canceller mode on
            voice signaling channel slot/port/startChannel-endChannel acoustic echo canceller mode off
        "
        DEFVAL { disabled }
        ::= { vsmSignalingChannelEntry 45 }


        vsmSigChanAcouEchoCanNonProc OBJECT-TYPE
        SYNTAX VsmEnableDisabled
        ACCESS read-write
        STATUS mandatory
        DESCRIPTION
        "

        This command enables or disables the (TBD: acoustic echo canceller non-linear processor or
                comfort noise level generator)

        For more information, please see the following CLI command:
            voice signaling channel slot/port/startChannel-endChannel acoustic echo canceller non-linear processor on
            voice signaling channel slot/port/startChannel-endChannel acoustic echo canceller non-linear processor off
        "
        DEFVAL {disabled}
        ::= { vsmSignalingChannelEntry 46 }


        vsmSigChanAcEchoCanSetSpGain OBJECT-TYPE
        SYNTAX INTEGER (0..31)
        ACCESS read-write
        STATUS mandatory
        DESCRIPTION
        "
            This command sets the Handset (HS) specker gain.

        For more information, please see the following CLI command:
            voice signaling channel slot/port/startChannel-endChannel acoustic echo canceller handset speaker gain (0 ... 31)
        "
        DEFVAL {10}
        ::= { vsmSignalingChannelEntry 47 }

        vsmSigChanAcEchoCanFreeSpGain OBJECT-TYPE
        SYNTAX INTEGER (0..31)
        ACCESS read-write
        STATUS mandatory
        DESCRIPTION
        "
        This command sets the Hands Free (HF) specker gain.

        For more information, please see the following CLI command:
            voice signaling channel slot/port/startChannel-endChannel acoustic echo canceller
                   hands free speaker gain (0 ... 31)
        "
        DEFVAL {0}
        ::= { vsmSignalingChannelEntry 48 }


        vsmSigChanAcousticEchoCanOper OBJECT-TYPE
          SYNTAX INTEGER {
                                handset                 (1),
                                handsfree               (2)
                                }
          ACCESS read-write
          STATUS mandatory
          DESCRIPTION
                 "new leaf for 2.2f parser

                 For more information, please see the following CLI command:
                  voice signaling channel slot/port/startChannel-endChannel acoustic echo canceller operation handset
                  voice signaling channel slot/port/startChannel-endChannel acoustic echo canceller operation hands free
                 "
          DEFVAL { handsfree }
          ::= { vsmSignalingChannelEntry 49 }

 
  vsmSigChanFxsLSCadenceCoefficient OBJECT-TYPE
          SYNTAX INTEGER {
                                northAmerica           (1),
                                europe                         (2)
                         }
          ACCESS read-write
          STATUS mandatory
          DESCRIPTION
                 "This command selects the fxs cadence coefficient on this channel.

                 For more information, please see the following CLI command:
                  voice signaling channel slot/port/startChannel-endChannel fxs ls cadence coefficient North America
                  voice signaling channel slot/port/startChannel-endChannel fxs ls cadence coefficient Europe
                 "
          DEFVAL { northAmerica }
          ::= { vsmSignalingChannelEntry 50 }


  vsmSigChanFxsLSRingId OBJECT-TYPE
          SYNTAX INTEGER {
                                default         (1),
                                zero            (2),
                                                                one                     (3),
                                                                two                     (4),
                                                                three           (5),
                                                                four            (6),
                                                                five            (7),
                                                                six                     (8),
                                                                seven           (9)
                         }
          ACCESS read-write
          STATUS mandatory
          DESCRIPTION
                 "This command selects the ring id for the specific fxs cadence 
                                 coefficient on this channel.

                 For more information, please see the following CLI command:
                  voice signaling channel slot/port/startChannel-endChannel fxs ls ring id default
                  voice signaling channel slot/port/startChannel-endChannel fxs ls ring id zero
                  voice signaling channel slot/port/startChannel-endChannel fxs ls ring id one
                  voice signaling channel slot/port/startChannel-endChannel fxs ls ring id two
                  voice signaling channel slot/port/startChannel-endChannel fxs ls ring id three
                  voice signaling channel slot/port/startChannel-endChannel fxs ls ring id four
                  voice signaling channel slot/port/startChannel-endChannel fxs ls ring id five
                  voice signaling channel slot/port/startChannel-endChannel fxs ls ring id six
                  voice signaling channel slot/port/startChannel-endChannel fxs ls ring id seven
                 "
          DEFVAL { default }
          ::= { vsmSignalingChannelEntry 51 }


  vsmSigChanFxsGSCadenceCoefficient OBJECT-TYPE
          SYNTAX INTEGER {
                                northAmerica           (1),
                                europe                         (2)
                         }
          ACCESS read-write
          STATUS mandatory
          DESCRIPTION
                 "This command selects the fxs cadence coefficient on this channel.

                 For more information, please see the following CLI command:
                  voice signaling channel slot/port/startChannel-endChannel fxs gs cadence coefficient North America
                  voice signaling channel slot/port/startChannel-endChannel fxs gs cadence coefficient Europe
                 "
          DEFVAL { northAmerica }
          ::= { vsmSignalingChannelEntry 52 }


  vsmSigChanFxsGSRingId OBJECT-TYPE
          SYNTAX INTEGER {
                                default         (1),
                                zero            (2),
                                                                one                     (3),
                                                                two                     (4),
                                                                three           (5),
                                                                four            (6),
                                                                five            (7),
                                                                six                     (8),
                                                                seven           (9)
                         }
          ACCESS read-write
          STATUS mandatory
          DESCRIPTION
                 "This command selects the ring id for the specific fxs cadence 
                                 coefficient on this channel.

                 For more information, please see the following CLI command:
                  voice signaling channel slot/port/startChannel-endChannel fxs gs ring id default
                  voice signaling channel slot/port/startChannel-endChannel fxs gs ring id zero
                  voice signaling channel slot/port/startChannel-endChannel fxs gs ring id one
                  voice signaling channel slot/port/startChannel-endChannel fxs gs ring id two
                  voice signaling channel slot/port/startChannel-endChannel fxs gs ring id three
                  voice signaling channel slot/port/startChannel-endChannel fxs gs ring id four
                  voice signaling channel slot/port/startChannel-endChannel fxs gs ring id five
                  voice signaling channel slot/port/startChannel-endChannel fxs gs ring id six
                  voice signaling channel slot/port/startChannel-endChannel fxs gs ring id seven
                 "
          DEFVAL { default }
          ::= { vsmSignalingChannelEntry 53 }



--======================================================================
--
-- E&M Common Signaling Channel Table
--
-- This table provides information that is used for all types of E&M
-- signaling.
--
--======================================================================

   vsmSigChanEmCommonTable OBJECT-TYPE
          SYNTAX SEQUENCE OF VsmSigChanEmCommonEntry
          ACCESS not-accessible
          STATUS mandatory
          DESCRIPTION
                  "This table contains information that is used for all
                   E&M type signaling protocols.
                   "

          ::= { vsmSignalingGroup 11 }

   vsmSigChanEmCommonEntry OBJECT-TYPE
           SYNTAX VsmSigChanEmCommonEntry
           ACCESS not-accessible
           STATUS mandatory
           DESCRIPTION
                 "This is an entry in the E&M Common Signaling Table.

                  For more information, please see the following CLI command:
                    [Note: There is NO equivalent command in the CLI.]
                 "
           INDEX {
                        vsmChanSlotIndex,
                        vsmChanPortIndex,
                        vsmChanIndex
                   }
           ::= { vsmSigChanEmCommonTable 1 }

   VsmSigChanEmCommonEntry ::=
          SEQUENCE {
                  vsmSigChanEmCommonOffHookDebounce               INTEGER,
                  vsmSigChanEmCommonOnHookDebounce                INTEGER,
                  vsmSigChanEmCommonSeizeDetect                  INTEGER,
                  vsmSigChanEmCommonClearDetect                   INTEGER,
                  vsmSigChanEmCommonClearConfDetect               INTEGER,
                  vsmSigChanEmCommonClearConfWaitMax      INTEGER,
                  vsmSigChanEmCommonGuardAll                      INTEGER,
                  vsmSigChanEmCommonGuardOut                      INTEGER,
                  vsmSigChanEmCommonDialTone                      VsmEnableDisabled,
                  vsmSigChanEmCommonMinConnectTime                INTEGER,
                  vsmSigChanEmCommonHangUpWait                    INTEGER
          }

  vsmSigChanEmCommonOffHookDebounce OBJECT-TYPE
         SYNTAX INTEGER (5..1000)
--         UNITS "milliseconds"
         ACCESS read-write
         STATUS mandatory
         DESCRIPTION
                "The time, in milliseconds, to allow to de-bounce
                 a transition to an offhook state.

                 For more information, please see the following CLI command:
                 voice signaling channel slot/port/startChannel-endChannel em off hook debounce (5..1000)
                 "
         DEFVAL { 50 }
         ::= { vsmSigChanEmCommonEntry 1 }

  vsmSigChanEmCommonOnHookDebounce OBJECT-TYPE
         SYNTAX INTEGER (5..1000)
--         UNITS "milliseconds"
         ACCESS read-write
         STATUS mandatory
         DESCRIPTION
                "The time, in milliseconds, to allow to de-bounce
                 a transition to an onhook state.

                 For more information, please see the following CLI command:
                 voice signaling channel slot/port/startChannel-endChannel em on hook debounce (5..1000)
                 "
         DEFVAL { 50 }
         ::= { vsmSigChanEmCommonEntry 2 }

  vsmSigChanEmCommonSeizeDetect OBJECT-TYPE
         SYNTAX INTEGER (5..5000)
--         UNITS "milliseconds"
         ACCESS read-write
         STATUS mandatory
         DESCRIPTION
                "The time to wait, in milliseconds, before
                 declaring an off-hook condition after the M-lead has
                 transitioned to the active state.

                 For more information, please see the following CLI command:
                 voice signaling channel slot/port/startChannel-endChannel em seize detect (5..5000)
                 "
         DEFVAL { 150 }
         ::= { vsmSigChanEmCommonEntry 3 }

  vsmSigChanEmCommonClearDetect OBJECT-TYPE
         SYNTAX INTEGER (5..5000)
--         UNITS "milliseconds"
         ACCESS read-write
         STATUS mandatory
         DESCRIPTION
                "The minimum time to wait, in milliseconds,
                 before declaring an on-hook condition after the M-lead
                 transitions to the inactive state and the interface was
                 off-hook.

                 For more information, please see the following CLI command:
                 voice signaling channel slot/port/startChannel-endChannel em clear detect (5..5000)
                 "
          DEFVAL { 400 }
         ::= { vsmSigChanEmCommonEntry 4 }

  vsmSigChanEmCommonClearConfDetect OBJECT-TYPE
         SYNTAX INTEGER (5..5000)
--         UNITS "milliseconds"
         ACCESS read-write
         STATUS mandatory
         DESCRIPTION
                "The amount of time, in milliseconds, that an
                 on-hook must be detected on the M-lead after going on-hook
                 on the E-lead.

                 For more information, please see the following CLI command:
                 voice signaling channel slot/port/startChannel-endChannel em clear confirm detect (5..5000)
                 "
         DEFVAL { 5000 }
         ::= { vsmSigChanEmCommonEntry 5 }

  vsmSigChanEmCommonClearConfWaitMax OBJECT-TYPE
         SYNTAX INTEGER (1..60000)
--         UNITS "seconds "
         ACCESS read-write
         STATUS mandatory
         DESCRIPTION
                 "Defines the maximum time, in seconds, to wait
                  for an on-hook indication following a clearing indication.

                  For more information, please see the following CLI command:
                 voice signaling channel slot/port/startChannel-endChannel em clear confirm wait maximum (1..60000)
                  "
          DEFVAL { 60000 }
         ::= { vsmSigChanEmCommonEntry 6 }

  vsmSigChanEmCommonGuardAll OBJECT-TYPE
         SYNTAX INTEGER (0..60000)
         -- UNITS "milliseconds"
         ACCESS read-write
         STATUS mandatory
         DESCRIPTION
                "The period, in milliseconds, after an aborted
                call when neither no incoming calls will be accepted nor outgoing
                calls initiated. In other words, this is the duration of time that
                the channel is out of service after a call is aborted.

                For more information, please see the following CLI command:
                 voice signaling channel slot/port/startChannel-endChannel em guard all (0..60000)
                "
         DEFVAL { 400 }
         ::= { vsmSigChanEmCommonEntry 7 }

  vsmSigChanEmCommonGuardOut OBJECT-TYPE
         SYNTAX INTEGER (5..60000)
         -- UNITS "milliseconds"
         ACCESS read-write
         STATUS mandatory
         DESCRIPTION
           "This specifies an additional period of time, in milliseconds, after
           guard-all when incoming calls will be accepted but outgoing calls
           will not be initiated for aborted calls.

           For more information, please see the following CLI command:
         voice signaling channel slot/port/startChannel-endChannel em guard out (0..60000)
           "
         DEFVAL { 400 }
         ::= { vsmSigChanEmCommonEntry 8 }

vsmSigChanEmCommonDialTone OBJECT-TYPE
         SYNTAX VsmEnableDisabled
         ACCESS read-write
         STATUS mandatory
         DESCRIPTION
           "Specifies whether dial tone should be generated on
           incoming calls.

           For more information, please see the following CLI command:
         voice signaling channel slot/port/startChannel-endChannel em dial tone on
         voice signaling channel slot/port/startChannel-endChannel em dial tone off
           "
         DEFVAL { enabled }
         ::= { vsmSigChanEmCommonEntry 9 }

vsmSigChanEmCommonMinConnectTime OBJECT-TYPE
         SYNTAX INTEGER (0..20000)
         -- UNITS "milliseconds"
         ACCESS read-write
         STATUS mandatory
         DESCRIPTION
           "The minimum period of time, in milliseconds, that
           a connection will be maintained. If the remote end disconnects during
           this interval, the disconnect will be acknowledged only at the end of
           this time interval.

           For more information, please see the following CLI command:
            voice signaling channel slot/port/startChannel-endChannel em minimum connect time (0..20000)
           "
         DEFVAL { 2000 }
         ::= { vsmSigChanEmCommonEntry 10 }

vsmSigChanEmCommonHangUpWait OBJECT-TYPE
         SYNTAX INTEGER (5..60000)
         -- UNITS "milliseconds"
         ACCESS read-write
         STATUS mandatory
         DESCRIPTION
           "The time period, in milliseconds, a port will wait
           after hanging up a call before signaling that it is in a disabled
           state.

           For more information, please see the following CLI command:
            voice signaling channel slot/port/startChannel-endChannel em hang up wait (5..60000)
           "
         DEFVAL { 2000 }
         ::= { vsmSigChanEmCommonEntry 11 }


--====================================================================
--
-- E&M Delayed Start Signaling Channel Table
--
-- This table provides information for control of E&M delay start
-- signaling.
--
--======================================================================

  vsmSigChanEmDelayTable OBJECT-TYPE
          SYNTAX SEQUENCE OF VsmSigChanEmDelayEntry
          ACCESS not-accessible
          STATUS mandatory
          DESCRIPTION
                 "This table contains entries that specify how to perform
                  E&M Delay signaling on the port indicated
                  "
          ::= { vsmSignalingGroup 12 }

  vsmSigChanEmDelayEntry OBJECT-TYPE
           SYNTAX VsmSigChanEmDelayEntry
           ACCESS not-accessible
           STATUS mandatory
           DESCRIPTION
                 "This is an entry in the E&M Delay Signaling Table.

                  For more information, please see the following CLI command:
                    [Note: There is NO equivalent command in the CLI.]
                 "
           INDEX {
                        vsmChanSlotIndex,
                        vsmChanPortIndex,
                        vsmChanIndex
                        }
           ::= { vsmSigChanEmDelayTable 1 }

  VsmSigChanEmDelayEntry ::=
          SEQUENCE {
                  vsmSigChanEmDelayInDelayDurMin                        INTEGER,
                  vsmSigChanEmDelayInDelayDurMax                        INTEGER,
                  vsmSigChanEmDelayInDigitIgnore                        INTEGER,
                  vsmSigChanEmDelayOutDelayDurMin                       INTEGER,
                  vsmSigChanEmDelayOutDelayDurMax                       INTEGER,
                  vsmSigChanEmDelayOutIntegrityChk                      VsmEnableDisabled,
                  vsmSigChanEmDelayOutDelayChk                          INTEGER
          }


   vsmSigChanEmDelayInDelayDurMin OBJECT-TYPE
          SYNTAX INTEGER (5..60000)
          ACCESS read-write
          STATUS mandatory
          DESCRIPTION
                "The minimum duration, in milliseconds,
                of the delay signal response to the seize detect (of incoming calls)
                on the M-lead.

                For more information, please see the following CLI command:
                 voice signaling channel slot/port/startChannel-endChannel emd in delay minimum (5..60000)
                "
          DEFVAL { 200 }
          ::= { vsmSigChanEmDelayEntry 1 }

   vsmSigChanEmDelayInDelayDurMax OBJECT-TYPE
          SYNTAX INTEGER (5..60000)
          ACCESS read-write
          STATUS mandatory
          DESCRIPTION
                "The maximum duration, in milliseconds, of the delay
                signal response to the Seize Detect (of incoming calls) on the
                M-lead.

                For more information, please see the following CLI command:
                 voice signaling channel slot/port/startChannel-endChannel emd in delay maximum (5..60000)
                "
          DEFVAL { 2500 }
          ::= { vsmSigChanEmDelayEntry 2 }

   vsmSigChanEmDelayInDigitIgnore OBJECT-TYPE
          SYNTAX INTEGER (5..60000)
          ACCESS read-write
          STATUS mandatory
          DESCRIPTION
                "The period of time in milliseconds, after completing
                the delay signal, before the digits will be accepted on incoming
                calls.

                For more information, please see the following CLI command:
                 voice signaling channel slot/port/startChannel-endChannel emd in digit ignore (5..60000)
                "
          DEFVAL { 30 }
          ::= { vsmSigChanEmDelayEntry 3 }

   vsmSigChanEmDelayOutDelayDurMin OBJECT-TYPE
          SYNTAX INTEGER (5..60000)
          ACCESS read-write
          STATUS mandatory
          DESCRIPTION
                "The minimum duration, in milliseconds, of the delay
                signal response on the M-lead for it to be detected on outgoing
                calls.

                For more information, please see the following CLI command:
                 voice signaling channel slot/port/startChannel-endChannel emd out delay duration minimum (5..60000)
                "
          DEFVAL { 100 }
          ::= { vsmSigChanEmDelayEntry 4 }

   vsmSigChanEmDelayOutDelayDurMax OBJECT-TYPE
          SYNTAX INTEGER (5..60000)
          ACCESS read-write
          STATUS mandatory
          DESCRIPTION
                "The maximum duration, in milliseconds, of the delay
                signal response on the M-lead for it to be declared as a glare
                condition by the TSG on outgoing calls.

                For more information, please see the following CLI command:
                 voice signaling channel slot/port/startChannel-endChannel emd out delay duration maximum (5..60000)
                "
          DEFVAL { 8000 }
          ::= { vsmSigChanEmDelayEntry 5 }

   vsmSigChanEmDelayOutIntegrityChk OBJECT-TYPE
          SYNTAX VsmEnableDisabled
          ACCESS read-write
          STATUS mandatory
          DESCRIPTION
                 "Enables or disables the Integrity Check mode.
                 If on, the delay signal response is required from the PBX
                 for outgoing calls. If off, no Integrity check is performed.

                 For more information, please see the following CLI command:
                 voice signaling channel slot/port/startChannel-endChannel emd out integrity check on
                 voice signaling channel slot/port/startChannel-endChannel emd out integrity check off
                 "
          DEFVAL { disabled }
          ::= { vsmSigChanEmDelayEntry 6 }

   vsmSigChanEmDelayOutDelayChk OBJECT-TYPE
          SYNTAX INTEGER (5..60000)
          ACCESS read-write
          STATUS mandatory
          DESCRIPTION
                "The wait period for outgoing calls with the
                Integrity Check set to off; the period of time, in milliseconds,
                after going off-hook on the E-lead before checking the M-lead for
                the delay signal response. If the response is not seen at this time,
                the call setup process will continue immediately.

                For more information, please see the following CLI command:
                 voice signaling channel slot/port/startChannel-endChannel emd out delay check (5..60000)
                "
          DEFVAL { 170 }
          ::= { vsmSigChanEmDelayEntry 7 }

--===================================================================
--
-- E&M Immediate Start Signaling ChannelTable
--
-- This table provides information for control of E&M immediate start
-- signaling.
--
--=======================================================================

   vsmSigChanEmImmedTable OBJECT-TYPE
          SYNTAX SEQUENCE OF VsmSigChanEmImmedEntry
          ACCESS not-accessible
          STATUS mandatory
          DESCRIPTION
                 "This table contains entries that specify how to perform
                  E&M Immediate signaling on the telephone channel.
                  "
          ::= { vsmSignalingGroup 13 }

   vsmSigChanEmImmedEntry OBJECT-TYPE
           SYNTAX VsmSigChanEmImmedEntry
           ACCESS not-accessible
           STATUS mandatory
           DESCRIPTION
                 "This is an entry in the E&M Immediate Signaling Table.

                  For more information, please see the following CLI command:
                    [Note: There is NO equivalent command in the CLI.]
                 "
           INDEX {
                        vsmChanSlotIndex,
                        vsmChanPortIndex,
                        vsmChanIndex
                        }
           ::= { vsmSigChanEmImmedTable 1 }

   VsmSigChanEmImmedEntry ::=
          SEQUENCE {
                  vsmSigChanEmImmedGlareReport  INTEGER,
                  vsmSigChanEmImmedDigitWait            INTEGER
          }


   vsmSigChanEmImmedGlareReport OBJECT-TYPE
          SYNTAX INTEGER (0..60000)
--          UNITS "milliseconds"
          ACCESS read-write
          STATUS mandatory
          DESCRIPTION
                "Specifies, how long, in milliseconds, the interface should remain
                 off hook after detecting a glare condition to indicate congestion.

                 For more information, please see the following CLI command:
                  voice signaling channel slot/port/startChannel-endChannel emi glare report (0..60000)
                 "
          DEFVAL { 5000 }
          ::= { vsmSigChanEmImmedEntry 1 }

   vsmSigChanEmImmedDigitWait OBJECT-TYPE
          SYNTAX INTEGER
--          UNITS "milliseconds"
          ACCESS read-write
          STATUS mandatory
          DESCRIPTION
                "Specifies how long, in milliseconds, to wait before digit
                 collection can be enabled.

                 For more information, please see the following CLI command:
                  voice signaling channel slot/port/startChannel-endChannel emi digit wait (0..60000)
                 "
          DEFVAL { 200 }
          ::= { vsmSigChanEmImmedEntry 2 }


--===================================================================
--
-- E&M Wink Start Signaling Channel Table
--
-- This table provides information for control of E&M wink start
-- signaling.
--
--======================================================================

  vsmSigChanEmWinkTable OBJECT-TYPE
          SYNTAX SEQUENCE OF VsmSigChanEmWinkEntry
          ACCESS not-accessible
          STATUS mandatory
          DESCRIPTION
                 "This table contains entries that specify how to perform
                  E&M Wink signaling on the channel indicated.
                  "
          ::= { vsmSignalingGroup 14 }

  vsmSigChanEmWinkEntry OBJECT-TYPE
           SYNTAX VsmSigChanEmWinkEntry
           ACCESS not-accessible
           STATUS mandatory
           DESCRIPTION
                 "This is an entry in the E&M Wink Signaling Table.

                  For more information, please see the following CLI command:
                    [Note: There is NO equivalent command in the CLI.]
                 "
           INDEX {
                        vsmChanSlotIndex,
                        vsmChanPortIndex,
                        vsmChanIndex
                        }
           ::= { vsmSigChanEmWinkTable 1 }

  VsmSigChanEmWinkEntry ::=
          SEQUENCE {
                  vsmSigChanEmWinkInWinkWaitMin    INTEGER,
                  vsmSigChanEmWinkInWinkWaitMax    INTEGER,
                  vsmSigChanEmWinkInWinkDur                INTEGER,
                  vsmSigChanEmWinkInDigitIgnore    INTEGER,
                  vsmSigChanEmWinkOutWinkWaitMax   INTEGER,
                  vsmSigChanEmWinkOutWinkDurMin    INTEGER,
                  vsmSigChanEmWinkOutWinkDurMax    INTEGER
          }


   vsmSigChanEmWinkInWinkWaitMin OBJECT-TYPE
          SYNTAX INTEGER (5..60000)
--          UNITS "milliseconds"
          ACCESS read-write
          STATUS mandatory
          DESCRIPTION
                 "Specifies the minimum delay, in milliseconds,
                  before beginning the wink on the E-lead after detecting a
                  line seizure on the M-lead during an incoming call.

                  For more information, please see the following CLI command:
                     voice signaling channel slot/port/startChannel-endChannel emw in wink wait minimum (5..60000)
                  "
          DEFVAL { 150 }
          ::= { vsmSigChanEmWinkEntry 1 }

   vsmSigChanEmWinkInWinkWaitMax OBJECT-TYPE
          SYNTAX INTEGER (5..60000)
--          UNITS "milliseconds"
          ACCESS read-write
          STATUS mandatory
          DESCRIPTION
                 "Specifies the maximum delay, in milliseconds,
                  before beginning the wink on the E-lead after detecting a
                  line seizure on the M-lead during an incoming call.

                  For more information, please see the following CLI command:
                     voice signaling channel slot/port/startChannel-endChannel emw in wink wait maximum (5..60000)
                  "
          DEFVAL { 290 }
          ::= { vsmSigChanEmWinkEntry 2 }

   vsmSigChanEmWinkInWinkDur OBJECT-TYPE
          SYNTAX INTEGER (5..60000)
--          UNITS "milliseconds"
          ACCESS read-write
          STATUS mandatory
          DESCRIPTION
                 "Specifies the duration of the wink signal on the E-lead
                 for incoming calls.

                 For more information, please see the following CLI command:
                    voice signaling channel slot/port/startChannel-endChannel emw in wink duration (5..60000)
                 "
          DEFVAL { 200 }
          ::= { vsmSigChanEmWinkEntry 3 }

   vsmSigChanEmWinkInDigitIgnore OBJECT-TYPE
          SYNTAX INTEGER (5..1000)
--          UNITS "milliseconds"
          ACCESS read-write
          STATUS mandatory
          DESCRIPTION
                 "Specifies how long in milliseconds, after
                  generating the wink signal on the E-lead, incoming digits
                  will be ignored.

                  For more information, please see the following CLI command:
                     voice signaling channel slot/port/startChannel-endChannel emw in wink digit ignore (5..1000)
                  "
          DEFVAL { 30 }
          ::= { vsmSigChanEmWinkEntry 4 }

   vsmSigChanEmWinkOutWinkWaitMax OBJECT-TYPE
          SYNTAX INTEGER (5..60000)
--          UNITS "milliseconds"
          ACCESS read-write
          STATUS mandatory
          DESCRIPTION
                "Specifies the time, in milliseconds, to wait
                to detect a wink of the M-lead after seizure of the E-lead
                during an outgoing call. If the wink signal is not
                received within this time period, it is considered an
                error and the call will not connect.

                For more information, please see the following CLI command:
                 voice signaling channel slot/port/startChannel-endChannel emw out wink wait maximum (5..60000)
                "
          DEFVAL { 8000 }
          ::= { vsmSigChanEmWinkEntry 5 }

   vsmSigChanEmWinkOutWinkDurMin OBJECT-TYPE
          SYNTAX INTEGER (5..60000)
--          UNITS "milliseconds"
          ACCESS read-write
          STATUS mandatory
          DESCRIPTION
                 "Specifies the minimum duration, in milliseconds,
                  of the wink on the M-lead during the processing of an
                  outgoing call.

                  For more information, please see the following CLI command:
                     voice signaling channel slot/port/startChannel-endChannel emw out wink duration minimum (5..60000)
                  "
          DEFVAL { 100 }
          ::= { vsmSigChanEmWinkEntry 6 }

   vsmSigChanEmWinkOutWinkDurMax OBJECT-TYPE
          SYNTAX INTEGER (5..60000)
--          UNITS "milliseconds"
          ACCESS read-write
          STATUS mandatory
          DESCRIPTION
                 "Specifies the maximum duration of the wink response on
                 the M-lead before it is to be declared as a glare condition for
                 outgoing calls. A glare condition occurs when both ends of a
                 channel are seized at the same time.  This command reduces the
                 chance of deadlock.

                 For more information, please see the following CLI command:
                 voice signaling channel slot/port/startChannel-endChannel emw out wink duration maximum (5..60000)
                 "
          DEFVAL { 800 }
          ::= { vsmSigChanEmWinkEntry 7 }

--======================================================================
--
-- Foreign Exchange Office (Fxo) Ground Start
-- Signaling Channel Table
--
-- This table provides information for control of FXO ground start
-- signaling.
--
--======================================================================

  vsmSigChanFxoGSTable OBJECT-TYPE
          SYNTAX SEQUENCE OF VsmSigChanFxoGSEntry
          ACCESS not-accessible
          STATUS mandatory
          DESCRIPTION
                 "This table contains entries that specify how to perform
                  Foreign Exchange Office (FXO) gorund start signaling on the
                  port indicated.
                  "
          ::= { vsmSignalingGroup 15 }

  vsmSigChanFxoGSEntry OBJECT-TYPE
           SYNTAX VsmSigChanFxoGSEntry
           ACCESS not-accessible
           STATUS mandatory
           DESCRIPTION
                 "This is an entry in the FXO ground start Signaling Table.

                  For more information, please see the following CLI command:
                    [Note: There is NO equivalent command in the CLI.]
                 "
           INDEX {
                        vsmChanSlotIndex,
                        vsmChanPortIndex,
                        vsmChanIndex
                        }
           ::= { vsmSigChanFxoGSTable 1 }

  VsmSigChanFxoGSEntry ::=
          SEQUENCE {
                vsmSigChanFxoGSConnectionLoopOpenDebounce                       INTEGER,
                vsmSigChanFxoGSMaxTipGroundWait                                 INTEGER,
                vsmSigChanFxoGSTipGroundDebounce                                INTEGER,
                vsmSigChanFxoGSRingingDebounce                                  INTEGER,
                vsmSigChanFxoGSRingingInterCycle                                INTEGER,
                vsmSigChanFxoGSRingingInterPulse                                INTEGER,
                vsmSigChanFxoGSCallerIdDetect                                   VsmEnableDisabled,
                vsmSigChanFxoGSAnswerAfterRings                                 INTEGER,
                vsmSigChanFxoGSLoopCurrentDebounce                              INTEGER,
                vsmSigChanFxoGSBattReversalDebounce                             INTEGER
                }

vsmSigChanFxoGSConnectionLoopOpenDebounce OBJECT-TYPE
          SYNTAX INTEGER (1..6000)
--          UNITS "milliseconds"
          ACCESS read-write
          STATUS mandatory
          DESCRIPTION
                "Debounce interval for loop open detection for an existing
                conection.

                For more information, please see the following CLI command:
                 voice signaling channel slot/port/startChannel-endChannel fxo gs connection loop open debounce (1..60000)
                "
          DEFVAL { 150 }
        ::= { vsmSigChanFxoGSEntry 1 }

vsmSigChanFxoGSMaxTipGroundWait OBJECT-TYPE
          SYNTAX INTEGER (1..60000)
--          UNITS "milliseconds"
          ACCESS read-write
          STATUS mandatory
          DESCRIPTION
                "Maximum time the interface will wait after ring ground is asserted
                                for a tip ground receive.
                For more information, please see the following CLI command:
                 voice signaling channel slot/port/startChannel-endChannel fxo gs maximum tip ground wait (1..60000)
                "
          DEFVAL { 30 }
        ::= { vsmSigChanFxoGSEntry 2 }

vsmSigChanFxoGSTipGroundDebounce OBJECT-TYPE
          SYNTAX INTEGER (1..1000)
--          UNITS "milliseconds"
          ACCESS read-write
          STATUS mandatory
          DESCRIPTION
                "Time, in milliseconds, to be used as a de-bouncer interval for debouncing
                the tip ground detector.

                For more information, please see the following CLI command:
                 voice signaling channel slot/port/startChannel-endChannel fxo gs tip ground debounce (1..1000)
                "
          DEFVAL { 20 }
        ::= { vsmSigChanFxoGSEntry 3 }

vsmSigChanFxoGSRingingDebounce OBJECT-TYPE
          SYNTAX INTEGER (1..1000)
--          UNITS "milliseconds"
          ACCESS read-write
          STATUS mandatory
          DESCRIPTION
                "When a ring signal is modulated by the ringing frequency,
                the debouncer is used to debounce the incoming ring signal.

                For more information, please see the following CLI command:
                 voice signaling channel slot/port/startChannel-endChannel fxo gs ringing debounce (1..1000)
                "
          DEFVAL { 20 }
        ::= { vsmSigChanFxoGSEntry 4 }

vsmSigChanFxoGSRingingInterCycle OBJECT-TYPE
          SYNTAX INTEGER (1..60000)
--          UNITS "milliseconds"
          ACCESS read-write
          STATUS mandatory
          DESCRIPTION
                "Specifies the time between consecutive ring cycles,
                in milliseconds. It is used to detect ringing.

                For more information, please see the following CLI command:
                voice signaling channel slot/port/startChannel-endChannel fxo gs ringing inter cycle (1..60000)

                "
          DEFVAL { 5000 }
          ::= { vsmSigChanFxoGSEntry 5 }

vsmSigChanFxoGSRingingInterPulse OBJECT-TYPE
          SYNTAX INTEGER (1..60000)
--          UNITS "milliseconds"
          ACCESS read-write
          STATUS mandatory
          DESCRIPTION
                "Specifies the time between consecutive
                ring pulses in the same ring cycle, in milliseconds. It is used
                to detect ringing.

                For more information, please see the following CLI command:
                 voice signaling channel slot/port/startChannel-endChannel fxo gs ringing inter pulse (1..60000)

                "
          DEFVAL { 550 }
          ::= { vsmSigChanFxoGSEntry 6 }

vsmSigChanFxoGSCallerIdDetect OBJECT-TYPE
          SYNTAX VsmEnableDisabled
          ACCESS read-write
          STATUS mandatory
          DESCRIPTION
                "If enabled, Caller ID will be detected.

                For more information, please see the following CLI command:
                 voice signaling channel slot/port/startChannel-endChannel fxo gs caller id detection on
                 voice signaling channel slot/port/startChannel-endChannel fxo gs caller id detection off
                "
          DEFVAL { disabled }
          ::= { vsmSigChanFxoGSEntry 7 }

vsmSigChanFxoGSAnswerAfterRings OBJECT-TYPE
          SYNTAX INTEGER (1..65535)
          ACCESS read-write
          STATUS mandatory
          DESCRIPTION
                "Specifies the number of rings to elapse before answering an
                 incoming call.

                 For more information, please see the following CLI command:
                  voice signaling channel slot/port/startChannel-endChannel fxo gs answer after (1..65535)
                 "
          DEFVAL { 2 }
          ::= { vsmSigChanFxoGSEntry 8 }

vsmSigChanFxoGSLoopCurrentDebounce OBJECT-TYPE
          SYNTAX INTEGER (0..1000)
--          UNITS "milliseconds"
          ACCESS read-write
          STATUS mandatory
          DESCRIPTION
                "Time, in milliseconds, to use as a de-bouncer interval for debouncing
                 the loop current detector.

                 For more information, please see the following CLI command:
                  voice signaling channel slot/port/startChannel-endChannel fxo gs loop current debounce (0..1000)
                "
          DEFVAL { 20 }
          ::= { vsmSigChanFxoGSEntry 9 }

vsmSigChanFxoGSBattReversalDebounce OBJECT-TYPE
          SYNTAX INTEGER (1..1000)
--          UNITS "milliseconds"
          ACCESS read-write
          STATUS mandatory
          DESCRIPTION
                "Time, in milliseconds, to use as a de-bouncer interval for debouncing
                 the battery reversal detector.

                 For more information, please see the following CLI command:
                  voice signaling channel slot/port/startChannel-endChannel fxo gs battery reversal debounce (1..1000)
                 "
          DEFVAL { 20 }
          ::= { vsmSigChanFxoGSEntry 10 }


--======================================================================
--
-- Foreign Exchange Office (Fxo) Loop Start
-- Signaling Channel Table
--
-- This table provides information for control of FXO loop start
-- signaling.
--
--======================================================================

  vsmSigChanFxoLSTable OBJECT-TYPE
          SYNTAX SEQUENCE OF VsmSigChanFxoLSEntry
          ACCESS not-accessible
          STATUS mandatory
          DESCRIPTION
                 "This table contains entries that specify how to perform
                  Foreign Exchange Office (FXO) Loop start signaling on the
                  port indicated.
                  "
          ::= { vsmSignalingGroup 16 }

  vsmSigChanFxoLSEntry OBJECT-TYPE
           SYNTAX VsmSigChanFxoLSEntry
           ACCESS not-accessible
           STATUS mandatory
           DESCRIPTION
                 "This is an entry in the FXO Loop start Signaling Table.

                  For more information, please see the following CLI command:
                    [Note: There is NO equivalent command in the CLI.]
                 "
           INDEX {
                        vsmChanSlotIndex,
                        vsmChanPortIndex,
                        vsmChanIndex
                        }
           ::= { vsmSigChanFxoLSTable 1 }

  VsmSigChanFxoLSEntry ::=
          SEQUENCE {
                vsmSigChanFxoLSRingingDebounce                  INTEGER,
                vsmSigChanFxoLSCPCDetectCtrl                    VsmEnableDisabled,
                vsmSigChanFxoLSCPCDetectDur                             INTEGER,
                vsmSigChanFxoLSGuardOut                                 INTEGER,
                vsmSigChanFxoLSRingingInterCycle                INTEGER,
                vsmSigChanFxoLSRingingInterPulse                INTEGER,
                vsmSigChanFxoLSCallerIdDetect                   VsmEnableDisabled,
                vsmSigChanFxoLSAnswerAfterRings                 INTEGER,
                vsmSigChanFxoLSLoopCurrentDebounce              INTEGER,
                vsmSigChanFxoLSBattReversalDebounce             INTEGER
                }

vsmSigChanFxoLSRingingDebounce OBJECT-TYPE
          SYNTAX INTEGER (1..1000)
--          UNITS "milliseconds"
          ACCESS read-write
          STATUS mandatory
          DESCRIPTION
                "When a ring signal is modulated by the ringing frequency,
                the debouncer is used to debounce the incoming ring signal.

                For more information, please see the following CLI command:
                 voice signaling channel slot/port/startChannel-endChannel fxo ls ringing debounce (1..1000)
                "
          DEFVAL { 50 }
::= { vsmSigChanFxoLSEntry 1 }

vsmSigChanFxoLSCPCDetectCtrl OBJECT-TYPE
          SYNTAX VsmEnableDisabled
          ACCESS read-write
          STATUS mandatory
          DESCRIPTION
                "This command is used to enable or disable detection of a
                CPC (supervisory disconnect) signal  (vsmSigChanFxoLSCPCDetectDur)..

                For more information, please see the following CLI command:
                 voice signaling channel slot/port/startChannel-endChannel fxo ls supervisory disconnect detection on
                 voice signaling channel slot/port/startChannel-endChannel fxo ls supervisory disconnect detection off
                "
          DEFVAL { enabled }
::= { vsmSigChanFxoLSEntry 2 }

vsmSigChanFxoLSCPCDetectDur OBJECT-TYPE
          SYNTAX INTEGER (1..60000)
--          UNITS "milliseconds"
          ACCESS read-write
          STATUS mandatory
          DESCRIPTION
                "The expected duration of the CPC (supervisory disconnect) signal
                in milliseconds. If the loop current drops for a time period
                shorter than indicated, it is not regarded as a supervisory
                disconnect.  This object is only valid if
                vsmSigChanFxoLSCPCDetectCtrl is enabled.

                For more information, please see the following CLI command:
                 voice signaling channel slot/port/startChannel-endChannel fxo ls supervisory disconnect detect (1..60000 )
                "
          DEFVAL { 600 }
          ::= { vsmSigChanFxoLSEntry 3 }

vsmSigChanFxoLSGuardOut OBJECT-TYPE
          SYNTAX INTEGER (1..60000)
--          UNITS "milliseconds"
          ACCESS read-write
          STATUS mandatory
          DESCRIPTION
                "After the call, the period of time where the channel
                 does not originate a call, but will receive a call.

                 For more information, please see the following CLI command:
                  voice signaling channel slot/port/startChannel-endChannel fxo ls guard out (1..60000)
                 "
          DEFVAL { 2000 }
          ::= { vsmSigChanFxoLSEntry 4 }

vsmSigChanFxoLSRingingInterCycle OBJECT-TYPE
          SYNTAX INTEGER (1..60000)
--          UNITS "milliseconds"
          ACCESS read-write
          STATUS mandatory
          DESCRIPTION
                "The time between ring cycles (ringing pulse plus time between
                ring pulses) in milliseconds. It is used to detect ringing.

                For more information, please see the following CLI command:
                 voice signaling channel slot/port/startChannel-endChannel fxo ls ringing inter cycle (1..60000)
                "
          DEFVAL { 5000 }
          ::= { vsmSigChanFxoLSEntry 5 }

vsmSigChanFxoLSRingingInterPulse OBJECT-TYPE
          SYNTAX INTEGER (1..60000)
--          UNITS "milliseconds"
          ACCESS read-write
          STATUS mandatory
          DESCRIPTION
                "The time between ring pulses in milliseconds. It is used
                to detect ringing.

                For more information, please see the following CLI command:
                 voice signaling channel slot/port/startChannel-endChannel fxo ls ringing inter pulse (1..60000)
                "
          DEFVAL { 550 }
          ::= { vsmSigChanFxoLSEntry 6 }

vsmSigChanFxoLSCallerIdDetect OBJECT-TYPE
          SYNTAX VsmEnableDisabled
          ACCESS read-write
          STATUS mandatory
          DESCRIPTION
                "If enabled, Caller ID will be detected.

                For more information, please see the following CLI command:
                 voice signaling channel slot/port/startChannel-endChannel fxo ls caller id detection on
                 voice signaling channel slot/port/startChannel-endChannel fxo ls caller id detection off
                "
          DEFVAL { enabled }
          ::= { vsmSigChanFxoLSEntry 7 }

vsmSigChanFxoLSAnswerAfterRings OBJECT-TYPE
          SYNTAX INTEGER (1..65535)
          ACCESS read-write
          STATUS mandatory
          DESCRIPTION
                "Specifies the number of rings to elapse before answering an
                 incoming call.

                 For more information, please see the following CLI command:
                  voice signaling channel slot/port/startChannel-endChannel fxo ls answer after (1..65535)
                 "
          DEFVAL { 2 }
          ::= { vsmSigChanFxoLSEntry 8 }

vsmSigChanFxoLSLoopCurrentDebounce OBJECT-TYPE
          SYNTAX INTEGER (1..6000)
--          UNITS "milliseconds"
          ACCESS read-write
          STATUS mandatory
          DESCRIPTION
                "Time, in milliseconds, to use as a de-bouncer interval for debouncing
                 the loop current detector.

                 For more information, please see the following CLI command:
                  voice signaling channel slot/port/startChannel-endChannel fxo ls loop current debounce (0..60000)
                 "
          DEFVAL { 20 }
          ::= { vsmSigChanFxoLSEntry 9 }

vsmSigChanFxoLSBattReversalDebounce OBJECT-TYPE
          SYNTAX INTEGER (0..60000)
--          UNITS "milliseconds"
          ACCESS read-write
          STATUS mandatory
          DESCRIPTION
                "Time, in milliseconds, to use as a de-bouncer interval for debouncing
                 the battery reversal detector.

                 For more information, please see the following CLI command:
                  voice signaling channel slot/port/startChannel-endChannel fxo ls battery reversal debounce (0..60000)
                 "
          DEFVAL { 20 }
          ::= { vsmSigChanFxoLSEntry 10 }


--===================================================================
--
-- Foreign Exchange Station (Fxs) Ground Start
-- Signaling Channel Table
--
-- This table provides information for control of FXS ground start
-- signaling.
--
--======================================================================

  vsmSigChanFxsGSTable OBJECT-TYPE
          SYNTAX SEQUENCE OF VsmSigChanFxsGSEntry
          ACCESS not-accessible
          STATUS mandatory
          DESCRIPTION
                 "This table contains entries that specify how to perform
                  Foreign Exchange Station (FXS) ground start signaling on
                  the port indicated
                  "
          ::= { vsmSignalingGroup 17 }

  vsmSigChanFxsGSEntry OBJECT-TYPE
           SYNTAX VsmSigChanFxsGSEntry
           ACCESS not-accessible
           STATUS mandatory
           DESCRIPTION
                 "This is an entry in the FXS ground start signaling Table.

                  For more information, please see the following CLI command:
                    [Note: There is NO equivalent command in the CLI.]
                 "
           INDEX {
                        vsmChanSlotIndex,
                        vsmChanPortIndex,
                        vsmChanIndex
                        }
           ::= { vsmSigChanFxsGSTable 1 }

  VsmSigChanFxsGSEntry ::=
          SEQUENCE {
                vsmSigChanFxsGSSeizeDetect                      INTEGER,
                vsmSigChanFxsGSOnHookDebounce           INTEGER,
                vsmSigChanFxsGSOrigClearDetect          INTEGER,
                vsmSigChanFxsGSAnswClearDetect          INTEGER,
                vsmSigChanFxsGSMinRingGround            INTEGER,
                vsmSigChanFxsGSMaxWaitLoop                      INTEGER,
                vsmSigChanFxsGSMinLoopOpen                      INTEGER,
                vsmSigChanFxsGSGenerateCallerId         VsmEnableDisabled,
                vsmSigChanFxsGSOffHookDebounce          INTEGER,
                vsmSigChanFxsGSRingGroundDebounce       INTEGER
                   }

vsmSigChanFxsGSSeizeDetect OBJECT-TYPE
           SYNTAX INTEGER (1..5000)
 --          UNITS      "milliseconds"
           ACCESS  read-write
           STATUS  mandatory
           DESCRIPTION
                "The time to wait before an off-hook condition is declared.

                For more information, please see the following CLI command:
                 voice signaling channel slot/port/startChannel-endChannel fxs gs seize detect (1..5000)

                "
           DEFVAL { 150 }
           ::= { vsmSigChanFxsGSEntry 1 }

vsmSigChanFxsGSOnHookDebounce OBJECT-TYPE
           SYNTAX INTEGER (1..1000)
 --          UNITS      "milliseconds"
           ACCESS  read-write
           STATUS mandatory
           DESCRIPTION
                "Debounce interval to onhook transition.

                For more information, please see the following CLI command:
                 voice signaling channel slot/port/startChannel-endChannel fxs gs on hook debounce (1..1000)
                "
           DEFVAL { 20 }
           ::= { vsmSigChanFxsGSEntry 2 }

vsmSigChanFxsGSOrigClearDetect OBJECT-TYPE
           SYNTAX INTEGER (1..60000)
 --          UNITS      "milliseconds"
           ACCESS  read-write
           STATUS mandatory
           DESCRIPTION
                "The minimum time to wait if the originator drops the
                line before declaring onhook.

                For more information, please see the following CLI command:
                 voice signaling channel slot/port/startChannel-endChannel fxs gs originate clear detect (1..60000)
                "
           DEFVAL { 200 }
           ::= { vsmSigChanFxsGSEntry 3 }

vsmSigChanFxsGSAnswClearDetect OBJECT-TYPE
           SYNTAX INTEGER (1..60000)
 --          UNITS      "milliseconds"
           ACCESS  read-write
           STATUS mandatory
           DESCRIPTION
                "Minimum time to wait when the answering party drops the
                line before declaring onhook.

                For more information, please see the following CLI command:
                 voice signaling channel slot/port/startChannel-endChannel fxs gs answer clear detect (1..60000)
                "
           DEFVAL { 100 }
           ::= { vsmSigChanFxsGSEntry 4 }

vsmSigChanFxsGSMinRingGround OBJECT-TYPE
           SYNTAX INTEGER (0..65535)
 --          UNITS      "milliseconds"
           ACCESS  read-write
           STATUS mandatory
           DESCRIPTION
                "The minimum time for the ring lead to be grounded before
                                it is considered a valid seizure
                For more information, please see the following CLI command:
                 voice signaling channel slot/port/startChannel-endChannel fxs gs minimum ring ground (0..65535)
                "
           DEFVAL { 100 }
           ::= { vsmSigChanFxsGSEntry 5 }

vsmSigChanFxsGSMaxWaitLoop OBJECT-TYPE
           SYNTAX INTEGER (0..65535)
 --          UNITS      "milliseconds"
           ACCESS  read-write
           STATUS mandatory
           DESCRIPTION
                "Specifies the maximum time to allow for the loop to close,
                after a ring ground is detected and the tip is grounded, before
                the interface will disconnect.

                For more information, please see the following CLI command:
                 voice signaling channel slot/port/startChannel-endChannel fxs gs maximum wait loop (0..65535)
                "
           DEFVAL { 100 }
           ::= { vsmSigChanFxsGSEntry 6 }

vsmSigChanFxsGSMinLoopOpen OBJECT-TYPE
           SYNTAX INTEGER (0..65535)
 --          UNITS      "milliseconds"
           ACCESS  read-write
           STATUS mandatory
           DESCRIPTION
                "Specifies the minimum time the interface
                waits after detecting an open loop condition, before returning
                to an idle state.

                For more information, please see the following CLI command:
                 voice signaling channel slot/port/startChannel-endChannel fxs gs minimum loop open (0..65535)
                "
           DEFVAL { 100 }
           ::= { vsmSigChanFxsGSEntry 7 }

vsmSigChanFxsGSGenerateCallerId OBJECT-TYPE
           SYNTAX VsmEnableDisabled
           ACCESS  read-write
           STATUS mandatory
           DESCRIPTION
                "If enabled, Caller ID will be generated.

                For more information, please see the following CLI command:
                 voice signaling channel slot/port/startChannel-endChannel fxs gs generate caller id on
                 voice signaling channel slot/port/startChannel-endChannel fxs gs generate caller id off
                "
           DEFVAL { disabled }
           ::= { vsmSigChanFxsGSEntry 8 }

vsmSigChanFxsGSOffHookDebounce OBJECT-TYPE
           SYNTAX INTEGER (1..1000)
 --          UNITS      "milliseconds"
           ACCESS  read-write
           STATUS mandatory
           DESCRIPTION
                "Specifies the time, in milliseconds, to be used as de-bouncer
                interval for off-hook transition.

                For more information, please see the following CLI command:
                 voice signaling channel slot/port/startChannel-endChannel fxs gs off hook debounce (1..1000)
                "
           DEFVAL { 20 }
           ::= { vsmSigChanFxsGSEntry 9 }

vsmSigChanFxsGSRingGroundDebounce OBJECT-TYPE
           SYNTAX INTEGER (1..1000)
 --          UNITS      "milliseconds"
           ACCESS  read-write
           STATUS mandatory
           DESCRIPTION
                "Time, in milliseconds, to be used as de-bouncer interval for debouncing
                the ring ground detector.

                For more information, please see the following CLI command:
                 voice signaling channel slot/port/startChannel-endChannel fxs gs ring ground debounce (1..1000)
                "
           DEFVAL { 20 }
           ::= { vsmSigChanFxsGSEntry 10 }


--===================================================================
--
-- Foreign Exchange Station (Fxs) Loop Start
-- Signaling Channel Table
--
-- This table provides information for control of FXS loop start
-- signaling.
--
--======================================================================

  vsmSigChanFxsLSTable OBJECT-TYPE
          SYNTAX SEQUENCE OF VsmSigChanFxsLSEntry
          ACCESS not-accessible
          STATUS mandatory
          DESCRIPTION
                 "This table contains entries that specify how to perform
                  FXS Loop signaling on the port indicated
                  "
          ::= { vsmSignalingGroup 18 }

  vsmSigChanFxsLSEntry OBJECT-TYPE
           SYNTAX VsmSigChanFxsLSEntry
           ACCESS not-accessible
           STATUS mandatory
           DESCRIPTION
                 "This is an entry in the FXS Loop Signaling Table.

                  For more information, please see the following CLI command:
                    [Note: There is NO equivalent command in the CLI.]
                 "
           INDEX {
                        vsmChanSlotIndex,
                        vsmChanPortIndex,
                        vsmChanIndex
                         }
           ::= { vsmSigChanFxsLSTable 1 }

  VsmSigChanFxsLSEntry ::=
          SEQUENCE {
                vsmSigChanFxsLSOffHookDebounce          INTEGER,
                vsmSigChanFxsLSOnHookDebounce           INTEGER,
                vsmSigChanFxsLSSeizeDetect                      INTEGER,
                vsmSigChanFxsLSOrigClearDetect          INTEGER,
                vsmSigChanFxsLSAnswClearDetect          INTEGER,
                vsmSigChanFxsLSCPCWait                          INTEGER,
                vsmSigChanFxsLSCPCDur                           INTEGER,
                vsmSigChanFxsLSGenerateCallerId         VsmEnableDisabled
                   }

vsmSigChanFxsLSOffHookDebounce OBJECT-TYPE
           SYNTAX INTEGER (1..1000)
 --          UNITS      "milliseconds"
           ACCESS  read-write
           STATUS mandatory
           DESCRIPTION
                "Debounce interval to offhook transition.

                For more information, please see the following CLI command:
                 voice signaling channel slot/port/startChannel-endChannel fxs ls off hook debounce (1..1000)
                "
           DEFVAL { 20 }
           ::= { vsmSigChanFxsLSEntry 1 }

vsmSigChanFxsLSOnHookDebounce OBJECT-TYPE
           SYNTAX INTEGER (1..1000)
 --          UNITS      "milliseconds"
           ACCESS  read-write
           STATUS mandatory
           DESCRIPTION
                "Debounce interval to onhook transition.

                For more information, please see the following CLI command:
                 voice signaling channel slot/port/startChannel-endChannel fxs ls on hook debounce (1..1000)
                "
           DEFVAL { 20 }
           ::= { vsmSigChanFxsLSEntry 2 }

vsmSigChanFxsLSSeizeDetect OBJECT-TYPE
           SYNTAX INTEGER (1..5000)
 --          UNITS      "milliseconds"
           ACCESS  read-write
           STATUS  mandatory
           DESCRIPTION
                "The time to wait before an off-hook condition is declared.

                For more information, please see the following CLI command:
                 voice signaling channel slot/port/startChannel-endChannel fxs ls seize detect (1..5000)
                "
           DEFVAL { 150 }
           ::= { vsmSigChanFxsLSEntry 3 }

vsmSigChanFxsLSOrigClearDetect OBJECT-TYPE
           SYNTAX INTEGER (1..1000)
 --          UNITS      "milliseconds"
           ACCESS  read-write
           STATUS mandatory
           DESCRIPTION
                "The minimum time to wait if the originator drops the
                line before declaring onhook.

                For more information, please see the following CLI command:
                 voice signaling channel slot/port/startChannel-endChannel fxs ls originate clear detect (1..1000)
                "
           DEFVAL { 300 }
           ::= { vsmSigChanFxsLSEntry 4 }

vsmSigChanFxsLSAnswClearDetect OBJECT-TYPE
           SYNTAX INTEGER (1..60000)
 --          UNITS      "milliseconds"
           ACCESS  read-write
           STATUS mandatory
           DESCRIPTION
                "Minimum time to wait when the answering party drops the
                line before declaring onhook.

                For more information, please see the following CLI command:
                 voice signaling channel slot/port/startChannel-endChannel fxs ls answer clear detect (1..60000)
                "
           DEFVAL { 300 }
           ::= { vsmSigChanFxsLSEntry 5 }

vsmSigChanFxsLSCPCWait OBJECT-TYPE
           SYNTAX INTEGER (1..60000)
 --          UNITS      "milliseconds"
           ACCESS  read-write
           STATUS mandatory
           DESCRIPTION
                "Time to wait after a Supervisory Disconnect (CPC) signal
                 is received before declaring on hook.

                 For more information, please see the following CLI command:
                  voice signaling channel slot/port/startChannel-endChannel fxs ls supervisory disconnect wait (1..60000)
                 "
           DEFVAL { 200 }
           ::= { vsmSigChanFxsLSEntry 6 }

vsmSigChanFxsLSCPCDur OBJECT-TYPE
           SYNTAX INTEGER (0..60000)
 --          UNITS      "milliseconds"
           ACCESS  read-write
           STATUS mandatory
           DESCRIPTION
                "If zero, then do not generate Supervisory Disconnect (CPC).

                For more information, please see the following CLI command:
                 voice signaling channel slot/port/startChannel-endChannel fxs ls supervisory disconnect duration (1..60000)
                "
           DEFVAL { 850 }
           ::= { vsmSigChanFxsLSEntry 7 }

vsmSigChanFxsLSGenerateCallerId OBJECT-TYPE
           SYNTAX VsmEnableDisabled
           ACCESS  read-write
           STATUS mandatory
           DESCRIPTION
                "If enabled, Caller ID will be generated.

                For more information, please see the following CLI command:
                 voice signaling channel slot/port/startChannel-endChannel fxs ls generate caller id on
                 voice signaling channel slot/port/startChannel-endChannel fxs ls generate caller id off
                "
           DEFVAL { enabled }
           ::= { vsmSigChanFxsLSEntry 8 }


--======================================================================
--==
--== vsmCodingProfileTable
--==
--== This table contains system wide coding profile information.
--==
--======================================================================
--== Note: vsmCodingProfileGroup OBJECT IDENTIFIER ::= { xylanVsmArch 3 }
--======================================================================

        vsmCodingProfileTable OBJECT-TYPE
                SYNTAX SEQUENCE OF VsmCodingProfEntry
                ACCESS not-accessible
                STATUS mandatory
                DESCRIPTION
                        "This table contains information for each coding profile.
                        "
                ::= { vsmCodingProfileGroup 1 }

        vsmCodingProfEntry OBJECT-TYPE
                SYNTAX VsmCodingProfEntry
                ACCESS not-accessible
                STATUS mandatory
                DESCRIPTION
                        "This is an entry in the vsmCodingProfileTable.

                  For more information, please see the following CLI command:
                    [Note: There is NO equivalent command in the CLI.]
                        "
                INDEX { vsmCodingProfName }
                ::= { vsmCodingProfileTable 1 }

        VsmCodingProfEntry ::=
                SEQUENCE {
                        vsmCodingProfId                                 INTEGER,
                        vsmCodingProfName                               DisplayString,
                        vsmCodingProfCallerId                   VsmEnableDisabled,
                        vsmCodingProfCodingType                 VsmVoiceCodingType,
                        vsmCodingProfPktInterval                INTEGER,
                        vsmCodingProfVIF                                INTEGER,
                        vsmCodingProfNetBufMode                 INTEGER,
                        vsmCodingProfNetBufNomDelay             INTEGER,
                        vsmCodingProfNetBufMaxDelay             INTEGER,
                        vsmCodingProfDtmfRelay                  VsmEnableDisabled,
                        vsmCodingProfVAD                        VsmEnableDisabled,
                        vsmCodingProfEC                         VsmEnableDisabled,
                        vsmCodingProfSwitchover                 VsmEnableDisabled,
                        vsmCodingProfCallProgToneDet            VsmEnableDisabled,
                        vsmCodingProfV18ToneDet                 VsmEnableDisabled,
                        vsmCodingProfVADThreshMode              INTEGER,
                        vsmCodingProfVADThreshLevel             INTEGER,
                        vsmCodingProfVEchoCanComfNoiseMode      INTEGER,
                        vsmCodingProfEchoCanRefreshCfg          INTEGER,
                        vsmCodingProfEchoCanRefreshState        INTEGER,
                        vsmCodingProfECTailDelay                INTEGER,
                        vsmCodingProfECNonLinear                VsmEnableDisabled,
                        vsmCodingProfFaxRate                    INTEGER,
                        vsmCodingProfFaxTxLevel                 INTEGER,
                        vsmCodingProfFaxCdThresh                INTEGER,
                        vsmCodingProfFaxTimeOut                 INTEGER,
                        vsmCodingProfFaxHsPktRate               INTEGER,
                        vsmCodingProfFaxLsRedun                 INTEGER,
                        vsmCodingProfFaxHsRedun                 INTEGER,
                        vsmCodingProfFaxTcfMethod               INTEGER,
                        vsmCodingProfSilenceDetect              VsmEnableDisabled,
                        vsmCodingProfSilenceDetectTime          INTEGER,
                        vsmCodingProfSilenceLevel               INTEGER,
                        vsmCodingProfVoiceComfortNoiseLevel     INTEGER,
                        vsmCodingProfG711ModemResampMode        VsmEnableDisabled,
                        vsmCodingProfSinFreqToneDet             VsmEnableDisabled,
                        vsmCodingProfRowStatus                  RowStatus
                        }

        vsmCodingProfId OBJECT-TYPE
                SYNTAX INTEGER  (1..255)
                ACCESS read-write
                STATUS mandatory
                DESCRIPTION
                        "The coding profile ID uniquely distinguishes the coding profile.

                        For more information, please see the following CLI command:
                          [Note: There is NO equivalent command in the CLI.]
                         "
                ::= { vsmCodingProfEntry 1 }

        vsmCodingProfName OBJECT-TYPE
                SYNTAX DisplayString
                ACCESS read-write
                STATUS mandatory
                DESCRIPTION
                        "The coding profile name provides a text label for the coding
                        profile.

                        For more information, please see the following CLI command:
                         voice coding profile 'codingProfName'
                        "
                ::= { vsmCodingProfEntry 2 }

        vsmCodingProfCallerId OBJECT-TYPE
                SYNTAX VsmEnableDisabled
                ACCESS read-write
                STATUS mandatory
                DESCRIPTION
                        "Enables or Disables Caller Id for the specified Coding Profile.

                        For more information, please see the following CLI command:
                         voice coding profile 'codingProfName' caller id on
                         voice coding profile 'codingProfName' caller id off
                        "
                DEFVAL { enabled }
                ::= { vsmCodingProfEntry 3 }

        vsmCodingProfCodingType OBJECT-TYPE
                SYNTAX VsmVoiceCodingType
                ACCESS read-write
                STATUS mandatory
                DESCRIPTION
                        "Used to define the codec type.

                        For more information, please see the following CLI command:
                           voice coding profile 'codingProfName' codec type g.711 mulaw
                           voice coding profile 'codingProfName' codec type g.711 alaw
                           voice coding profile 'codingProfName' codec type g.723.1 53
                           voice coding profile 'codingProfName' codec type g.723.1 63
                           voice coding profile 'codingProfName' codec type g.729ab
                           voice coding profile 'codingProfName' codec type fax t.38

                        Note: The following are not supported in this Release
                           voice coding profile 'codingProfName' codec type fax
                           voice coding profile 'codingProfName' codec type g.726 16
                           voice coding profile 'codingProfName' codec type g.726 24
                           voice coding profile 'codingProfName' codec type g.726 32
                           voice coding profile 'codingProfName' codec type g.726 40
                           voice coding profile 'codingProfName' codec type g.727 16
                           voice coding profile 'codingProfName' codec type g.727 24
                           voice coding profile 'codingProfName' codec type g.727 32
                           voice coding profile 'codingProfName' codec type g.727 40
                        "
                DEFVAL {ituG723-63}
                ::= { vsmCodingProfEntry 4 }

        vsmCodingProfPktInterval OBJECT-TYPE
                SYNTAX INTEGER {
                                                interval1               (10),
                                                interval2               (20),
                                                interval3               (30),
                                                interval4               (40),
                                                interval5               (50),
                                                interval6               (60),
                                                interval7               (70),
                                                interval8               (80)
                                                }
                ACCESS read-write
                STATUS mandatory
                DESCRIPTION
                         "Specifies the Voice Packet Interval in milliseconds.  The size
                         of the Voice Information Field (vsmCodingProfVIF) is determined
                         by using the current setting of:
                         vsmCodingProfCodingType and vsmCodingProfPktInterval.  The
                         following table shows the relationship between the
                         three parameters:

                   CODEC TYPE:             Voice Packet                           Voice Information
                                                           Intervals Allowed:             Field Size(in bits):
                        Pcm mulaw                               TBD                                                     TBD
                        Pcm alaw                                TBD                                                     TBD
                        g.723 53                                30 ms                                           192
                        g.723 63                                30 ms                                           192
                        g.723 53                                60 ms                                           384
                        g.723 63                                60 ms                                           384
                        g.729ab                                 10 ms                                           80
                        g.729ab                                 20 ms                                           160
                        g.729ab                                 30 ms                                           240
                        g.729ab                                 40 ms                                           320
                        g.729ab                                 50 ms                                           400
                        g.729ab                                 60 ms                                           480
                        g.729ab                                 70 ms                                           560
                        g.729ab                                 80 ms                                           640
                        Fax                                     TBD                                                     TBD
                        fax t.38                                TBD                                                     TBD
                        g.726 16                                10 ms                                           160
                        g.726 16                                20 ms                                           320
                        g.726 16                                30 ms                                           480
                        g.727 16                                10 ms                                           160
                        g.727 16                                20 ms                                           320
                        g.727 16                                30 ms                                           480
                        g.726 24                                10 ms                                           240
                        g.726 24                                20 ms                                           480
                        g.726 24                                30 ms                                           720
                        g.727 24                                10 ms                                           240
                        g.727 24                                20 ms                                           480
                        g.727 24                                30 ms                                           720
                        g.726 32                                10 ms                                           320
                        g.726 32                                20 ms                                           640
                        g.726 32                                30 ms                                           960
                        g.727 32                                10 ms                                           320
                        g.727 32                                20 ms                                           640
                        g.727 32                                30 ms                                           960
                        g.726 40                                10 ms                                           400
                        g.726 40                                20 ms                                           800
                        g.726 40                                30 ms                                           1200
                        g.727 40                                10 ms                                           400
                        g.727 40                                20 ms                                           800
                        g.727 40                                30 ms                                           1200

                        end of table.

                        For more information, please see the following CLI command:
                         voice coding profile 'codingProfName' voice packet interval 10
                         voice coding profile 'codingProfName' voice packet interval 20
                         voice coding profile 'codingProfName' voice packet interval 30
                         voice coding profile 'codingProfName' voice packet interval 40
                         voice coding profile 'codingProfName' voice packet interval 50
                         voice coding profile 'codingProfName' voice packet interval 60
                         voice coding profile 'codingProfName' voice packet interval 70
                         voice coding profile 'codingProfName' voice packet interval 80
                        "
                DEFVAL {interval3}
                ::= { vsmCodingProfEntry 5 }

        vsmCodingProfVIF OBJECT-TYPE
                SYNTAX INTEGER
                ACCESS read-only
                STATUS deprecated
                DESCRIPTION
                         "deprecated"
                DEFVAL {384}
                ::= { vsmCodingProfEntry 6 }

        vsmCodingProfNetBufMode OBJECT-TYPE
                SYNTAX INTEGER {
                        adaptive        (1),
                        static          (2)
                        }
                ACCESS read-write
                STATUS mandatory
                DESCRIPTION
                        "Configures the mode of the adaptive playback function
                        for a coding profile.  With the voice network delay buffer mode
                        set to static (adaptive playout disabled), the nominal and
                        maximum playout values are valid.  If this object is set to
                        adaptive (adaptive playout enabled), the nominal and maximum
                        values hold, but the DSP will adjust the nominal delay
                        (playout point) to reflect any observed jitter.

                        For more information, please see the following CLI command:
                         voice coding profile 'codingProfName' voice network delay buffer mode adaptive
                         voice coding profile 'codingProfName' voice network delay buffer mode static
                        "
                 DEFVAL {static}
                 ::= { vsmCodingProfEntry 7 }

        vsmCodingProfNetBufNomDelay OBJECT-TYPE
                SYNTAX INTEGER
                ACCESS read-write
                STATUS mandatory
                DESCRIPTION
                        "The average delay (in msec) maintained in the path from the
                        packet network to the PCM interface to compensate for the network
                        jitter effects.

                        For more information, please see the following CLI command:
                         voice coding profile 'codingProfName' voice network delay buffer nominal delay (1..1000)
                        "
                DEFVAL {120}
                ::= { vsmCodingProfEntry 8 }

        vsmCodingProfNetBufMaxDelay OBJECT-TYPE
                SYNTAX INTEGER
                ACCESS read-write
                STATUS mandatory
                DESCRIPTION
                        "The maximum instantaneous delay (in msec) beyond which the
                        playout buffer is being recentered.

                        For more information, please see the following CLI command:
                         voice coding profile 'codingProfName' voice network delay buffer maximum delay (1..1000 )
                        "
                DEFVAL {240}
                ::= { vsmCodingProfEntry 9 }

        vsmCodingProfDtmfRelay OBJECT-TYPE
                SYNTAX VsmEnableDisabled
                ACCESS read-write
                STATUS mandatory
                DESCRIPTION
                        "Enables or disables the DTMF Relay mode for a Coding Profile, in
                        which DTMF tones are detected during voice processing and
                        separately packetized for transmission.

                        For more information, please see the following CLI command:
                         voice coding profile 'codingProfName' voice dtmf relay on
                         voice coding profile 'codingProfName' voice dtmf relay off
                        "
                DEFVAL {enabled}
                ::= { vsmCodingProfEntry 10 }

        vsmCodingProfVAD OBJECT-TYPE
                SYNTAX VsmEnableDisabled
                ACCESS read-write
                STATUS mandatory
                DESCRIPTION
                        "Enables or disables Voice Activity Detection (VAD).

                        For more information, please see the following CLI command:
                         voice coding profile 'codingProfName' voice activity detector on
                         voice coding profile 'codingProfName' voice activity detector off
                        "
                DEFVAL {enabled}
                ::= { vsmCodingProfEntry 11 }

        vsmCodingProfEC OBJECT-TYPE
                SYNTAX VsmEnableDisabled
                ACCESS read-write
                STATUS mandatory
                DESCRIPTION
                        "Enables or disables the Echo Canceller (EC).

                        For more information, please see the following CLI command:
                         voice coding profile 'codingProfName' voice echo canceller on
                         voice coding profile 'codingProfName' voice echo canceller off
                        "
                DEFVAL {enabled}
                ::= { vsmCodingProfEntry 12 }

        vsmCodingProfSwitchover OBJECT-TYPE
                SYNTAX VsmEnableDisabled
                ACCESS read-write
                STATUS mandatory
                DESCRIPTION
                        "Enables or Disables switchover to FAX when configured as a voice
                        line.  If enabled, switchover will occur when the appropriate
                        FAX tones have been detected.

                        For more information, please see the following CLI command:
                         voice coding profile 'codingProfName' switchover on
                         voice coding profile 'codingProfName' switchover off
                        "
                DEFVAL {disabled}
                ::= { vsmCodingProfEntry 13 }


                vsmCodingProfCallProgToneDet OBJECT-TYPE
                                SYNTAX VsmEnableDisabled
                                ACCESS read-write
                                STATUS mandatory
                                DESCRIPTION
                                "
                                This command is used to specify a secondary level of control of call progress detection.  If the call
                                progress detection control for a channel is set to relative (See Set Call progress tone detection
                                (off/on/relative) command in section 10.7.1 above) in the signaling, then this parameter determines if
                                detection is to be enabled or not.

                                For more information, please see the following CLI command:
                                    voice coding profile 'codingProfName' call progress tone detection on
                                    voice coding profile 'codingProfName' call progress tone detection off
                                "
                                DEFVAL {disabled}
                                ::= { vsmCodingProfEntry 15 }

        vsmCodingProfV18ToneDet OBJECT-TYPE
                SYNTAX VsmEnableDisabled
                ACCESS read-write
                STATUS mandatory
                DESCRIPTION
                        "Enables or disables V.18 Annex A tone detection.
                        The V.18 Annex A tone is a 1400 HZ tone is detected for 100ms.
                        It is used for channel configuration purposes.

                        For more information, please see the following CLI command:
                         voice coding profile 'codingProfName' v.18 tone detection on
                         voice coding profile 'codingProfName' v.18 tone detection off
                        "
                DEFVAL {disabled}
                ::= { vsmCodingProfEntry 16 }

        vsmCodingProfVADThreshMode OBJECT-TYPE
                SYNTAX INTEGER {
                                adaptive        (1),
                                relative        (2)
                                }
                ACCESS read-write
                STATUS mandatory
                DESCRIPTION
                        "The mode of the audio threshold level
                        for the Voice Activity Detector (VAD) in a Coding Profile to be
                        adaptive or relative to a reference level of -30 dBm.

                        For more information, please see the following CLI command:
                         voice coding profile 'codingProfName' voice activity detection threshold mode adaptive
                         voice coding profile 'codingProfName' voice activity detection threshold mode relative
                        "
                DEFVAL {adaptive}
                ::= { vsmCodingProfEntry 17 }

        vsmCodingProfVADThreshLevel OBJECT-TYPE
                SYNTAX INTEGER ( -20..20 )
                ACCESS read-write
                STATUS mandatory
                DESCRIPTION
                        "If the Voice Activity Detector (VAD) is set to relative using
                        vsmCodingProfVADThreshMode, then this object is used to set
                        the audio threshold level (in dBm) releative to a reference
                        level of -30 dBm.

                        For more information, please see the following CLI command:
                         voice coding profile 'codingProfName' voice activity detection threshold level -20
                         voice coding profile 'codingProfName' voice activity detection threshold level -19
                         voice coding profile 'codingProfName' voice activity detection threshold level -18
                         voice coding profile 'codingProfName' voice activity detection threshold level -17
                         voice coding profile 'codingProfName' voice activity detection threshold level -16
                         voice coding profile 'codingProfName' voice activity detection threshold level -15
                         voice coding profile 'codingProfName' voice activity detection threshold level -14
                         voice coding profile 'codingProfName' voice activity detection threshold level -13
                         voice coding profile 'codingProfName' voice activity detection threshold level -12
                         voice coding profile 'codingProfName' voice activity detection threshold level -11
                         voice coding profile 'codingProfName' voice activity detection threshold level -10
                         voice coding profile 'codingProfName' voice activity detection threshold level -9
                         voice coding profile 'codingProfName' voice activity detection threshold level -8
                         voice coding profile 'codingProfName' voice activity detection threshold level -7
                         voice coding profile 'codingProfName' voice activity detection threshold level -6
                         voice coding profile 'codingProfName' voice activity detection threshold level -5
                         voice coding profile 'codingProfName' voice activity detection threshold level -4
                         voice coding profile 'codingProfName' voice activity detection threshold level -3
                         voice coding profile 'codingProfName' voice activity detection threshold level -2
                         voice coding profile 'codingProfName' voice activity detection threshold level -1
                         voice coding profile 'codingProfName' voice activity detection threshold level 0
                         voice coding profile 'codingProfName' voice activity detection threshold level 20
                         voice coding profile 'codingProfName' voice activity detection threshold level 19
                         voice coding profile 'codingProfName' voice activity detection threshold level 18
                         voice coding profile 'codingProfName' voice activity detection threshold level 17
                         voice coding profile 'codingProfName' voice activity detection threshold level 16
                         voice coding profile 'codingProfName' voice activity detection threshold level 15
                         voice coding profile 'codingProfName' voice activity detection threshold level 14
                         voice coding profile 'codingProfName' voice activity detection threshold level 13
                         voice coding profile 'codingProfName' voice activity detection threshold level 12
                         voice coding profile 'codingProfName' voice activity detection threshold level 11
                         voice coding profile 'codingProfName' voice activity detection threshold level 10
                         voice coding profile 'codingProfName' voice activity detection threshold level 9
                         voice coding profile 'codingProfName' voice activity detection threshold level 8
                         voice coding profile 'codingProfName' voice activity detection threshold level 7
                         voice coding profile 'codingProfName' voice activity detection threshold level 6
                         voice coding profile 'codingProfName' voice activity detection threshold level 5
                         voice coding profile 'codingProfName' voice activity detection threshold level 4
                         voice coding profile 'codingProfName' voice activity detection threshold level 3
                         voice coding profile 'codingProfName' voice activity detection threshold level 2
                         voice coding profile 'codingProfName' voice activity detection threshold level 1
                        "
                DEFVAL {-13}
                ::= { vsmCodingProfEntry 18 }


        vsmCodingProfVEchoCanComfNoiseMode OBJECT-TYPE
                SYNTAX INTEGER {
                                static    (1),
                                adaptive  (2)
                                }
                ACCESS read-write
                STATUS mandatory
                DESCRIPTION
                        "New leaf for 2.2f parser.

                        For more information, please see the following CLI command:
                         voice coding profile 'codingProfName' voice echo canceller comfort noise mode static
                         voice coding profile 'codingProfName' voice echo canceller comfort noise mode adaptive
                        "
                DEFVAL {static}
                ::= { vsmCodingProfEntry 19 }


        vsmCodingProfEchoCanRefreshCfg OBJECT-TYPE
                SYNTAX INTEGER {
                                frozen    (1),
                                refresh    (2)
                                }
                ACCESS read-write
                STATUS mandatory
                DESCRIPTION
                        "New leaf for 2.2f parser.

                        For more information, please see the following CLI command:
                         voice coding profile 'codingProfName' echo canceller refresh configuration frozen
                         voice coding profile 'codingProfName' echo canceller refresh configuration refresh
                        "
                DEFVAL {frozen}
                ::= { vsmCodingProfEntry 20 }

        vsmCodingProfEchoCanRefreshState OBJECT-TYPE
                SYNTAX INTEGER {
                                on        (1),
                                off        (2)
                                }
                ACCESS read-write
                STATUS mandatory
                DESCRIPTION
                        "New leaf for 2.2f parser.

                        For more information, please see the following CLI command:
                         voice coding profile 'codingProfName' echo canceller refresh state on
                         voice coding profile 'codingProfName' echo canceller refresh state off
                        "
                DEFVAL {on}
                ::= { vsmCodingProfEntry 21 }

        vsmCodingProfECTailDelay OBJECT-TYPE
                SYNTAX INTEGER {
                                                delay1  (4),
                                                delay2  (8),
                                                delay3  (16),
                                                delay4  (32)
                                                }
                ACCESS read-write
                STATUS mandatory
                DESCRIPTION
                        "Echo canceller (EC) tail delay in msec.

                        For more information, please see the following CLI command:
                         voice coding profile 'codingProfName'      voice echo canceller tail (0 .. 128 )
                        "
                DEFVAL {delay3}
                ::= { vsmCodingProfEntry 22 }

        vsmCodingProfECNonLinear OBJECT-TYPE
                SYNTAX VsmEnableDisabled
                ACCESS read-write
                STATUS mandatory
                DESCRIPTION
                        "Enables or disables non-linear echo canceller (EC).  object
                        only has effect if the vsmCodingProfEC object is enabled.

                        For more information, please see the following CLI command:
                         voice coding profile 'codingProfName' voice echo canceller non linear on
                         voice coding profile 'codingProfName' voice echo canceller non linear off
                        "
                DEFVAL {enabled}
                ::= { vsmCodingProfEntry 23 }

        vsmCodingProfFaxRate OBJECT-TYPE
                SYNTAX INTEGER {
                                                rate1   (2400),
                                                rate2   (4800),
                                                rate3   (7200),
                                                rate4   (9600),
                                                rate5   (12000),
                                                rate6   (14400)
                                                }
                ACCESS read-write
                STATUS mandatory
                DESCRIPTION
                        "Specifies the FAX maximum rate.

                        For more information, please see the following CLI command:
                         voice coding profile 'codingProfName' fax rate 2400
                         voice coding profile 'codingProfName' fax rate 4800
                         voice coding profile 'codingProfName' fax rate 7200
                         voice coding profile 'codingProfName' fax rate 9600
                         voice coding profile 'codingProfName' fax rate 12000
                         voice coding profile 'codingProfName' fax rate 14400
                        "
                DEFVAL {rate6}
                ::= { vsmCodingProfEntry 35 }

        vsmCodingProfFaxTxLevel OBJECT-TYPE
                SYNTAX INTEGER (-13..0)
                ACCESS read-write
                STATUS mandatory
                DESCRIPTION
                        "Specifies the fax modem transmit (tx) gain.

                        For more information, please see the following CLI command:
                         voice coding profile 'codingProfName' fax transmit level -13
                         voice coding profile 'codingProfName' fax transmit level -12
                         voice coding profile 'codingProfName' fax transmit level -11
                         voice coding profile 'codingProfName' fax transmit level -10
                         voice coding profile 'codingProfName' fax transmit level -9
                         voice coding profile 'codingProfName' fax transmit level -8
                         voice coding profile 'codingProfName' fax transmit level -7
                         voice coding profile 'codingProfName' fax transmit level -6
                         voice coding profile 'codingProfName' fax transmit level -5
                         voice coding profile 'codingProfName' fax transmit level -4
                         voice coding profile 'codingProfName' fax transmit level -3
                         voice coding profile 'codingProfName' fax transmit level -2
                         voice coding profile 'codingProfName' fax transmit level -1
                         voice coding profile 'codingProfName' fax transmit level 0
                        "
                DEFVAL {-13}
                ::= { vsmCodingProfEntry 36 }

        vsmCodingProfFaxCdThresh OBJECT-TYPE
                SYNTAX INTEGER {
                        n26dBm    (1),
                        n33dBm    (2),
                        n43dBm    (3)
                        }
                ACCESS read-write
                STATUS mandatory
                DESCRIPTION
                        "Specifies the fax modem carrier-detection threshold.

                        For more information, please see the following CLI command:
                         voice coding profile 'codingProfName' fax carrier detect threshold low
                         voice coding profile 'codingProfName' fax carrier detect threshold medium
                         voice coding profile 'codingProfName' fax carrier detect threshold high
                                          "
                DEFVAL {n43dBm}
                ::= { vsmCodingProfEntry 37 }

        vsmCodingProfFaxTimeOut OBJECT-TYPE
                SYNTAX INTEGER (10..3200)
                ACCESS read-write
                STATUS mandatory
                DESCRIPTION
                        "Specifies the amount of time of no activity on a fax modem
                        connection before the call will be cleared.

                        For more information, please see the following CLI command:
                         voice coding profile 'codingProfName' fax timeout (10..32000)
                        "
                DEFVAL {20}
                ::= { vsmCodingProfEntry 38 }

        vsmCodingProfFaxHsPktRate OBJECT-TYPE
                SYNTAX INTEGER {
                                                rate1   (10),
                                                rate2   (20),
                                                rate3   (30),
                                                rate4   (40)
                                                }
                ACCESS read-write
                STATUS mandatory
                DESCRIPTION
                        "Specifies the rate at which high speed data will be sent
                        across the network, for fax coding.

                        For more information, please see the following CLI command:
                         voice coding profile 'codingProfName' fax t.38 high speed packet rate 10
                         voice coding profile 'codingProfName' fax t.38 high speed packet rate 20
                         voice coding profile 'codingProfName' fax t.38 high speed packet rate 30
                         voice coding profile 'codingProfName' fax t.38 high speed packet rate 40
                        "
                DEFVAL {rate2}
                ::= { vsmCodingProfEntry 39 }

        vsmCodingProfFaxLsRedun OBJECT-TYPE
                SYNTAX INTEGER (1..6 )
                ACCESS read-write
                STATUS mandatory
                DESCRIPTION
                        "Specifies the packet-level redundancy for low speed data
                        transmission, for fax coding.

                        For more information, please see the following CLI command:
                         voice coding profile 'codingProfName' fax t.38 low speed redundancy 0
                         voice coding profile 'codingProfName' fax t.38 low speed redundancy 1
                         voice coding profile 'codingProfName' fax t.38 low speed redundancy 2
                         voice coding profile 'codingProfName' fax t.38 low speed redundancy 3
                         voice coding profile 'codingProfName' fax t.38 low speed redundancy 4
                         voice coding profile 'codingProfName' fax t.38 low speed redundancy 5
                        "
                DEFVAL {4}
                ::= { vsmCodingProfEntry 40 }

        vsmCodingProfFaxHsRedun OBJECT-TYPE
                SYNTAX INTEGER ( 1..3 )
                ACCESS read-write
                STATUS mandatory
                DESCRIPTION
                        "Specifies the packet-level redundancy for high speed data
                        transmission, for fax coding.

                        For more information, please see the following CLI command:
                         voice coding profile 'codingProfName' fax t.38 high speed redundancy 0
                         voice coding profile 'codingProfName' fax t.38 high speed redundancy 1
                         voice coding profile 'codingProfName' fax t.38 high speed redundancy 2
                        "
                DEFVAL {2}
                ::= { vsmCodingProfEntry 41 }

        vsmCodingProfFaxTcfMethod OBJECT-TYPE
                SYNTAX INTEGER {
                        local (1),
                        network(2)
                        }
                ACCESS read-write
                STATUS mandatory
                DESCRIPTION
                        "Specifies the method with which data is handled over the
                        network, for fax coding.

                        For more information, please see the following CLI command:
                         voice coding profile 'codingProfName' fax t.38 training check field method local
                         voice coding profile 'codingProfName' fax t.38 training check field method network
                        "
                DEFVAL {network}
                ::= { vsmCodingProfEntry 42 }

        vsmCodingProfSilenceDetect OBJECT-TYPE
                SYNTAX VsmEnableDisabled
                ACCESS read-write
                STATUS mandatory
                DESCRIPTION
                        "Enables or disables silence detection.

                        For more information, please see the following CLI command:
                         voice coding profile 'codingProfName' no silence detect time
                        "
                DEFVAL { disabled }
                ::= { vsmCodingProfEntry 43 }

        vsmCodingProfSilenceDetectTime OBJECT-TYPE
                SYNTAX INTEGER ( 5..32000 )
                ACCESS read-write
                STATUS mandatory
                DESCRIPTION
                        "Specifies the silent time for declaring silence detection.
                        To disable silence detection use the object
                        vsmCodingProfSilenceDetect.

                        For more information, please see the following CLI command:
                         voice coding profile 'codingProfName' silence detect time (5..32000)
                        "
                DEFVAL { 5 }
                ::= { vsmCodingProfEntry 44 }

        vsmCodingProfSilenceLevel OBJECT-TYPE
                SYNTAX INTEGER ( -50..-40 )
                ACCESS read-write
                STATUS mandatory
                DESCRIPTION
                        "Specifies the silence signal level for declaring silence
                        detection.

                        For more information, please see the following CLI command:
                         voice coding profile 'codingProfName' silence detect level -50
                         voice coding profile 'codingProfName' silence detect level -49
                         voice coding profile 'codingProfName' silence detect level -48
                         voice coding profile 'codingProfName' silence detect level -47
                         voice coding profile 'codingProfName' silence detect level -46
                         voice coding profile 'codingProfName' silence detect level -45
                         voice coding profile 'codingProfName' silence detect level -44
                         voice coding profile 'codingProfName' silence detect level -43
                         voice coding profile 'codingProfName' silence detect level -42
                         voice coding profile 'codingProfName' silence detect level -41
                         voice coding profile 'codingProfName' silence detect level -40
                        "
                DEFVAL { -50 }
                ::= { vsmCodingProfEntry 45 }

      vsmCodingProfVoiceComfortNoiseLevel OBJECT-TYPE
                      SYNTAX INTEGER (-70..-40)
                      ACCESS read-write
                      STATUS mandatory
                      DESCRIPTION
                      "
                      This command is used to set the comfort noise level.

                      For more information, please see the following CLI command:
                          voice coding profile 'codingProfName' voice comfort noise level (-70 ... -40)
                      "
                      DEFVAL {-40}
                      ::= { vsmCodingProfEntry 46}

      vsmCodingProfG711ModemResampMode OBJECT-TYPE
                      SYNTAX VsmEnableDisabled
                      ACCESS read-write
                      STATUS mandatory
                      DESCRIPTION
                      "
                      This command toggles resampling on or off for a Coding Profile.

                      For more information, please see the following CLI command:
                           voice coding profile 'codingProfName' g.711 modem resampling mode on
                           voice coding profile 'codingProfName' g.711 modem resampling mode off
                      "
                      DEFVAL {disabled}
                      ::= { vsmCodingProfEntry 47 }

      vsmCodingProfSinFreqToneDet OBJECT-TYPE
                      SYNTAX VsmEnableDisabled
                      ACCESS read-write
                      STATUS mandatory
                      DESCRIPTION
                      "
                      This command is used to enable or disable SF Single Frequency signaling tone
                      detection.  The SF Signaling characteristocs are defined in the Bellcore
                      document TP-NPL-000275. The DSPs on the VSx card supports detection of 2600 Hz
                      tone.

                      For more information, please see the following CLI command:
                           voice coding profile 'codingProfName' single frequency tone detection on
                           voice coding profile 'codingProfName' single frequency tone detection off
                      "
                      DEFVAL {disabled}
                      ::= { vsmCodingProfEntry 48 }


        vsmCodingProfRowStatus OBJECT-TYPE
                SYNTAX RowStatus
                ACCESS read-write
                STATUS mandatory
                DESCRIPTION
                        "This object is the RowStatus (locking flag) for creating the
                        vsmCodingProfileTable conceptual row.

                        For more information, please see the following CLI command:
                         voice no coding profile 'codingProfName'
                        "
                ::= { vsmCodingProfEntry 49 }

--======================================================================
--======================================================================
--
--      The Dial Scheme Group
--
--======================================================================
-- == Note: vsmDialSchemeGroup OBJECT IDENTIFIER ::= { xylanVsmArch 4 }
--======================================================================
--======================================================================

--======================================================================
--
--      Destinations
--
--======================================================================

        vsmDestinationsTable OBJECT-TYPE
                SYNTAX SEQUENCE OF VsmDestinationsEntry
                ACCESS not-accessible
                STATUS mandatory
                DESCRIPTION
                        "This table defines all the possible network destinations on
                        this switch.  This table includes definitions for both destinations
                        and local destinations.  Not all elements of the table are used
                        for both types od destinations.  Each element description should
                        be checked to see if local or non-local or both types are
                        supported.  Local destinations are defined to be destinations
                        that reside on the same Vsd board.  Thus they do not ahve to
                        travel over IP.
                        "
                ::= { vsmDialSchemeGroup 1 }

        vsmDestinationsEntry OBJECT-TYPE
                SYNTAX VsmDestinationsEntry
                ACCESS not-accessible
                STATUS mandatory
                DESCRIPTION
                        "This is an entry in the vsmDialDestinationsTable.

                  For more information, please see the following CLI command:
                    [Note: There is NO equivalent command in the CLI.]
                        "
                INDEX { vsmDestinationsName }
                ::= { vsmDestinationsTable 1 }

        VsmDestinationsEntry ::=
                SEQUENCE {
                        vsmDestinationsName                     DisplayString,
                        vsmDestinationsIpAddr                   IpAddress,
                        vsmDestinationsNetworkPort              INTEGER,
                        vsmDestinationsH323Name                 DisplayString,
                        vsmDestinationsLocalPort                INTEGER,
                        vsmDestinationsStartChan                INTEGER,
                        vsmDestinationsEndChan                  INTEGER,
                        vsmDestinationsType                     INTEGER,
                        vsmDestinationsRowStatus                RowStatus
                        }

        vsmDestinationsName OBJECT-TYPE
                SYNTAX DisplayString
                ACCESS read-write
                STATUS mandatory
                DESCRIPTION
                        "A name describing the network destination.  This object is valid
                        for both local and non-local destinations.

                        For more information, please see the following CLI command:
                         voice destination 'endPointNameStr' h.323 xxx.xxx.xxx.xxx h323port
                                                 voice destination 'destinationNameStr' local channel 'endpointNameStr'/port/startChannel-endChannel
                        "
                ::= { vsmDestinationsEntry 1 }

        vsmDestinationsIpAddr OBJECT-TYPE
                SYNTAX IpAddress
                ACCESS read-write
                STATUS mandatory
                DESCRIPTION
                        "IP Address of a network endpoint
                        The default value is 127.0.0.1

                        For more information, please see the following CLI command:
                                                 voice destination 'endPointNameStr' h.323 xxx.xxx.xxx.xxx [h323port]
                        "
                ::= { vsmDestinationsEntry 2 }

        vsmDestinationsNetworkPort OBJECT-TYPE
                SYNTAX INTEGER
                ACCESS read-write
                STATUS mandatory
                DESCRIPTION
                        "Network H.323 port for destination, For now this parameter is
                        always 1720.  This is valid for only non-local destinations.

                        For more information, please see the following CLI command:
                                                 voice destination 'endPointNameStr' h.323 xxx.xxx.xxx.xxx [h323port]
                        "
                ::= { vsmDestinationsEntry 3 }

        vsmDestinationsH323Name OBJECT-TYPE
                SYNTAX DisplayString
                ACCESS read-write
                STATUS mandatory
                DESCRIPTION
                        "The end point name describing the network destination that is associated
                        with an IP address.  All local ports will have this name
                        associated with them.  This object is valid for local ports
                        only.

                        For more information, please see the following CLI command:
                                                 voice destination 'destinationNameStr' local channel 'endpointNameStr'/port/startChannel-endChannel

                        "
                ::= { vsmDestinationsEntry 4 }

        vsmDestinationsLocalPort OBJECT-TYPE
                SYNTAX INTEGER
                ACCESS read-write
                STATUS mandatory
                DESCRIPTION
                        "The Physical port number on which this local destination
                        exists.  This is valid for only local destinations.

                        For more information, please see the following CLI command:
                                                 voice destination 'destinationNameStr' local channel 'endpointNameStr'/port/startChannel-endChannel
                        "
                ::= { vsmDestinationsEntry 5 }

        vsmDestinationsStartChan OBJECT-TYPE
                SYNTAX INTEGER
                ACCESS read-write
                STATUS mandatory
                DESCRIPTION
                        "a group of channels is associated with a local destination,
                        this specifies the first channel number in that group.  This
                        object is for local destinations only.

                        For more information, please see the following CLI command:
                                                 voice destination 'destinationNameStr' local channel 'endpointNameStr'/port/startChannel-endChannel
                        "
                ::= { vsmDestinationsEntry 6 }

        vsmDestinationsEndChan OBJECT-TYPE
                SYNTAX INTEGER
                ACCESS read-write
                STATUS mandatory
                DESCRIPTION
                        "a group of channels is associated with a local destination,
                        this specifies the last channel number in that group.  This
                        object is for local destinations only.

                        For more information, please see the following CLI command:
                                                 voice destination 'destinationNameStr' local channel 'endpointNameStr'/port/startChannel-endChannel
                        "
                ::= { vsmDestinationsEntry 7 }

        vsmDestinationsType OBJECT-TYPE
                SYNTAX INTEGER {
                        h323               (1)
                        }
                ACCESS read-write
                STATUS mandatory
                DESCRIPTION
                        "The type of destination, hsmu (H.323), tsgm, or qsmu.  Currently we
                        only support hsmu.  This is valid for all destinations as a local
                        destination will be set to tsgm.

                        For more information, please see the following CLI command:
                         voice destination 'endPointNameStr' h.323 xxx.xxx.xxx.xxx h323port
                        "
                DEFVAL { h323 }
                ::= { vsmDestinationsEntry 8 }

        vsmDestinationsRowStatus OBJECT-TYPE
                SYNTAX RowStatus
                ACCESS read-write
                STATUS mandatory
                DESCRIPTION
                        "The status of a row in this table using CreateAndGo and DeleteRow.
                        Objects in this table cannot be set individually.  There are two
                        basic operations supported.  1. endpoints can be created,
                        2. destinations can be created.  When endpoints are created,
                        In the PDU supplied with the RowStatus there must also be a
                        vsmDestinationsName object, and a vsmDestinationsIpAddr object
                        and optionally a vsmDestinationsNetworkPort object.

                        When destinations are created, inside the Pdu with the RowStatus
                        create request, the packet must also contain the vsmDestinationsName
                        object, vsmDestinationsH323Name object, vsmDestinationsLocalPort object,
                        vsmDestinationsStartChan object and vsmDestinationsEndChan object.

                        The vsmDestinationsType object is currently not used since there
                        is only one type supported.

                        For more information, please see the following CLI command:
                           voice no destination 'NameStr'
                        "
                ::= { vsmDestinationsEntry 9 }


--======================================================================
--
--      Phone Groups
--
--======================================================================

        vsmPhoneGroupTable OBJECT-TYPE
                SYNTAX SEQUENCE OF VsmPhoneGroupEntry
                ACCESS not-accessible
                STATUS mandatory
                DESCRIPTION
                        "This table contains information on the extensions
                        and the usage of those extensions for each defined
                        phone group.
                        "
                ::= { vsmDialSchemeGroup 2 }

        vsmPhoneGroupEntry OBJECT-TYPE
                SYNTAX VsmPhoneGroupEntry
                ACCESS not-accessible
                STATUS mandatory
                DESCRIPTION
                        "This is an entry in the vsmPhoneGroupTable.

                          For more information, please see the following CLI command:
                            [Note: There is NO equivalent command in the CLI.]
                        "
                INDEX { vsmPhoneGroupName }
                ::= { vsmPhoneGroupTable 1 }

        VsmPhoneGroupEntry ::=
                SEQUENCE {
                        vsmPhoneGroupName                               DisplayString,
                        vsmPhoneGroupType                               INTEGER,
                        vsmPhoneGroupFormat                             DisplayString,
                        vsmPhoneGroupUsageVoice                         VsmEnableDisabled,
                        vsmPhoneGroupUsageFax                           VsmEnableDisabled,
                        vsmPhoneGroupUsageModem                         VsmEnableDisabled,
                        vsmPhoneGroupUsageData                          VsmEnableDisabled,
                        vsmPhoneGroupSitePrefixEnable                   VsmEnableDisabled,
                        vsmPhoneGroupSitePrefixString                   DisplayString,
                        vsmPhoneGroupStripDigitLength                   INTEGER,
                                                vsmPhoneGroupForwardingPrefixEnable                             VsmEnableDisabled,
                                                vsmPhoneGroupForwardingPrefix                                   DisplayString,
                        vsmPhoneGroupRowStatus                          RowStatus
                        }

        vsmPhoneGroupName OBJECT-TYPE
                SYNTAX DisplayString
                ACCESS read-write
                STATUS mandatory
                DESCRIPTION
                        "A name describing a row in the phone group table.

                        For more information, please see the following CLI command:
                         voice phone group 'PhoneGroupName'
                        "
                ::= { vsmPhoneGroupEntry 1 }

        vsmPhoneGroupType OBJECT-TYPE
                SYNTAX INTEGER {
                        localExt                        (1),
                        nanpExt                         (2),
                        internationalExt                (3),
                        nanpPstn                        (4),
                        internationalPstn               (5)
                        }
                ACCESS read-write
                STATUS mandatory
                DESCRIPTION
                        "Specifies the type of phone group type.

                        For more information, please see the following CLI command:
                         voice phone group 'PhoneGroupName' type local extensions
                         voice phone group 'PhoneGroupName' type NANP extensions
                         voice phone group 'PhoneGroupName' type international extensions
                         voice phone group 'PhoneGroupName' type NANP PSTN
                         voice phone group 'PhoneGroupName' type international PSTN
                        "
                DEFVAL { localExt }
                ::= { vsmPhoneGroupEntry 2 }

        vsmPhoneGroupFormat OBJECT-TYPE
                SYNTAX DisplayString
                ACCESS read-write
                STATUS mandatory
                DESCRIPTION
                        "This command is used to set the preferred user viewing format
                        specification for this phone group. This field is used to
                        calculated the # of digits allowed.

                        For more information, please see the following CLI command:
                         voice phone group 'PhoneGroupName' format 'formatString'
                        "
                ::= { vsmPhoneGroupEntry 3 }

        vsmPhoneGroupUsageVoice OBJECT-TYPE
                SYNTAX VsmEnableDisabled
                ACCESS read-write
                STATUS mandatory
                DESCRIPTION
                        "This command is used to set the allowed usages of these phone lines
                        This parameter allows for better type checking upon binding later on.

                        For more information, please see the following CLI command:
                         voice phone group 'PhoneGroupName' usage voice on
                         voice phone group 'PhoneGroupName' usage voice off
                        "
                DEFVAL {enabled}
                ::= { vsmPhoneGroupEntry 4 }

        vsmPhoneGroupUsageFax OBJECT-TYPE
                SYNTAX VsmEnableDisabled
                ACCESS read-write
                STATUS mandatory
                DESCRIPTION
                        "This command is used to set the allowed usages of these phone lines
                        This parameter allows for better type checking upon binding later on.

                        For more information, please see the following CLI command:
                         voice phone group 'PhoneGroupName' usage fax on
                         voice phone group 'PhoneGroupName' usage fax off
                        "
                DEFVAL {enabled}
                ::= { vsmPhoneGroupEntry 5 }

        vsmPhoneGroupUsageModem OBJECT-TYPE
                SYNTAX VsmEnableDisabled
                ACCESS read-write
                STATUS mandatory
                DESCRIPTION
                        "This command is used to set the allowed usages of these phone lines
                        This parameter allows for better type checking upon binding later on.

                        For more information, please see the following CLI command:
                         voice phone group 'PhoneGroupName' usage modem on
                         voice phone group 'PhoneGroupName' usage modem off
                        "
                DEFVAL {enabled}
                ::= { vsmPhoneGroupEntry 6 }

        vsmPhoneGroupUsageData OBJECT-TYPE
                SYNTAX VsmEnableDisabled
                ACCESS read-write
                STATUS mandatory
                DESCRIPTION
                        "This command is used to set the allowed usages of these phone lines
                        This parameter allows for better type checking upon binding later on.

                        For more information, please see the following CLI command:
                         voice phone group 'PhoneGroupName' usage data on
                         voice phone group 'PhoneGroupName' usage data off
                        "
                DEFVAL {enabled}
                ::= { vsmPhoneGroupEntry 7 }

        vsmPhoneGroupSitePrefixEnable OBJECT-TYPE
                SYNTAX VsmEnableDisabled
                ACCESS read-write
                STATUS mandatory
                DESCRIPTION
                        "This command selects if a site prefix will be used.  A caller
                        uses this prefix to route members of this phone group.

                        For more information, please see the following CLI command:
                         voice phone group 'PhoneGroupName' site prefix on
                         voice phone group 'PhoneGroupName' site prefix off
                        "
                DEFVAL {enabled}
                ::= { vsmPhoneGroupEntry 8 }

        vsmPhoneGroupSitePrefixString OBJECT-TYPE
                SYNTAX DisplayString
                ACCESS read-write
                STATUS mandatory
                DESCRIPTION
                        "This command sets the site prefix digits to be used. For example
                        **9 would mean that from any channel on the network, if the digits
                        **9 are pressed, we expect # of digits to follow.  So if the
                        user sets up a site prefix of **9, and the format is XXXX then to
                        get to extension 4601, the user would dial **94601 to get to that
                        extension from anywhere on the VoIP network.  In this case, a 3
                        digit dialing prefix is used, so the VoIP network can support 1728
                        sites, with 1000 extensions per site

                        For more information, please see the following CLI command:
                         voice phone group 'PhoneGroupName' site prefix digits 'String'
                        "
                ::= { vsmPhoneGroupEntry 9 }

        vsmPhoneGroupStripDigitLength OBJECT-TYPE
                SYNTAX INTEGER
                ACCESS read-write
                STATUS mandatory
                DESCRIPTION
                        "Number of digits to strip from the beginning of the digits
                        collected before forwarding on the destination side.

                        For more information, please see the following CLI command:
                         voice phone group 'PhoneGroupName' strip digit length vsmPreStripLength
                        "
                DEFVAL {0}
                ::= { vsmPhoneGroupEntry 10 }

                vsmPhoneGroupForwardingPrefixEnable OBJECT-TYPE
                SYNTAX VsmEnableDisabled
                ACCESS read-write
                STATUS mandatory
                DESCRIPTION
                        "This command is used to enable/disable the forwarding prefix.  The forwarding
                        prefix is a digit that must be typed before the phone group is entered.

                        For more information, please see the following CLI command:
                         voice phone group 'PhoneGroupName' forwarding prefix on
                         voice phone group 'PhoneGroupName' forwarding prefix off
                        "
                DEFVAL {disabled}
                ::= { vsmPhoneGroupEntry 11 }

                vsmPhoneGroupForwardingPrefix OBJECT-TYPE
                SYNTAX DisplayString
                ACCESS read-write
                STATUS mandatory
                DESCRIPTION
                        "String of digits to prefix before forwarding on the destination side.
                        Digits to be attached at the beginning of the address being forwarded.
                                                For example, when dialing out to a PBX, dial 9 before outward dialing.
                                                This is an optional parameter.

                        For more information, please see the following CLI command:
                         voice phone group 'PhoneGroupName' forwarding prefix digits 'String'
                        "
                ::= { vsmPhoneGroupEntry 12 }

        vsmPhoneGroupRowStatus OBJECT-TYPE
                SYNTAX RowStatus
                ACCESS read-write
                STATUS mandatory
                DESCRIPTION
                        "The status of a row in this table using SNMPv2 Standard
                        for row status; CreateAndWait, CreateAndGo, ActivateRow,
                        InactivateRow and DeleteRow.

                        For more information, please see the following CLI command:
                         voice no phone group 'PhoneGroupName'
                        "
                ::= { vsmPhoneGroupEntry 13 }

--======================================================================
--
--      Phone Group Numbers
--
--======================================================================
--
        vsmPGNumbersTable OBJECT-TYPE
                SYNTAX SEQUENCE OF VsmPGNumbersEntry
                ACCESS not-accessible
                STATUS mandatory
                DESCRIPTION
                        "This table contains arrays of phone ranges for the above
                        phone groups.  This table has two indexes, because there
                        is an array of phone ranges for each phone group.
                        "
                ::= { vsmDialSchemeGroup 3 }

-- Note: was vsmPGSiteNumbersEntry
        vsmPGNumbersEntry OBJECT-TYPE
                SYNTAX VsmPGNumbersEntry
                ACCESS not-accessible
                STATUS mandatory
                DESCRIPTION
                        "This is an entry in the vsmPhoneGroupTable.

                        For more information, please see the following CLI command:
                          [Note: There is NO equivalent command in the CLI.]
                        "
                INDEX { vsmPhoneGroupName, vsmPGNumber }
                ::= { vsmPGNumbersTable 1 }

-- Note: was VsmPGSiteNumbersEntry
        VsmPGNumbersEntry ::=
                SEQUENCE {
                        vsmPGNumber                 DisplayString,
                        vsmPGNumbersRowStatus       RowStatus
                        }

-- Note: was vsmPGSiteNumber
        vsmPGNumber OBJECT-TYPE
                SYNTAX DisplayString
                ACCESS read-only
                STATUS mandatory
                DESCRIPTION
                        "The site number being added to the phone group entry.

                        For more information, please see the following CLI command:
                         voice phone group 'PhoneGroupName' add numbers 'StartRange'
                         voice phone group 'PhoneGroupName' add numbers 'StartRange' thru 'EndRange'
                        "
                ::= { vsmPGNumbersEntry 1 }

-- Note: was vsmPGSiteNumbersRowStatus
        vsmPGNumbersRowStatus OBJECT-TYPE
                SYNTAX RowStatus
                ACCESS read-write
                STATUS mandatory
                DESCRIPTION
                        "The status of a row in this table using SNMPv2 Standard
                        for row status; CreateAndWait, CreateAndGo, ActivateRow,
                        InactivateRow and DeleteRow.

                        For more information, please see the following CLI command:
                         voice phone group 'PhoneGroupName' delete numbers 'StartRange'
                         voice phone group 'PhoneGroupName' delete numbers 'StartRange' thru 'EndRange'
                        "
                ::= { vsmPGNumbersEntry 2 }


--======================================================================
--
--      Numbering Plan
--
--======================================================================

        vsmNumPlanTable OBJECT-TYPE
                SYNTAX SEQUENCE OF VsmNumPlanEntry
                ACCESS not-accessible
                STATUS mandatory
                DESCRIPTION
                        "This table contains information on the extensions
                        and the usage of those extensions for each defined
                        phone group.
                        "
                ::= { vsmDialSchemeGroup 4 }

        vsmNumPlanEntry OBJECT-TYPE
                SYNTAX VsmNumPlanEntry
                ACCESS not-accessible
                STATUS mandatory
                DESCRIPTION
                        "This is an entry in the vsmNumPlanTable.

                         For more information, please see the following CLI command:
                           [Note: There is NO equivalent command in the CLI.]
                        "
                INDEX { vsmNumPlanName }
                ::= { vsmNumPlanTable 1 }

        VsmNumPlanEntry ::=
                SEQUENCE {
                        vsmNumPlanName                  DisplayString,
                        vsmNumPlanHuntMethod            INTEGER,
                        vsmNumPlanDescription           DisplayString,
                                                vsmNumPlanAllActivate                   INTEGER,
                        vsmNumPlanRowStatus             RowStatus
                        }

        vsmNumPlanName OBJECT-TYPE
                SYNTAX DisplayString
                ACCESS read-write
                STATUS mandatory
                DESCRIPTION
                        "A name describing a row in the numbering plan table.

                        For more information, please see the following CLI command:
                           voice numbering plan 'NumberingPlanName'
                        "
                ::= { vsmNumPlanEntry 1 }

        vsmNumPlanHuntMethod OBJECT-TYPE
                SYNTAX INTEGER {
                        roundRobin                              (1),
                        topDown                                 (2)
                        }
                ACCESS read-write
                STATUS mandatory
                DESCRIPTION
                        "This command is used to set the method of outgoing hunting.
                        It also serves to group related destinations together.

                        For more information, please see the following CLI command:
                           voice numbering plan 'NumberingPlanName' hunt method round robin
                           voice numbering plan 'NumberingPlanName' hunt method top down
                        "
                DEFVAL {roundRobin}
                ::= { vsmNumPlanEntry 2 }

        vsmNumPlanDescription OBJECT-TYPE
                SYNTAX DisplayString
                ACCESS read-write
                STATUS mandatory
                DESCRIPTION
                        "This parameter is used to store a description of this phone group
                        It is for the users convenience only.  This command is optional
                        and has no effect on any hardware.  This can be used to hold the
                        circuit identifier is so desired.

                        For more information, please see the following CLI command:
                           voice numbering plan 'NumberingPlanName' description 'String'
                        "
                ::= { vsmNumPlanEntry 3 }

          vsmNumPlanAllActivate OBJECT-TYPE
                          SYNTAX INTEGER {
                                                        activate                (1),
                                                        active                  (2),
                                                        inactive                (3),
                                                        invalid                 (4)
                                                        }
                          ACCESS read-write
                          STATUS mandatory
                          DESCRIPTION
                                         "This object has one writable state called activate, This will
                                         force the configured row to become the active configuration for
                                         the specified card.  This object can be read to determine the
                                         current state of the row.  If the row has not been activated,
                                         by default, the state is inactive.  If the row has been activated
                                         and the configuration is good, then this object transitions to active.
                                         If the row has been activated and the configuration is not good
                                         then this object transitions to invalid.

                                         For more information, please see the following CLI command:
                                          voice numbering plan all activate
                                         "
                         ::= { vsmNumPlanEntry 4 }


        vsmNumPlanRowStatus OBJECT-TYPE
                SYNTAX RowStatus
                ACCESS read-write
                STATUS mandatory
                DESCRIPTION
                        "The status of a row in this table using SNMPv2 Standard
                        for row status; CreateAndWait, CreateAndGo, ActivateRow,
                        InactivateRow and DeleteRow.

                        For more information, please see the following CLI command:
                           voice no numbering plan 'NumberingPlanName'
                        "
                ::= { vsmNumPlanEntry 5 }

--======================================================================
--
--      Numbering Plan Phone Groups
--
--======================================================================

        vsmNPPhoneGroupTable OBJECT-TYPE
                SYNTAX SEQUENCE OF VsmNPPhoneGroupEntry
                ACCESS not-accessible
                STATUS mandatory
                DESCRIPTION
                        "This table contains arrays of phone groups that are
                        associated with numbering plans.
                        "
                ::= { vsmDialSchemeGroup 5 }

        vsmNPPhoneGroupEntry OBJECT-TYPE
                SYNTAX VsmNPPhoneGroupEntry
                ACCESS not-accessible
                STATUS mandatory
                DESCRIPTION
                        "This is an entry in the vsmNumPlanTable.

                        For more information, please see the following CLI command:
                          [Note: There is NO equivalent command in the CLI.]
                        "
                INDEX { vsmNumPlanName, vsmPhoneGroupName }
                ::= { vsmNPPhoneGroupTable 1 }

        VsmNPPhoneGroupEntry ::=
                SEQUENCE {
                        vsmNPPhoneGroupRowStatus        RowStatus
                        }

        vsmNPPhoneGroupRowStatus OBJECT-TYPE
                SYNTAX RowStatus
                ACCESS read-write
                STATUS mandatory
                DESCRIPTION
                        "The status of a row in this table using SNMPv2 Standard
                        for row status; CreateAndWait, CreateAndGo, ActivateRow,
                        InactivateRow and DeleteRow.

                        For more information, please see the following CLI command:
                           voice numbering plan 'NumberingPlanName' associate phone group member 'PhoneGroupName'
                           voice numbering plan 'NumberingPlanName' disassociate phone group member 'PhoneGroupName'
                        "
                ::= { vsmNPPhoneGroupEntry 1 }

--======================================================================
--
--      Numbering Plan Destinations
--
--======================================================================

        vsmNPDestinationsTable OBJECT-TYPE
                SYNTAX SEQUENCE OF VsmNPDestinationsEntry
                ACCESS not-accessible
                STATUS mandatory
                DESCRIPTION
                        "This table contains arrays of destinations that are
                        associated with Numbering Plans.
                        "
                ::= { vsmDialSchemeGroup 6 }

        vsmNPDestinationsEntry OBJECT-TYPE
                SYNTAX VsmNPDestinationsEntry
                ACCESS not-accessible
                STATUS mandatory
                DESCRIPTION
                        "This is an entry in the vsmNumPlanTable.

                        For more information, please see the following CLI command:
                          [Note: There is NO equivalent command in the CLI.]
                        "
                INDEX { vsmNumPlanName, vsmDestinationsName }
                ::= { vsmNPDestinationsTable 1 }

        VsmNPDestinationsEntry ::=
                SEQUENCE {
                        vsmNPDestinationsRowStatus                      RowStatus
                        }

        vsmNPDestinationsRowStatus OBJECT-TYPE
                SYNTAX RowStatus
                ACCESS read-write
                STATUS mandatory
                DESCRIPTION
                        "The status of a row in this table using SNMPv2 Standard
                        for row status; CreateAndWait, CreateAndGo, ActivateRow,
                        InactivateRow and DeleteRow.
                        For more information, please see the following CLI command:
                           voice numbering plan 'NumberingPlanName' associate destination member 'NameStr'
                           voice numbering plan 'NumberingPlanName' disassociate destination member 'NameStr'
                        "
                ::= { vsmNPDestinationsEntry 1 }


--======================================================================
--=====================================================================
--
--      The VSM Physical Group
--
--=====================================================================
--== Note: vsmPhysicalGroup  OBJECT IDENTIFIER ::= { xylanVsmArch 5 }
--======================================================================

--======================================================================
--
--       Card Physical Configuration Table
--
-- This table contains information that is unique to each VSM daughter
-- card.
-- The information is indexed by slot/card.
--
--======================================================================
  vsmCardConfTable OBJECT-TYPE
          SYNTAX SEQUENCE OF VsmCardConfEntry
          ACCESS not-accessible
          STATUS  mandatory
          DESCRIPTION
                 "This table contains VSM local interface
                  configuration parameters, one entry per VSM
                  daughter card.
                  "
          ::= { vsmPhysicalGroup 1 }

  vsmCardConfEntry OBJECT-TYPE
          SYNTAX VsmCardConfEntry
          ACCESS not-accessible
          STATUS mandatory
          DESCRIPTION
                 "This list contains VSM interface configuration
                  parameters and state variables.

                  For more information, please see the following CLI command:
                    [Note: There is NO equivalent command in the CLI.]
                  "
          INDEX { vsmCardSlotIndex, vsmCardSubunitIndex }
          ::= { vsmCardConfTable  1}

  VsmCardConfEntry ::= SEQUENCE  {
        vsmCardSlotIndex                                INTEGER,
        vsmCardSubunitIndex                             XylanModuleSubunit,
        vsmCardIpAddr                                   IpAddress,
        vsmCardIpMask                                   IpAddress,
        vsmCardIpDefGateway                             IpAddress,
        vsmCardFirstDigitWaitDur                        INTEGER,
        vsmCardInterDigitWaitDur                        INTEGER,
        vsmCardDialTimeDur                              INTEGER,
        vsmCardTermDigitStr                             DisplayString,
        vsmCardH323AutomaticAnswer                      VsmEnableDisabled,
        vsmCardH323InFastStart                          VsmEnableDisabled,
        vsmCardH323OutFastStart                         VsmEnableDisabled,
        vsmCardConfigStatus                             INTEGER
        }

  vsmCardSlotIndex OBJECT-TYPE
          SYNTAX INTEGER  (1..9)
          ACCESS read-only
          STATUS mandatory
          DESCRIPTION
                 "The slot number for the card

                  For more information, please see the following CLI command:
                    [Note: There is NO equivalent command in the CLI.]
                 "
          ::= { vsmCardConfEntry 1 }

  vsmCardSubunitIndex OBJECT-TYPE
          SYNTAX XylanModuleSubunit
          ACCESS read-only
          STATUS mandatory
          DESCRIPTION
                 "The sub-unit number within module in slot 'n'.
                  For each non-empty slot there will exist a module
                  entry with a chasModuleSubUnit value of base.
                  If the chasModuleType of that chasModuleEntry is
                  hsm, then there may be additional chasModuleEntrys
                  with the same chasModuleSlot value but with
                  chasModuleSubUnit values of hsm1 or hsm2.
                  These are HSM sub-modules.  An HSM module can
                  have up to 2 daughter cards on it. The first position
                  would be denoted by hsm1(2) and the second position is
                  hsm2(3).

                  The general implication of this field is: each occupied
                  slot will have an entry field will be base(1), and may
                  if the module supports daughter cards have entries
                  for which if this field is hsm1(2) or hsm2(3),
                  corresponding to an installed daughter card
                  on the HSM in the specified chasModuleSlot.
                  (and the card type will be listed in chasModuleType).

                  For more information, please see the following CLI command:
                    [Note: There is NO equivalent command in the CLI.]
                  "
          ::= { vsmCardConfEntry 2 }

  vsmCardIpAddr OBJECT-TYPE
          SYNTAX IpAddress
          ACCESS read-write
          STATUS mandatory
          DESCRIPTION
                 "The IP address of the daughter card

                 For more information, please see the following CLI command:
                 voice daughter card slot/daughter_card_number ip address xxx.xxx.xxx.xxx

                 "
          ::= { vsmCardConfEntry 3 }

  vsmCardIpMask    OBJECT-TYPE
          SYNTAX IpAddress
          ACCESS read-write
          STATUS mandatory
          DESCRIPTION
                 "The IP mask of the daughter card

                 For more information, please see the following CLI command:
                voice daughter card slot/daughter_card_number ip mask xxx.xxx.xxx.xxx

                 "
          ::= { vsmCardConfEntry 4 }

  vsmCardIpDefGateway    OBJECT-TYPE
          SYNTAX IpAddress
          ACCESS read-write
          STATUS mandatory
          DESCRIPTION
                 "The IP Default Gateway of the daughter card

                 For more information, please see the following CLI command:
                voice daughter card slot/daughter_card_number ip default gateway xxx.xxx.xxx.xxx

                 "
          ::= { vsmCardConfEntry 5}

  vsmCardFirstDigitWaitDur OBJECT-TYPE
          SYNTAX INTEGER (1..2147483647)
          --UNITS milliseconds
          ACCESS           read-write
          STATUS           mandatory
          DESCRIPTION
                 "Time between off-hook and when the first dial digit is entered.
                 At expiration, causes a no digits received error condition to
                 occur, this in turn, causes the numbering plan lookup to fail.  This
                 object has a range of 100 to 65500 milliseconds, in increments
                 of 100 ms.

                 For more information, please see the following CLI command:
                  voice daughter card slot/daughter_card_number first digit wait duration  (1..4294967295)
                 "
          DEFVAL { 10000 }
          ::= { vsmCardConfEntry 6 }

  vsmCardInterDigitWaitDur OBJECT-TYPE
          SYNTAX INTEGER (1..2147483647)
          --UNITS milliseconds
          ACCESS read-write
          STATUS mandatory
          DESCRIPTION
                 "The maximum time allowed between entry of each digit after the
                 first digit. At expiration, assumes that the user is done entering
                 digits, and causes the numbering plan to attempt a match.  This
                 object has a range of 100 to 65500 milliseconds, in increments
                 of 100 ms.

                 For more information, please see the following CLI command:
                  voice daughter card slot/daughter_card_number inter digit wait duration  (1..4294967295)"
          DEFVAL { 5000 }
          ::= { vsmCardConfEntry 7 }

  vsmCardDialTimeDur OBJECT-TYPE
          SYNTAX INTEGER (1..2147483647)
          --UNITS milliseconds
          ACCESS read-write
          STATUS mandatory
          DESCRIPTION
                 "The maximum time allowed for entry of the entire string of
                 dialed digits if no other dial string terminating condition
                 is declared.  At expiration, assumes that the user is done
                 entering digits, and causes the numbering plan to attempt a
                 match.  This object has a range of 100 to 65500 milliseconds,
                 in increments of 100 ms.

                 For more information, please see the following CLI command:
                  voice daughter card slot/daughter_card_number dial time duration (1..4294967295)
                                    "
          DEFVAL { 30000 }
          ::= { vsmCardConfEntry 8 }

  vsmCardTermDigitStr OBJECT-TYPE
          SYNTAX DisplayString
          ACCESS read-write
          STATUS mandatory
          DESCRIPTION
                 "A NULL for the string disables dial termination
                 string detection.
                 This object is only a 1 digit string.  Any valid digit: 0, 1,
                 2, 3, 4, 5, 6, 7, 8, 9, a, b, c, d, * or #.
                 The Dial Terminating Digit is used for the purpose of
                 determining when the dial process is complete. When this
                 digit is received, ignore all digits entered after it.
                 Upon receiving this digit, causes the numbering plan to
                 attempt a match with the digits received before this
                 terminating digit.  The Dial Terminating Digit can not
                 be part of a valid number. All the digits dialed until the Dial
                 Terminating Digit are considered valid and the Dial Terminating
                 Digit is discarded.

                 For more information, please see the following CLI command:
                    voice daughter card slot/daughter_card_number no termination digit
                    voice daughter card slot/daughter_card_number termination digit 0
                    voice daughter card slot/daughter_card_number termination digit 1
                    voice daughter card slot/daughter_card_number termination digit 2
                    voice daughter card slot/daughter_card_number termination digit 3
                    voice daughter card slot/daughter_card_number termination digit 4
                    voice daughter card slot/daughter_card_number termination digit 5
                    voice daughter card slot/daughter_card_number termination digit 6
                    voice daughter card slot/daughter_card_number termination digit 7
                    voice daughter card slot/daughter_card_number termination digit 8
                    voice daughter card slot/daughter_card_number termination digit 9
                    voice daughter card slot/daughter_card_number termination digit #
                    voice daughter card slot/daughter_card_number termination digit *

              Note: The following are not supported in this Release.
                voice daughter card slot/daughter_card_number termination digit A
                voice daughter card slot/daughter_card_number termination digit B
                voice daughter card slot/daughter_card_number termination digit C
                voice daughter card slot/daughter_card_number termination digit D
                "
          ::= { vsmCardConfEntry 9 }


  vsmCardH323InFastStart OBJECT-TYPE
          SYNTAX VsmEnableDisabled
          ACCESS read-write
          STATUS mandatory
          DESCRIPTION
                 "This command is used to select the H.323 Fast Start mode on
                 the incoming side of the link.

                 For more information, please see the following CLI command:
                    voice daughter card slot/daughter_card_number h.323 in[coming] fast start on
                    voice daughter card slot/daughter_card_number h.323 in[coming] fast start off
                 "
          DEFVAL { enabled }
          ::= { vsmCardConfEntry 10 }

  vsmCardH323OutFastStart OBJECT-TYPE
          SYNTAX VsmEnableDisabled
          ACCESS read-write
          STATUS mandatory
          DESCRIPTION
                 "This command is used to select the H.323 Fast Start mode on
                 the outgoing side of the link.

                 For more information, please see the following CLI command:
                 voice daughter card slot/daughter_card_number h.323 out[going] fast start on
                 voice daughter card slot/daughter_card_number h.323 out[going] fast start off
                 "
          DEFVAL { enabled }
          ::= { vsmCardConfEntry 11 }

  vsmCardH323AutomaticAnswer OBJECT-TYPE
        SYNTAX VsmEnableDisabled
        ACCESS read-write
        STATUS mandatory
        DESCRIPTION
        "
        This command is used to select the H.323 automatic call answering mode on the incoming side
        of the link. If on then the call is connected automatically for instant voice.

        For more information, please see the following CLI command:
                 voice daughter card slot/daughter_card_number h.323 auto[matic] answer on
                 voice daughter card slot/daughter_card_number h.323 auto[matic] answer off
        "
        DEFVAL {disabled}
        ::= { vsmCardConfEntry 12 }

  vsmCardConfigStatus OBJECT-TYPE
          SYNTAX INTEGER {
                        activate                (1),
                        active                  (2),
                        inactive                (3),
                        invalid                 (4)
                        }
          ACCESS read-write
          STATUS mandatory
          DESCRIPTION
                 "This object has one writable state called activate, This will
                 force the configured row to become the active configuration for
                 the specified card.  This object can be read to determine the
                 current state of the row.  If the row has not been activated,
                 by default, the state is inactive.  If the row has been activated
                 and the configuration is good, then this object transitions to active.
                 If the row has been activated and the configuration is not good
                 then this object transitions to invalid.

                 For more information, please see the following CLI command:
                  voice daughter card slot/daughter_card_number activate
                 "
         ::= { vsmCardConfEntry 13 }

--======================================================================
--
--       Port Physical Configuration Table
--
-- This table contains information that is configurable on a per
-- physical port connection on each VSM daughter card.
-- The information is indexed by ifindex.
--
--======================================================================

  vsmPortConfTable OBJECT-TYPE
          SYNTAX SEQUENCE OF VsmPortConfEntry
          ACCESS not-accessible
          STATUS mandatory
          DESCRIPTION
                 "This table contains VSM local interface
                  configuration parameters, one entry per VSM
                  physical port.
                  "
          ::= { vsmPhysicalGroup 2 }

  vsmPortConfEntry OBJECT-TYPE
          SYNTAX VsmPortConfEntry
          ACCESS not-accessible
          STATUS mandatory
          DESCRIPTION
                 "This list contains VSM interface configuration
                  parameters and state variables.

                  For more information, please see the following CLI command:
                    [Note: There is NO equivalent command in the CLI.]
                  "
          INDEX { vsmPortSlotNum,
                          vsmPortNum }
          ::= { vsmPortConfTable 1 }

  VsmPortConfEntry        ::= SEQUENCE  {
        vsmPortSlotNum                    INTEGER,
        vsmPortNum                        INTEGER,
        vsmPortInterfaceType              INTEGER,
        vsmPortDialType                   INTEGER,
        vsmPortDsx1LineType                   INTEGER,
        vsmPortDsx1LineCoding                 INTEGER,
        vsmPortDsx1SendCode                   INTEGER,
        vsmPortDsx1CircuitIdentifier          DisplayString,
        vsmPortDsx1LoopbackConfig             INTEGER,
        vsmPortDsx1LineStatus                 INTEGER,
        vsmPortDsx1SignalMode                 INTEGER,
        vsmPortDsx1TransmitClockSource        INTEGER,
        vsmPortDsx1Fdl                        INTEGER,
        vsmPortDsx1LineBuildOut               INTEGER,
        vsmPortDsx1CableType                  INTEGER,
        vsmPortDsx1LineLength                 INTEGER,
        vsmPortDsx1LineStatusChangeTrapEnable INTEGER,
        vsmPortDsx1LoopbackStatus             INTEGER,
        vsmPortDsx1PortFdlRole                INTEGER,
        vsmPortDsx1PortNfasAlign              INTEGER,
        vsmPortDsx1PortAttenuation         INTEGER,
        vsmPortIsdnProtocol                   INTEGER,
        vsmPortIsdnSwitchType                 INTEGER
        }

  vsmPortSlotNum OBJECT-TYPE
          SYNTAX INTEGER
          ACCESS read-only
          STATUS mandatory
          DESCRIPTION
                 "The ifIndex for this Port in the interfaces table.

                  For more information, please see the following CLI command:
                    [Note: There is NO equivalent command in the CLI.]
                 "
          ::= { vsmPortConfEntry 1 }

  vsmPortNum OBJECT-TYPE
          SYNTAX INTEGER
          ACCESS read-only
          STATUS mandatory
          DESCRIPTION
                 "The ifIndex for this Port in the interfaces table.

                  For more information, please see the following CLI command:
                    [Note: There is NO equivalent command in the CLI.]
                 "
          ::= { vsmPortConfEntry 2 }

  vsmPortInterfaceType OBJECT-TYPE
          SYNTAX INTEGER {
                        t1                      (1),
                        e1                      (2),
                        prie1                   (3),  -- not in this release
                        e1IsdnPri               (4),
                        briEuro                 (5)
                                }
          ACCESS read-only
          STATUS mandatory
          DESCRIPTION
                        "The interface type of this port.  This is used to determine
                        the # of channels per port.

                        For more information, please see the following CLI command:
                         voice port slot/port interface type T1
                         voice port slot/port interface type E1
                         voice port slot/port interface type E1 ISDN PRI
                         voice port slot/port interface type BRI EURO
                 "
          DEFVAL {t1}
          ::= { vsmPortConfEntry 3 }

  vsmPortDialType OBJECT-TYPE
          SYNTAX INTEGER {
                tone    (1),
                pulse   (2)
                        }
          ACCESS read-write
          STATUS deprecated
          DESCRIPTION
                "Obsolete"
          ::= { vsmPortConfEntry 4 }

  vsmPortDsx1LineType OBJECT-TYPE
                SYNTAX  INTEGER {
                                 other(1),  -- archiac
                                vsmPortDsx1ESF(2), -- archiac
                                vsmPortDsx1D4(3), -- archiac
                                vsmPortDsx1E1(4),
                                vsmPortDsx1E1-CRC(5),
                                vsmPortDsx1E1-MF(6), -- archiac
                                vsmPortDsx1E1-CRC-MF(7), -- archiac
                                -- vsmPortDsx1Unframed(8),
                                 vsmPortDsx1E1Unframed(8)  -- archiac
                                                                }
                ACCESS  read-write
                STATUS  mandatory
                DESCRIPTION
                                                "This variable indicates  the  variety  of  DS1
                        Line  implementing      this  circuit.  The type of
                        circuit affects the number of bits      per      second
                        that  the circuit can reasonably carry, as well
                        as the interpretation of the  usage      and  error
                        statistics.  The values, in sequence, describe:

                        TITLE:             SPECIFICATION:
                        vsmPortDsx1ESF                 Extended SuperFrame DS1
                        vsmPortDsx1E1                  CCITT Recommendation G.704
                                                                                                                (Table 5a)
                        vsmPortDsx1E1-CRC      CCITT Recommendation G.704
                                                                                                                (Table 5b)
                        vsmPortDsxE1-MF                G.704 (Table 4a) with TS16
                                                                                                                multiframing enabled
                        vsmPortDsx1E1-CRC-MF   G.704 (Table 4b) with TS16
                                                                                                                multiframing enabled
                        vsmPortDsx1Unframed    No Framing performed
                        vsmPortDsx1E1Unframed  E1 with No Framing
                        For clarification, the capacity for each E1 type
                        is as listed below:
                        vsmPortDsx1E1Unframed - E1, no framing = 32 x 64k = 2048k
                        vsmPortDsx1E1 or vsmPortDsx1E1CRC - E1, with framing,
                        no signalling = 31 x 64k = 1984k
                        vsmPortDsx1E1MF or vsmPortDsx1E1CRCMF - E1, with framing,
                        signalling = 30 x 64k = 1920k

                        For further information See CCITT Recomm G.704

                        For more information, please see the following CLI command:
                            voice port slot/port frame format none
                            voice port slot/port frame format superframe
                            voice port slot/port frame format extended superframe
                            voice port slot/port frame format E1
                            voice port slot/port frame format E1 CRC

                        Note: The following are not supported in this Release
                          voice port slot/port frame format E1 MF
                          voice port slot/port frame format E1 CRC MF
                         "
                        DEFVAL {other}
                                ::= { vsmPortConfEntry 5 }


                vsmPortDsx1LineCoding OBJECT-TYPE
                                SYNTAX  INTEGER {
                                                vsmPortDsx1JBZS  (1),  -- archiac
                                                vsmPortDsx1B8ZS  (2),
                                                vsmPortDsx1HDB3  (3),
                                               -- vsmPortDsx1ZBTSI (4),
                                                vsmPortDsx1AMI   (4),
                                                other(5)     -- archiac
                                }
                                ACCESS  read-write
                                STATUS  mandatory
                                DESCRIPTION
                                                "This variable describes the  variety  of  Zero
                                                Code  Suppression  used  on      the link, which in
                                                turn affects a number of its characteristics.

                                                vsmPortDsx1JBZS refers the Jammed  Bit      Zero  Suppres-
                                                sion,  in  which  the  AT&T specification of at
                                                least one pulse every 8 bit periods is literal-
                                                ly      implemented      by forcing a pulse in bit 8 of
                                                each channel.  Thus, only seven bits per  chan-
                                                nel, or 1.344 Mbps, is available for data.

                                                vsmPortDsx1B8ZS refers to the use of a specified  pat-
                                                tern  of  normal  bits  and      bipolar violations
                                                which are used to replace a sequence  of  eight
                                                zero bits.

                                                ANSI Clear Channels may use vsmPortDsx1ZBTSI, or  Zero
                                                Byte Time Slot Interchange.

                                                E1 links, with or without CRC, use vsmPortDsx1HDB3  or
                                                vsmPortDsx1AMI.

                                                vsmPortDsx1AMI refers to a mode wherein no  zero  code
                                                suppression      is      present  and the line encoding
                                                does not solve the problem directly.   In  this
                                                application, the higher layer must provide data
                                                which meets or exceeds the      pulse  density  re-
                                                quirements, such as inverting HDLC data.


                                                For more information, please see the following CLI command:
                                                 voice port slot/port line coding AMI
                                                 voice port slot/port line coding B8ZS
                                                 voice port slot/port line coding HDB3
                                                                        "
                                DEFVAL {vsmPortDsx1JBZS}
                                ::= { vsmPortConfEntry 6 }


                vsmPortDsx1SendCode OBJECT-TYPE
                                SYNTAX  INTEGER {
                                                vsmPortDsx1SendNoCode(1),
                                                vsmPortDsx1SendLineCode(2),
                                                vsmPortDsx1SendPayloadCode(3),
                                                vsmPortDsx1SendResetCode(4),
                                                vsmPortDsx1SendQRS(5),
                                                vsmPortDsx1Send511Pattern(6),
                                                vsmPortDsx1Send3in24Pattern(7),
                                                vsmPortDsx1SendOtherTestPattern(8)   -- other
                                }
                                ACCESS  read-write
                                STATUS  mandatory
                                DESCRIPTION
                                                "This variable indicates what type of  code  is
                                                being sent across the DS1 interface by the dev-
                                                ice.  The values mean:

                                                vsmPortDsx1SendNoCode
                                                                sending looped or normal data

                                                vsmPortDsx1SendLineCode
                                                                sending a request for a line loopback

                                                vsmPortDsx1SendPayloadCode
                                                                sending a request for a payload loopback

                                                vsmPortDsx1SendResetCode
                                                                sending a loopback termination request

                                                vsmPortDsx1SendQRS
                                                                sending a Quasi-Random Signal  (QRS)  test
                                                                pattern

                                                vsmPortDsx1Send511Pattern
                                                                sending a 511 bit fixed test pattern

                                                vsmPortDsx1Send3in24Pattern
                                                                sending a fixed test pattern of 3 bits set
                                                                in 24

                                                vsmPortDsx1SendOtherTestPattern
                                                                sending a test pattern  other  than      those
                                                                described by this object


                                        For more information, please see the following CLI command:
                                         voice port slot/port send code none
                                         voice port slot/port send code line
                                         voice port slot/port send code pay load
                                         voice port slot/port send code reset
                                         voice port slot/port send code quasi
                                         voice port slot/port send code quasi random signal
                                         voice port slot/port send code 511
                                         voice port slot/port send code 511 pattern
                                         voice port slot/port send code 3 in 24
                                         voice port slot/port send code 3 in 24 pattern
                                         voice port slot/port send code other
                                                                "
                                DEFVAL {vsmPortDsx1SendNoCode}
                                ::= { vsmPortConfEntry 7 }


         vsmPortDsx1CircuitIdentifier OBJECT-TYPE
                         SYNTAX  DisplayString (SIZE (0..255))
                         ACCESS  read-write
                         STATUS  mandatory
                         DESCRIPTION
                                "This  variable   contains   the   transmission
                                vendor's circuit identifier, for the purpose of
                                facilitating troubleshooting.

                                For more information, please see the following CLI command:
                                 voice port slot/port circuit identifier 'String'
                                "
                        ::= { vsmPortConfEntry 8 }


         vsmPortDsx1LoopbackConfig OBJECT-TYPE
                         SYNTAX  INTEGER {
                                                 vsmPortDsx1NoLoop(1),
                                                 vsmPortDsx1PayloadLoop(2),
                                                 vsmPortDsx1LineLoop(3),
                                                 vsmDSx1Inward(4),
                                                 vsmPortDsx1OtherLoop(5)  -- archiac
                                         }
                         ACCESS  read-write
                         STATUS  mandatory
                         DESCRIPTION
                                "This variable represents the  loopback  confi-
                                guration of the DS1 interface.  Agents support-
                                ing read/write access should return badValue in
                                response to a requested loopback state that the
                                interface does not support.  The values mean:

                                vsmPortDsx1NoLoop
                                         Not in the loopback state.  A device  that
                                         is not capable of performing a loopback on
                                         the interface shall always return this  as
                                         it's value.

                                vsmPortDsx1PayloadLoop
                                         The received signal at this  interface  is
                                         looped  through  the device. Typically the
                                         received signal is      looped  back  for      re-
                                         transmission  after  it has passed through
                                         the device's framing function.

                                vsmPortDsx1LineLoop
                                         The received signal at this interface does
                                         not  go  through the device (minimum pene-
                                         tration) but is looped back out.

                                vsmPortDsx1OtherLoop
                                         Loopbacks that are not defined here.


                                For more information, please see the following CLI command:
                                 voice port slot/port loop back mode none
                                 voice port slot/port loop back mode payload
                                 voice port slot/port loop back mode line
                                 voice port slot/port loop back mode inward
                                "
                        DEFVAL {vsmPortDsx1NoLoop}
                        ::= { vsmPortConfEntry 9 }


                vsmPortDsx1LineStatus OBJECT-TYPE
                                SYNTAX  INTEGER (1..8191)
                                ACCESS  read-only
                                STATUS  deprecated
                                DESCRIPTION
                                                "This variable indicates the Line Status of the
                                                interface.       It contains loopback, failure, re-
                                                ceived 'alarm'  and transmitted 'alarm'  infor-
                                                mation.

                                                The vsmPortDsx1LineStatus is a bit  map      represented  as  a      sum,
                                                therefore, it can represent multiple failures (alarms) and
                                                a LoopbackState simultaneously.

                                                vsmPortDsx1NoAlarm should be set if and only if no other flag  is
                                                set.

                                                If the vsmPortDsx1LoopbackState bit is set, the loopback  in  ef-
                                                fect can be determined from the vsmPortDsx1LoopbackConfig object.

                                                The various bit positions are:
                                                                1         vsmPortDsx1NoAlarm                   No Alarm Present
                                                                2         vsmPortDsx1RcvFarEndLOF      Far end LOF (a.k.a., Yellow Alarm)
                                                                4         vsmPortDsx1XmtFarEndLOF      Near end sending LOF Indication
                                                                8         vsmPortDsx1RcvAIS                    Far end sending AIS
                                                                16         vsmPortDsx1XmtAIS                        Near end sending AIS
                                                                32         vsmPortDsx1LossOfFrame           Near end LOF (a.k.a., Red Alarm)
                                                                64         vsmPortDsx1LossOfSignal          Near end Loss Of Signal
                                                                128             vsmPortDsx1LoopbackState     Near end is looped
                                                                256             vsmPortDsx1T16AIS                    E1 TS16 AIS
                                                                512             vsmPortDsx1RcvFarEndLOMF     Far End Sending TS16 LOMF
                                                                1024     vsmPortDsx1XmtFarEndLOMF     Near End Sending TS16 LOMF
                                                                2048     vsmPortDsx1RcvTestCode               Near End detects a test code
                                                                4096     vsmPortDsx1OtherFailure      any line status not defined here


                                                For more information, please see the following CLI command:
                                                  {this command is not supported by the CLI}
                                                "
                                ::= { vsmPortConfEntry 10 }


                vsmPortDsx1SignalMode OBJECT-TYPE
                                SYNTAX  INTEGER {
                                                none (1),
                                                cas  (2),
                                                ccs  (3),
                                                -- robbedBit (2),
                                                -- bitOriented (3),
                                                messageOriented (4)
                                                }
                                ACCESS  read-write
                                STATUS  mandatory
                                DESCRIPTION
                                                "'none' indicates that no bits are reserved for
                                                signaling on this channel.

                                                'robbedBit' indicates that T1 Robbed Bit  Sig-
                                                naling is in use.

                                                'bitOriented' indicates that E1 Channel  Asso-
                                                ciated Signaling is in use.

                                                'messageOriented' indicates that Common  Chan-
                                                nel Signaling is in use either on channel 16 of
                                                an E1 link or channel 24 of a T1.

                                                For more information, please see the following CLI command:
                                                 voice port slot/port signaling mode none
                                                 voice port slot/port signaling mode CAS
                                                 voice port slot/port signaling mode CCS
                                                                        "
                        DEFVAL {none}
                                ::= { vsmPortConfEntry 11 }


                vsmPortDsx1TransmitClockSource OBJECT-TYPE
                                SYNTAX  INTEGER {
                                                loopTiming (1),
                                                localTiming (2),
                                                throughTiming (3)
                                                }
                                ACCESS  read-write
                                STATUS  mandatory
                                DESCRIPTION
                                "The source of Tranmit Clock.
                                 'loopTiming' indicates that the recovered  re-
                                ceive clock is used as the transmit clock.

                                 'localTiming' indicates  that  a  local  clock
                                source is used.

                                 'throughTiming' indicates that  recovered  re-
                                ceive  clock  from another interface is used as
                                the transmit clock.

                                For more information, please see the following CLI command:
                                 voice port slot/port transmit clock source loop timing
                                 voice port slot/port transmit clock source local timing
                                "
                        DEFVAL {loopTiming}
                                ::= { vsmPortConfEntry 12 }


                vsmPortDsx1Fdl OBJECT-TYPE
                                SYNTAX  INTEGER {
                                                vsmPortDsx1Fdl-none(1),
                                                vsmPortDsx1Att-54016(2),
                                                vsmPortDsx1Ansi-T1-403(3),
                                                vsmPortDsx1T1-403-ATT(4),
                                                 other(5)  -- archiac
                                                }
                                ACCESS  read-write
                                STATUS  mandatory
                                DESCRIPTION
                                "This bitmap describes the use of  the  facili-
                                ties data link, and is the sum of the capabili-
                                ties:

                                 'other' indicates that a protocol  other  than
                                one following is used.

                                 'vsmPortDsx1Ansi-T1-403' refers to the  FDL  exchange
                                recommended by ANSI.

                                 'vsmPortDsx1Att-54016' refers to ESF FDL exchanges.

                                 'vsmPortDsx1Fdl-none' indicates that the device  does
                                not use the FDL.

                                For more information, please see the following CLI command:
                                 voice port slot/port facilities data link protocol none
                                 voice port slot/port facilities data link protocol AT&T 54016
                                 voice port slot/port facilities data link protocol ANSI T1.403
                                 voice port slot/port facilities data link protocol T1.403 AT&T
                                "
                                DEFVAL {vsmPortDsx1Fdl-none}
                                ::= { vsmPortConfEntry 13 }

                vsmPortDsx1LineBuildOut OBJECT-TYPE
                                SYNTAX  INTEGER {
                                        shortHaul        (1),
                                        longHaul         (2)
                                                }
                                ACCESS  read-write
                                STATUS  mandatory
                                DESCRIPTION
                                        "Indicates line build out of this port.  It's worth noting that only
                                        T1/E1 port with LIU (Line Interface Unit) equipped can support
                                        Long Haul (LH); otherwise, only Short Haul (SH) is supported.

                                        For more information, please see the following CLI command:
                                         voice port slot/port line build out short
                                         voice port slot/port line build out short haul
                                         voice port slot/port line build out long
                                         voice port slot/port line build out long haul
                                                "
                                DEFVAL {shortHaul}
                                ::= { vsmPortConfEntry 14 }

                vsmPortDsx1CableType OBJECT-TYPE
                                SYNTAX  INTEGER {
                                                cable75ohm        (1),
                                                cable120ohm       (2)
                                                }
                                ACCESS  read-write
                                STATUS  mandatory
                                DESCRIPTION
                        "The cable type for this port.

                        For more information, please see the following CLI command:
                                                 voice port slot/port cable type 75
                         voice port slot/port line build out cable type 75
                         voice port slot/port cable type 120
                         voice port slot/port line build out cable type 120
                        "
                                DEFVAL {cable120ohm}
                                ::= { vsmPortConfEntry 15 }

                vsmPortDsx1LineLength OBJECT-TYPE
                                SYNTAX  INTEGER (0..200)
                                ACCESS  read-write
                                STATUS  mandatory
                                DESCRIPTION
                                          "The length of the ds1 line in meters. This
                                          objects provides information for line build out
                                          circuitry if it exists and can use this object to
                                          adjust the line build out.

                                          For more information, please see the following CLI command:
                                           voice port slot/port line length (0..200)
                                           voice port slot/port line build out line length (0..200)
                                          "
                                DEFVAL {30}
                                ::= { vsmPortConfEntry 16 }

                vsmPortDsx1LineStatusChangeTrapEnable OBJECT-TYPE
                                SYNTAX   INTEGER {
                                                enabled(1),
                                                disabled(2)
                                                }
                                ACCESS  read-write
                                STATUS  mandatory
                                DESCRIPTION
                                                "Indicates whether vsmPortDsx1LineStatusChange traps
                                                should be generated for this interface.

                                                For more information, please see the following CLI command:
                                                 voice port slot/port trap generation enable
                                                 voice port slot/port trap generation disable
                                                "
                                DEFVAL { disabled }
                                ::= { vsmPortConfEntry 17 }

                vsmPortDsx1LoopbackStatus OBJECT-TYPE
                                SYNTAX          INTEGER (1..127)
                                ACCESS          read-only
                                STATUS          deprecated
                                DESCRIPTION
                                          "This variable represents the current state of the
                                          loopback on the DS1 interface.  It contains
                                          information about loopbacks established by a
                                          manager and remotely from the far end.

                                          The vsmPortDsx1LoopbackStatus is a bit map represented as
                                          a sum, therefore is can represent multiple
                                          loopbacks simultaneously.

                                          The various bit positions are:
                                           1  vsmPortDsx1NoLoopback
                                           2  vsmPortDsx1NearEndPayloadLoopback
                                           4  vsmPortDsx1NearEndLineLoopback
                                           8  vsmPortDsx1NearEndOtherLoopback
                                          16  vsmPortDsx1NearEndInwardLoopback
                                          32  vsmPortDsx1FarEndPayloadLoopback
                                          64  vsmPortDsx1FarEndLineLoopback

                                          For more information, please see the following CLI command:
                                                {This command is not supported by the CLI}
                                          "
                                ::= { vsmPortConfEntry 18 }

                vsmPortDsx1PortFdlRole OBJECT-TYPE
                                SYNTAX   INTEGER {
                                                network(1),
                                                user(2)
                                                }
                                ACCESS  read-write
                                STATUS  mandatory
                                DESCRIPTION
                                                "Indicates Facility Data Link port role of this
                                                port.  If the port role is network and fdlMode is
                                                set to AT&T 54016, then this port periodically sends
                                                AT&T  performance requests to CI.

                                                For more information, please see the following CLI command:
                                                 voice port slot/port facilities data link port role network
                                                 voice port slot/port facilities data link port role user
                                                                        "
                                DEFVAL { network }
                                ::= { vsmPortConfEntry 19 }

                vsmPortDsx1PortNfasAlign OBJECT-TYPE
                                SYNTAX   INTEGER {
                                                enable(1),
                                                disable(2)
                                                }
                                ACCESS  read-write
                                STATUS  mandatory
                                DESCRIPTION
                                                "This object indicates if framing criterion is based on
                                                bit 2 of Time Slot 0 NOT-FAS.  This object only applies
                                                to E1.

                                                For more information, please see the following CLI command:
                                                 voice port slot/port NFAS framing enable
                                                 voice port slot/port NFAS framing disable
                                                "
                                DEFVAL { disable}
                                ::= { vsmPortConfEntry 20 }

                vsmPortDsx1PortAttenuation OBJECT-TYPE
                                SYNTAX   INTEGER {
                                att1 (1), -- attenuation 0
                                att2 (2), -- attenuation -7.5
                                att3 (3), -- attenuation -15.0
                                att4 (4) -- attenuation -22.5
                                }
                                ACCESS  read-write
                                STATUS  mandatory
                                DESCRIPTION
                                        "attenuation to set for vsmPortDsx1 port.

                                        For more information, please see the following CLI command:
                                         voice port slot/port attenuation 0
                                         voice port slot/port line build out attenuation 0
                                         voice port slot/port attenuation -7.5
                                         voice port slot/port line build out attenuation -7.5
                                         voice port slot/port attenuation -15.0
                                         voice port slot/port line build out attenuation -15.0
                                         voice port slot/port attenuation -22.5
                                         voice port slot/port line build out attenuation -22.5
                                                "
                                DEFVAL { att1 }
                                ::= { vsmPortConfEntry 21 }

                vsmPortIsdnProtocol OBJECT-TYPE
                                SYNTAX INTEGER {
                                                net (1),
                                                user (2),
                                                qmaster (3),
                                                qslave (4)
                                                }
                                ACCESS read-write
                                STATUS mandatory
                                DESCRIPTION
                                        "Configures the isdn mode on the specified Slot/Port combination.

                                        For more information, please see the following CLI command:
                                         voice port slot/port isdn protocol net
                                         voice port slot/port isdn protocol user
                                         voice port slot/port isdn protocol qmaster
                                         voice port slot/port isdn protocol qslave
                                                "
                                DEFVAL { qmaster}
                                ::= { vsmPortConfEntry 22 }

                vsmPortIsdnSwitchType OBJECT-TYPE
                                SYNTAX INTEGER {
                                               net3 (1),   --not suport in this release
                                               net5 (2)
                                                }
                                ACCESS read-write
                                STATUS mandatory
                                DESCRIPTION
                                                "If the object vsmIsdnProtocol is set to user, then this
                                                object specifies the switch the ISDN link is connected to.
                                                If the object vsmIsdnProtocol is set to net, then this
                                                pbject specifies the switch to be emulated.  At present only
                                                net5 is supported for this command.

                                                For more information, please see the following CLI command:
                                                 voice port slot/port isdn switch type net5
                                                "
                                DEFVAL { net5 }
                                ::= { vsmPortConfEntry 23 }



--======================================================================
--
--       Channel Physical Configuration Table
--
-- This table contains information that is configurable on a per physical
-- channel connection on each VSM daughter card.
-- The information is indexed by ifIndex.
--
--======================================================================
  vsmChanConfTable OBJECT-TYPE
          SYNTAX SEQUENCE OF VsmChanConfEntry
          ACCESS not-accessible
          STATUS mandatory
          DESCRIPTION
                 "This table contains VSM local interface
                  configuration parameters, one entry per VSM
                  channel.  A physical port may have multiple channels
                  associated with it, depending on port type.
                   "
          ::= { vsmPhysicalGroup 3 }

  vsmChanConfEntry OBJECT-TYPE
          SYNTAX VsmChanConfEntry
          ACCESS not-accessible
          STATUS mandatory
          DESCRIPTION
                 "This list contains VSM channel configuration
                  parameters and state variables.

                  For more information, please see the following CLI command:
                    [Note: There is NO equivalent command in the CLI.]
                  "
          INDEX { vsmChanSlotIndex,
                          vsmChanPortIndex,
                          vsmChanIndex }
          ::= { vsmChanConfTable  1 }

  VsmChanConfEntry        ::= SEQUENCE  {
        vsmChanSlotIndex                        INTEGER,
        vsmChanPortIndex                        INTEGER,
        vsmChanIndex                            INTEGER,
        vsmChanMode                             INTEGER,
        vsmChanPlarNumber                       DisplayString,
        vsmChanPerferredVoiceProfile            DisplayString,
        vsmChanPerferredFaxProfile              DisplayString,
        vsmChanPerferredModemProfile            DisplayString,
        vsmChanISDNChanType                     INTEGER,
        vsmChanDslId                            INTEGER,
        vsmChanDChannelPort                     INTEGER,
        vsmChanDChannel                         INTEGER,
        vsmChanStatus                           INTEGER
        }

  vsmChanSlotIndex OBJECT-TYPE
          SYNTAX INTEGER
          ACCESS read-only
          STATUS mandatory
          DESCRIPTION
                 "The slot number associated with this row.

                 For more information, please see the following CLI command:
                    [Note: There is NO equivalent command in the CLI.]
                 "
          ::= { vsmChanConfEntry 1 }

  vsmChanPortIndex OBJECT-TYPE
          SYNTAX INTEGER
          ACCESS read-only
          STATUS mandatory
          DESCRIPTION
                 "The port number associated with this row.

                 For more information, please see the following CLI command:
                    [Note: There is NO equivalent command in the CLI.]
                 "
          ::= { vsmChanConfEntry 2 }

  vsmChanIndex OBJECT-TYPE
          SYNTAX INTEGER
          ACCESS read-only
          STATUS mandatory
          DESCRIPTION
                 "The channel number associated with this row.

                 For more information, please see the following CLI command:
                    [Note: There is NO equivalent command in the CLI.]
                 "
          ::= { vsmChanConfEntry 3 }

  vsmChanMode OBJECT-TYPE
          SYNTAX INTEGER {
                                 telephony              (1),
                                 passThrough            (2),
                                 plar                   (3),
                                 wan                    (4)  -- not in this release
                          }
          ACCESS read-write
          STATUS mandatory
          DESCRIPTION
                 "This object Indicates in which mode of operation
                  the channel operates.

                  telephony - The channel processing will be handled by the
                  gateway and normal call processing.

                  passThrough - The channel will be direct connected to the
                  corresponding channel on the other port on the same daughter
                  card. No processing will be done by the gateway or call
                  processor.

                  plar - The channel will automatically initiate dialing when it
                  goes off-hook.  The number to be dialed is specified in
                  vsmChannelPlarNumber.  If no number has been specified,
                  operation will behave as if in telephony mode.

                  wan - The channel will operate in WAN mode.

                  For more information, please see the following CLI command:
                     voice channel slot/port/startChannel-endChannel mode telephony
                     voice channel slot/port/startChannel-endChannel mode plar

                  Note: The following are not supported in this Release.
                     voice channel slot/port/startChannel-endChannel mode pass through
                  "
                 DEFVAL { telephony }
         ::= { vsmChanConfEntry 4 }

  vsmChanPlarNumber OBJECT-TYPE
          SYNTAX DisplayString
          ACCESS  read-write
          STATUS mandatory
          DESCRIPTION
                 "The number to be dialed when the channel goes off-hook,
                 if vsmChannelType has been set to 'plar'.

                 For more information, please see the following CLI command:
                  voice channel slot/port/startChannel-endChannel dial in private line automatic ringdown 'plar_phone_number'
                 "
          ::= { vsmChanConfEntry 5 }

  vsmChanPerferredVoiceProfile OBJECT-TYPE
          SYNTAX DisplayString
          ACCESS read-write
          STATUS mandatory
          DESCRIPTION
                 "Sets the preferred coding profile to use for voice calls
                 on the specified channel.

                 For more information, please see the following CLI command:
                  voice channel slot/port/startChannel-endChannel assign preferred voice coding profile 'codingProfName'
                 "
          ::= { vsmChanConfEntry 6 }

  vsmChanPerferredFaxProfile OBJECT-TYPE
          SYNTAX DisplayString
          ACCESS read-write
          STATUS mandatory
          DESCRIPTION
                 "Sets the preferred coding profile to use for fax calls
                 on the specified channel.

                 For more information, please see the following CLI command:
                  voice channel slot/port/startChannel-endChannel assign preferred fax coding profile 'codingProfName'
                 "
          ::= { vsmChanConfEntry 7 }

  vsmChanPerferredModemProfile OBJECT-TYPE
          SYNTAX DisplayString
          ACCESS  read-write
          STATUS mandatory
          DESCRIPTION
                 "Sets the preferred coding profile to use for modem calls
                 on the specified channel.

                 For more information, please see the following CLI command:
                  voice channel slot/port/startChannel-endChannel assign preferred modem coding profile 'codingProfName'
                 "
          ::= { vsmChanConfEntry 8 }

  vsmChanISDNChanType OBJECT-TYPE
          SYNTAX INTEGER {
                                 dchannel               (1),
                                 bchannel               (2),
                                 none                   (3)
                          }
          ACCESS read-only
          STATUS mandatory
          DESCRIPTION
                          "This object sets the channel specified by the slot/port/channel indices
                                  as either a dchannel or bchannel or none if the channel is not yet
                                  configured.  This object is only valid is the signaling protocol for this
                                  channel is set to ISDN.  If this object is set to bchannel, then the
                                  objects vsmChanDChannelPort and vsmChanDChannel must also be specifeid
                           For more information, please see the following CLI command:
                            voice channel slot/port/channel isdn b channel port/dchannel dsl_id
                           "
                 DEFVAL { bchannel}
         ::= { vsmChanConfEntry 9 }

  vsmChanDslId OBJECT-TYPE
          SYNTAX INTEGER
          ACCESS read-write
          STATUS deprecated
          DESCRIPTION
                  "deprecated"
                 
         ::= { vsmChanConfEntry 10 }

  vsmChanDChannelPort OBJECT-TYPE
          SYNTAX INTEGER
          ACCESS read-write
          STATUS deprecated
          DESCRIPTION
                  "deprecated"
                 
         ::= { vsmChanConfEntry 11 }

  vsmChanDChannel OBJECT-TYPE
          SYNTAX INTEGER
          ACCESS read-write
          STATUS deprecated
          DESCRIPTION
                                  "deprecated "
         ::= { vsmChanConfEntry 12 }

  vsmChanStatus OBJECT-TYPE
          SYNTAX INTEGER {
                                activate                (1),
                                deactivate              (2),
                                in-service              (3),
                                out-of-service          (4),
                                invalid                 (5)
                                }
          ACCESS read-write
          STATUS mandatory
          DESCRIPTION
                 "This object controls the state of the channel configuration
                 when writing to this object.  The channel can be put into service
                 by setting this object to activate.  The channel can be taken
                 out of service by setting this object to deactivate.  The actual
                 status of the channel can be read from this object.  The
                 channel is in out-of-service by default.
                 If the channel is activated and all configuration
                 is good, then the channel is in-service.  If the channel is activated
                 and something is wrong with the configuration, then the channel
                 state is invalid.

                 For more information, please see the following CLI command:
                  voice channel slot/port/startChannel-endChannel state in service
                  voice channel slot/port/startChannel-endChannel state out of service
                 "
                 DEFVAL { out-of-service }
          ::= { vsmChanConfEntry 13 }


--======================================================================
--
--       Allowed Coding Profiles Table
--
-- This table allows coding profiles to be available to a channel.
--
--
--======================================================================
  vsmAllowedCodingProfileTable OBJECT-TYPE
          SYNTAX SEQUENCE OF VsmAllowedCodingProfileEntry
          ACCESS not-accessible
          STATUS mandatory
          DESCRIPTION
                 "This table makes available defined coding profiles to
                 channels.
                 "
          ::= { vsmPhysicalGroup 4 }

  vsmAllowedCodingProfileEntry OBJECT-TYPE
          SYNTAX VsmAllowedCodingProfileEntry
          ACCESS not-accessible
          STATUS mandatory
          DESCRIPTION
                 "This list contains VSM channel configuration
                  parameters and state variables.

                  For more information, please see the following CLI command:
                    [Note: There is NO equivalent command in the CLI.]
                  "
          INDEX { vsmChanSlotIndex,
                          vsmChanPortIndex,
                          vsmChanIndex,
                          vsmCodingProfName }
          ::= { vsmAllowedCodingProfileTable  1 }

  VsmAllowedCodingProfileEntry    ::= SEQUENCE  {
        vsmAllowedCodingProfileRowStatus        RowStatus
   }


  vsmAllowedCodingProfileRowStatus OBJECT-TYPE
          SYNTAX RowStatus
          ACCESS read-write
          STATUS mandatory
          DESCRIPTION
                 "This object is the RowStatus (locking flag) for creating the
                 vsmAllowedCodingProfileTable conceptual row.

                 Note: destroy(6) is not supported in this release. 

                 For more information, please see the following CLI command:
                    voice channel slot/port/startChannel-endChannel available coding profile 'codingProfName'
                    voice channel slot/port/startChannel-endChannel unavailable coding profile 'codingProfName'
                 "
          ::= { vsmAllowedCodingProfileEntry 1 }

--======================================================================
--======================================================================
--
--      The VSM ConfigControlGroup
--
--=====================================================================
--== Note: vsmConfigControlGroup  OBJECT IDENTIFIER ::= { xylanVsmArch 6 }
--======================================================================

 vsmConfigDumpFlag OBJECT-TYPE 
    SYNTAX INTEGER 
    ACCESS read-write
    STATUS mandatory
    DESCRIPTION  "Set to 1 makes vsm ascii configuration to dump"
    ::= { vsmConfigControlGroup 1 }

 vsmConfigRebootFlag OBJECT-TYPE 
    SYNTAX INTEGER 
    ACCESS read-write
    STATUS mandatory
    DESCRIPTION  "Set to 1 makes switch to reboot"
    ::= { vsmConfigControlGroup 2 }

 vsmConfigDumpFileName OBJECT-TYPE 
    SYNTAX  DisplayString  (SIZE (0..12))
    ACCESS  read-write
    STATUS  mandatory
    DESCRIPTION "Name of vsm ascii configuration dump file"
    ::= { vsmConfigControlGroup 3 }


--=======================================================================
--==
--== Statistics Group
--==
--=======================================================================
--== Note: The vsmStatsGroup is not supported in this release !
--=======================================================================
--== Note: vsmStatsGroup OBJECT IDENTIFIER ::= { xylanVsmArch 7 }
--=======================================================================

--=======================================================================
--
-- Telephony Channel Levels Table
--
--=======================================================================
--==  Note: This table is not supported in this release !
--=======================================================================

        vsmTeleLevelTable OBJECT-TYPE
                SYNTAX  SEQUENCE OF VsmTeleLevelEntry
                ACCESS  not-accessible
                STATUS  mandatory
                DESCRIPTION
                        "Telephone channel transmit and receive levels by
                        slot/port/channel.  Displays the current and mean transmit and
                        receive levels at the PCM interface of the DSP.  Rx means
                        received from the telephony interface; Tx means transmitted
                        to that interface.  Current levels are given in 0.1 dBm0 unis.
                        Mean values are given in 0.1 linear PCM units.

                        For more information, please see the following CLI command:
                           voice channel slot/port/channel telephony level stat[istic]s  view
                        "
                ::= { vsmStatsGroup 1 }

        vsmTeleLevelEntry OBJECT-TYPE
                SYNTAX   VsmTeleLevelEntry
                ACCESS   not-accessible
                STATUS   mandatory
                DESCRIPTION
                        "Individual Telephone Channel Level Entry.

                  For more information, please see the following CLI command:
                    [Note: There is NO equivalent command in the CLI.]
                        "
                INDEX {
                        vsmChanSlotIndex,
                        vsmChanPortIndex,
                        vsmChanIndex
                        }
                ::= { vsmTeleLevelTable 1 }

        VsmTeleLevelEntry ::=
                SEQUENCE {
                        vsmTeleLevelRx                  INTEGER,
                        vsmTeleLevelTx                  INTEGER,
                        vsmTeleLevelRxMean              INTEGER,
                        vsmTeleLevelTxMean              INTEGER
                        }

        vsmTeleLevelRx OBJECT-TYPE
                SYNTAX  INTEGER
                ACCESS  read-only
                STATUS  mandatory
                DESCRIPTION
                        "The receive level at the PCM inteface of the DSP.  Current
                        Levels are given in 0.1 dBm. "
                ::= { vsmTeleLevelEntry 1 }


        vsmTeleLevelTx OBJECT-TYPE
                SYNTAX  INTEGER
                ACCESS  read-only
                STATUS  mandatory
                DESCRIPTION
                        "The transmit level at the PCM interface of the DSP.  Current
                        Levels are given in 0.1 dBm."
                ::= { vsmTeleLevelEntry 2 }


        vsmTeleLevelRxMean OBJECT-TYPE
                SYNTAX  INTEGER
                ACCESS  read-only
                STATUS  mandatory
                DESCRIPTION
                        "The receive level at the PCM interface givben in 0.1 linear
                        PCM units.  Mean values are in 0.1 linear PCM units.

                        For more information, please see the following CLI command:
                          [Note: This object is not supported in this Release]
                        "
                ::= { vsmTeleLevelEntry 3 }


        vsmTeleLevelTxMean OBJECT-TYPE
                SYNTAX  INTEGER
                ACCESS  read-only
                STATUS  mandatory
                DESCRIPTION
                        "The transmit level at the PCM interface in 0.1 linear
                        PCM units.  Mean values are in 0.1 linear PCM units."
                ::= { vsmTeleLevelEntry 4 }


--=======================================================================
--
-- Telephone Channel Statistics Table
--
--=======================================================================
--=======================================================================

        vsmTeleStatsTable OBJECT-TYPE
                SYNTAX  SEQUENCE OF VsmTeleStatsEntry
                ACCESS  not-accessible
                STATUS  mandatory
                DESCRIPTION
                        "Telephone channel statistics by slot/port/channel.

                        For more information, please see the following CLI command:
                           voice channel slot/port/channel telephony channel stat[istic]s view
                        "
                ::= { vsmStatsGroup 2 }

        vsmTeleStatsEntry OBJECT-TYPE
                SYNTAX   VsmTeleStatsEntry
                ACCESS   not-accessible
                STATUS   mandatory
                DESCRIPTION
                        "Individual Telephone Channel Statistics Entry.

                  For more information, please see the following CLI command:
                    [Note: There is NO equivalent command in the CLI.]

                        "
                INDEX {
                        vsmChanSlotIndex,
                        vsmChanPortIndex,
                        vsmChanIndex
                        }
                ::= { vsmTeleStatsTable 1 }

        VsmTeleStatsEntry ::=
                SEQUENCE {
                        vsmNumOffHooks                  INTEGER,
                        vsmNumOnHooks                   INTEGER,
                        vsmNumSeizures                  INTEGER,
                        vsmNumToneDigits                INTEGER,
                        vsmNumPulseDigits               INTEGER,
			vsmResetTeleStats		INTEGER
                        }

        vsmNumOffHooks OBJECT-TYPE
                SYNTAX  INTEGER
                ACCESS  read-only
                STATUS  mandatory
                DESCRIPTION
                        "The number of times an off-hook indication was detected."
                ::= { vsmTeleStatsEntry 1 }

        vsmNumOnHooks OBJECT-TYPE
                SYNTAX  INTEGER
                ACCESS  read-only
                STATUS  mandatory
                DESCRIPTION
                        "The number of times an on-hook indication was detected."
                ::= { vsmTeleStatsEntry 2 }

        vsmNumSeizures OBJECT-TYPE
                SYNTAX  INTEGER
                ACCESS  read-only
                STATUS  mandatory
                DESCRIPTION
                        "The number of seizures detected on a channel."
                ::= { vsmTeleStatsEntry 3 }

        vsmNumToneDigits OBJECT-TYPE
                SYNTAX  INTEGER
                ACCESS  read-only
                STATUS  mandatory
                DESCRIPTION
                        "The number of tone digits detected"
                ::= { vsmTeleStatsEntry 4 }	

        vsmNumPulseDigits OBJECT-TYPE
                SYNTAX  INTEGER
                ACCESS  read-only
                STATUS  mandatory
                DESCRIPTION
                        "The number of good pulse digits detected."
                ::= { vsmTeleStatsEntry 5 }	    

        vsmResetTeleStats OBJECT-TYPE
                SYNTAX  INTEGER
                ACCESS  write-only
		STATUS  mandatory
                DESCRIPTION
                        "Any write operation on this field will 
			 reset the telephony statistics for the specified slot/port/channel"
                ::= { vsmTeleStatsEntry 6 }	  

--=======================================================================
--
-- DSP Voice Playout Statistics Table
--
--=======================================================================
--=======================================================================

        vsmDspVPStatsTable OBJECT-TYPE
                SYNTAX  SEQUENCE OF VsmDspVPStatsEntry
                ACCESS  not-accessible
                STATUS  mandatory
                DESCRIPTION
                        "DSP voice playout statistics by slot/port/channel.

                        For more information, please see the following CLI command:
                           voice channel slot/port/channel voice play out stat[istic]s view
                        "
                ::= { vsmStatsGroup 3 }

        vsmDspVPStatsEntry OBJECT-TYPE
                SYNTAX   VsmDspVPStatsEntry
                ACCESS   not-accessible
                STATUS   mandatory
                DESCRIPTION
                        "Individual DSP voice playout statistics entry.

                  For more information, please see the following CLI command:
                    [Note: There is NO equivalent command in the CLI.]
                        "
                INDEX {
                        vsmChanSlotIndex,
                        vsmChanPortIndex,
                        vsmChanIndex
                        }
                ::= { vsmDspVPStatsTable 1 }

        VsmDspVPStatsEntry ::=
                SEQUENCE {
                        vsmDspAvgPlayoutDelay           INTEGER,
                        vsmDspLostPackets               INTEGER,
                        vsmDspReplayPackets             INTEGER,
                        vsmDspIdlePackets               INTEGER,
                        vsmDspDroppedPackets            INTEGER,
                        vsmDspReceivedPackets           INTEGER,
                        vsmDspRxAvgFrameJitter          INTEGER,
			vsmResetDspPlayOutStats         INTEGER
                        }

        vsmDspAvgPlayoutDelay OBJECT-TYPE
                SYNTAX  INTEGER
                ACCESS  read-only
                STATUS  mandatory
                DESCRIPTION
                        "The average delay of the voice playout FIFOin the DSP, in milliseconds."
                ::= { vsmDspVPStatsEntry 1 }

        vsmDspLostPackets OBJECT-TYPE
                SYNTAX  INTEGER
                ACCESS  read-only
                STATUS  mandatory
                DESCRIPTION
                        "The number of lost packets in teh DSP based on missing sequence number."
                ::= { vsmDspVPStatsEntry 2 }

        vsmDspReplayPackets OBJECT-TYPE
                SYNTAX  INTEGER
                ACCESS  read-only
                STATUS  mandatory
                DESCRIPTION
                        "The number of packets replayed by the DSP due to lost packets."
                ::= { vsmDspVPStatsEntry 3 }

        vsmDspIdlePackets OBJECT-TYPE
                SYNTAX  INTEGER
                ACCESS  read-only
                STATUS  mandatory
                DESCRIPTION
                        "The number of idle packets being played out by the DSP due to
                        either lost packets or voice playout FIFO buffer underrun."
                ::= { vsmDspVPStatsEntry 4 }

        vsmDspDroppedPackets OBJECT-TYPE
                SYNTAX  INTEGER
                ACCESS  read-only
                STATUS  mandatory
                DESCRIPTION
                        "The number of voice packets dropped by the DSP due to the voice
                        playout FIFO buffer overrun."
                ::= { vsmDspVPStatsEntry 5 }

        vsmDspReceivedPackets OBJECT-TYPE
                SYNTAX  INTEGER
                ACCESS  read-only
                STATUS  mandatory
                DESCRIPTION
                        "The number of packets being submitted by packetization unit
                        in the DSP for playout."
                ::= { vsmDspVPStatsEntry 6 }

        vsmDspRxAvgFrameJitter OBJECT-TYPE
                SYNTAX  INTEGER
                ACCESS  read-only
                STATUS  mandatory
                DESCRIPTION
                        "The average recieve jitter on a frame in the DSP in milliseconds."
                ::= { vsmDspVPStatsEntry 7 }

        vsmResetDspPlayOutStats OBJECT-TYPE
                SYNTAX  INTEGER
                ACCESS  write-only
		STATUS  mandatory
                DESCRIPTION
                        "Any write operation on this field will 
			 reset DSP play out statistics for the specified slot/port/channel"
                ::= { vsmDspVPStatsEntry 8 }	

--=======================================================================
--
-- DSP Receive and Transmit Statistics Table
--
--=======================================================================
--=======================================================================

        vsmDspRxTxStatsTable OBJECT-TYPE
                SYNTAX  SEQUENCE OF VsmDspRxTxStatsEntry
                ACCESS  not-accessible
                STATUS  mandatory
                DESCRIPTION
                        "DSP receive and transmit statistics by slot/port/channel.

                        For more information, please see the following CLI command:
                           voice channel slot/port/channel dsp stat[istic]s view
                        "
                ::= { vsmStatsGroup 4 }

        vsmDspRxTxStatsEntry OBJECT-TYPE
                SYNTAX   VsmDspRxTxStatsEntry
                ACCESS   not-accessible
                STATUS   mandatory
                DESCRIPTION
                        "Individual DSP receive and transmit statistics entry.

                  For more information, please see the following CLI command:
                    [Note: There is NO equivalent command in the CLI.]
                        "
                INDEX {
                        vsmChanSlotIndex,
                        vsmChanPortIndex,
                        vsmChanIndex
                        }
                ::= { vsmDspRxTxStatsTable 1 }

        VsmDspRxTxStatsEntry ::=
                SEQUENCE {
                        vsmDspRxPackets                         INTEGER,
                        vsmDspTxPackets                         INTEGER,
                        vsmDspSilencePackets                    INTEGER,
                        vsmDspRxMinJitter                       INTEGER,
                        vsmDspRxMaxJitter                       INTEGER,
                        vsmDspRxAvgJitter                       INTEGER,
                        vsmTxDroppedFrames                      INTEGER,
                        vsmTxOctets                             INTEGER,
                        vsmRxOctets                             INTEGER,
			vsmAal2CodPrfChgs    			INTEGER,
			vsmDtmfTxOctets                         INTEGER,
			vsmDtmfRxOctets                         INTEGER,
			vsmResetDspRxTxStats                    INTEGER 
                        }


        vsmDspRxPackets OBJECT-TYPE
                SYNTAX  INTEGER
                ACCESS  read-only
                STATUS  mandatory
                DESCRIPTION
                        "The number of voice packets received that are sent for playout."
                ::= { vsmDspRxTxStatsEntry 1 }

        vsmDspTxPackets OBJECT-TYPE
                SYNTAX  INTEGER
                ACCESS  read-only
                STATUS  mandatory
                DESCRIPTION
                        "The number of voice packets that are written into the data
                        buffer to be transmitted."
                ::= { vsmDspRxTxStatsEntry 2 }

        vsmDspSilencePackets OBJECT-TYPE
                SYNTAX  INTEGER
                ACCESS  read-only
                STATUS  mandatory
                DESCRIPTION
                        "The number of voice packets on the transmit side that were
                        classified as silence."
                ::= { vsmDspRxTxStatsEntry 3 }

        vsmDspRxMinJitter OBJECT-TYPE
                SYNTAX  INTEGER
                ACCESS  read-only
                STATUS  mandatory
                DESCRIPTION
                        "Minimum packet interarrival time specified in milliseconds."
                ::= { vsmDspRxTxStatsEntry 4 }

        vsmDspRxMaxJitter OBJECT-TYPE
                SYNTAX  INTEGER
                ACCESS  read-only
                STATUS  mandatory
                DESCRIPTION
                        "Maximum packet interarrival time specified in milliseconds."
                ::= { vsmDspRxTxStatsEntry 5 }

        vsmDspRxAvgJitter OBJECT-TYPE
                SYNTAX  INTEGER
                ACCESS  read-only
                STATUS  mandatory
                DESCRIPTION
                        "RTP average packet interarrival time in timetimestamp units."
                ::= { vsmDspRxTxStatsEntry 6 }

        vsmTxDroppedFrames OBJECT-TYPE
                SYNTAX  INTEGER
                ACCESS  read-only
                STATUS  mandatory
                DESCRIPTION
                        "The number of basic frames lost due to resync requests."
                ::= { vsmDspRxTxStatsEntry 7 }

        vsmTxOctets OBJECT-TYPE
                SYNTAX  INTEGER
                ACCESS  read-only
                STATUS  mandatory
                DESCRIPTION
                        "The number of octets transmitted by the DSP."
                ::= { vsmDspRxTxStatsEntry 8 }

        vsmRxOctets OBJECT-TYPE
                SYNTAX  INTEGER
                ACCESS  read-only
                STATUS  mandatory
                DESCRIPTION
                        "The number of octets received by the DSP."
                ::= { vsmDspRxTxStatsEntry 9 }

        vsmAal2CodPrfChgs OBJECT-TYPE
                SYNTAX  INTEGER
                ACCESS  read-only
                STATUS  mandatory
                DESCRIPTION
                        "The number of AAL2 coding profile chnages"
                ::= { vsmDspRxTxStatsEntry 10 }

        vsmDtmfTxOctets OBJECT-TYPE
                SYNTAX  INTEGER
                ACCESS  read-only
                STATUS  mandatory
                DESCRIPTION
                        "The number of DTMF trasmitted octets"
                ::= { vsmDspRxTxStatsEntry 11 }

	vsmDtmfRxOctets OBJECT-TYPE
                SYNTAX  INTEGER
                ACCESS  read-only
                STATUS  mandatory
                DESCRIPTION
                        "The number of DTMF received octets"
                ::= { vsmDspRxTxStatsEntry 12 }

        vsmResetDspRxTxStats OBJECT-TYPE
                SYNTAX  INTEGER
                ACCESS  write-only
		STATUS  mandatory
                DESCRIPTION
                        "Any write operation on this field will 
			 reset DSP Rx Tx statistics for the specified slot/port/channel"
                ::= { vsmDspRxTxStatsEntry 13 }	

--=======================================================================
--
-- DSP Voice Error Statistics Table
--
--=======================================================================
--==  Note: This table is not supported in this release !
--=======================================================================

        vsmDspVoiceErrorStatsTable OBJECT-TYPE
                SYNTAX  SEQUENCE OF VsmDspVoiceErrorStatsEntry
                ACCESS  not-accessible
                STATUS  mandatory
                DESCRIPTION
                        "DSP voice error statistics by slot/port/channel.

                        For more information, please see the following CLI command:
                           voice channel slot/port/channel error stat[istic]s view
                        "
                ::= { vsmStatsGroup 5 }

        vsmDspVoiceErrorStatsEntry OBJECT-TYPE
                SYNTAX   VsmDspVoiceErrorStatsEntry
                ACCESS   not-accessible
                STATUS   mandatory
                DESCRIPTION
                        "Individual DSP voice error statistics entry.

                  For more information, please see the following CLI command:
                    [Note: There is NO equivalent command in the CLI.]
                        "
                INDEX {
                        vsmChanSlotIndex,
                        vsmChanPortIndex,
                        vsmChanIndex
                        }
                ::= { vsmDspVoiceErrorStatsTable 1 }

        VsmDspVoiceErrorStatsEntry ::=
                SEQUENCE {
                        vsmDspInvalidHeaderCount                        INTEGER,
                        vsmDspMicroOverflowCount                        INTEGER,
                        vsmDspLostEnhPackets                            INTEGER,
                        vsmDspMissingCorePackets                        INTEGER,
                        vsmDspPktsLostByNetwork                         INTEGER,
			vsmResetDspErrorStats                           INTEGER
                        }


        vsmDspInvalidHeaderCount OBJECT-TYPE
                SYNTAX  INTEGER
                ACCESS  read-only
                STATUS  mandatory
                DESCRIPTION
                        "The number of incomming voice packets dropped by the DSP
                        due to invalid generic voice header syntax."
                ::= { vsmDspVoiceErrorStatsEntry 1 }

        vsmDspMicroOverflowCount OBJECT-TYPE
                SYNTAX  INTEGER
                ACCESS  read-only
                STATUS  mandatory
                DESCRIPTION
                        "The number of voice packets that could not be transmitted by
                        the DSP because the DSP-to-MIC voice data buffer was busy."
                ::= { vsmDspVoiceErrorStatsEntry 2 }

        vsmDspLostEnhPackets OBJECT-TYPE
                SYNTAX  INTEGER
                ACCESS  read-only
                STATUS  mandatory
                DESCRIPTION
                        "The number of lost incomming enhancement packets detected when
                        two core packets are received without enhancement in between,
                        in the DSP (E-ADPCM only)."
                ::= { vsmDspVoiceErrorStatsEntry 3 }

        vsmDspMissingCorePackets OBJECT-TYPE
                SYNTAX  INTEGER
                ACCESS  read-only
                STATUS  mandatory
                DESCRIPTION
                        "The number of enhancement packets that are dropped since the
                        core packet was not received (E-ADPCM only)."
                ::= { vsmDspVoiceErrorStatsEntry 4 }

        vsmDspPktsLostByNetwork OBJECT-TYPE
                SYNTAX  INTEGER
                ACCESS  read-only
                STATUS  mandatory
                DESCRIPTION
                        "The number of packets lost by the network."
                ::= { vsmDspVoiceErrorStatsEntry 5 }


        vsmResetDspErrorStats OBJECT-TYPE
                SYNTAX  INTEGER
                ACCESS  write-only
		STATUS  mandatory
                DESCRIPTION
                        "Any write operation on this field will 
			 reset DSP error statistics for the specified slot/port/channel"
                ::= { vsmDspVoiceErrorStatsEntry 6 }	


--=======================================================================
--
-- DSP Modem Statistics Table
--
--=======================================================================
--==  Note: This table is not supported in this release !
--=======================================================================

        vsmDspModemStatsTable OBJECT-TYPE
                SYNTAX  SEQUENCE OF VsmDspModemStatsEntry
                ACCESS  not-accessible
                STATUS  mandatory
                DESCRIPTION 
                       "DSP modem statistics by slot/port/channel.

                        For more information, please see the following CLI command:
                          voice channel slot/port/channel modem stat[istic]s view
                        "
                ::= { vsmStatsGroup 6 }

        vsmDspModemStatsEntry OBJECT-TYPE
                SYNTAX   VsmDspModemStatsEntry
                ACCESS   not-accessible
                STATUS   mandatory
                DESCRIPTION
                        "Individual DSP modem statistics entry.

                  For more information, please see the following CLI command:
                    [Note: There is NO equivalent command in the CLI.]
                        "
                INDEX {
                        vsmChanSlotIndex,
                        vsmChanPortIndex,
                        vsmChanIndex
                        }
                ::= { vsmDspModemStatsTable 1 }

        VsmDspModemStatsEntry ::=
                SEQUENCE {
                        vsmDspModemStatus                       INTEGER,
                        vsmDspModemRxLevel                      INTEGER,
                        vsmDspModemRxRate                       INTEGER,
                        vsmDspModemTxLevel                      INTEGER,
                        vsmDspModemTxRate                       INTEGER,
                        vsmDspModemCarrFreqOffset               INTEGER,
                        vsmDspModemTimeFreqOffset               INTEGER,
			vsmResetDspModemStats                   INTEGER 
                        }


        vsmDspModemStatus OBJECT-TYPE
                SYNTAX  INTEGER
                ACCESS  read-only
                STATUS  mandatory
                DESCRIPTION
                        "The DSP modem status. "
                ::= { vsmDspModemStatsEntry 1 }

        vsmDspModemRxLevel OBJECT-TYPE
                SYNTAX  INTEGER
                ACCESS  read-only
                STATUS  mandatory
                DESCRIPTION
                        "The DSP modem receive level in dB."
                ::= { vsmDspModemStatsEntry 2 }

        vsmDspModemRxRate OBJECT-TYPE
                SYNTAX  INTEGER
                ACCESS  read-only
                STATUS  mandatory
                DESCRIPTION
                        "The DSP modem receive rate in bps."
                ::= { vsmDspModemStatsEntry 3 }

        vsmDspModemTxLevel OBJECT-TYPE
                SYNTAX  INTEGER
                ACCESS  read-only
                STATUS  mandatory
                DESCRIPTION
                        "The DSP modem transmit level in dB."
                ::= { vsmDspModemStatsEntry 4 }

        vsmDspModemTxRate OBJECT-TYPE
                SYNTAX  INTEGER
                ACCESS  read-only
                STATUS  mandatory
                DESCRIPTION
                        "The DSP modem transmit rate in bps."
                ::= { vsmDspModemStatsEntry 5 }

        vsmDspModemCarrFreqOffset OBJECT-TYPE
                SYNTAX  INTEGER
                ACCESS  read-only
                STATUS  mandatory
                DESCRIPTION
                        "The DSP modem carrier freq offset (1/10 Hz)."
                ::= { vsmDspModemStatsEntry 6 }

        vsmDspModemTimeFreqOffset OBJECT-TYPE
                SYNTAX  INTEGER
                ACCESS  read-only
                STATUS  mandatory
                DESCRIPTION
                        "The DSP modem timing freq offset (1/10000 of clock rate)."
                ::= { vsmDspModemStatsEntry 7 }

        vsmResetDspModemStats OBJECT-TYPE
                SYNTAX  INTEGER
                ACCESS  write-only
		STATUS  mandatory
                DESCRIPTION
                        "Any write operation on this field will 
			 reset DSP modem statistics for the specified slot/port/channel"
                ::= { vsmDspModemStatsEntry 8 }	


--=======================================================================
--
-- DSP Fax Statistics for Channel Table
--
--=======================================================================

        vsmDspFaxStatsTable OBJECT-TYPE
                SYNTAX  SEQUENCE OF VsmDspFaxStatsEntry
                ACCESS  not-accessible
                STATUS  mandatory
                DESCRIPTION
                        "DSP fax statistics for channel by slot/port/channel.

                        For more information, please see the following CLI command:
                        voice channel slot/port/channel fax stat[istic]s view
                        "
                ::= { vsmStatsGroup 7 }

        vsmDspFaxStatsEntry OBJECT-TYPE
                SYNTAX  VsmDspFaxStatsEntry
                ACCESS  not-accessible
                STATUS  mandatory
                DESCRIPTION
                        "Individual DSP fax statistics entry.

                  For more information, please see the following CLI command:
                    [Note: There is NO equivalent command in the CLI.]
                        "
                INDEX {
                        vsmChanSlotIndex,
                        vsmChanPortIndex,
                        vsmChanIndex
                        }
                ::= { vsmDspFaxStatsTable 1 }

        VsmDspFaxStatsEntry ::=
                SEQUENCE {
                        vsmDspFaxTxPackets              INTEGER,
                        vsmDspFaxRxPackets              INTEGER,
                        vsmDspFaxLostPackets            INTEGER,
                        vsmDspFaxDroppedPackets         INTEGER,
                        vsmDspFaxRxOutOfSeqPkts         INTEGER,
			vsmResetDspFaxStats             INTEGER   
                        }

        vsmDspFaxTxPackets OBJECT-TYPE
                SYNTAX  INTEGER
                ACCESS  read-only
                STATUS  mandatory
                DESCRIPTION
                        "The number of DSP fax transmitted packets."
                ::= { vsmDspFaxStatsEntry 1 }

        vsmDspFaxRxPackets OBJECT-TYPE
                SYNTAX  INTEGER
                ACCESS  read-only
                STATUS  mandatory
                DESCRIPTION
                        "The number of DSP fax received packets."
                ::= { vsmDspFaxStatsEntry 2 }

        vsmDspFaxLostPackets OBJECT-TYPE
                SYNTAX  INTEGER
                ACCESS  read-only
                STATUS  mandatory
                DESCRIPTION
                        "The number of DSP fax lost packets."
                ::= { vsmDspFaxStatsEntry 3 }

        vsmDspFaxDroppedPackets OBJECT-TYPE
                SYNTAX  INTEGER
                ACCESS  read-only
                STATUS  mandatory
                DESCRIPTION
                        "The number of DSP fax dropped packets."
                ::= { vsmDspFaxStatsEntry 4 }

        vsmDspFaxRxOutOfSeqPkts OBJECT-TYPE
                SYNTAX  INTEGER
                ACCESS  read-only
                STATUS  mandatory
                DESCRIPTION
                        "The number of DSP fax received packets out of sequence."
                ::= { vsmDspFaxStatsEntry 5 }

        vsmResetDspFaxStats OBJECT-TYPE
                SYNTAX  INTEGER
                ACCESS  write-only
		STATUS  mandatory
                DESCRIPTION
                        "Any write operation on this field will 
			 reset DSP fax statistics for the specified slot/port/channel"
                ::= { vsmDspFaxStatsEntry 6 }	


--=======================================================================
--
-- ISDN Level 2 Stats Table
--
--=======================================================================
--==  Note: This table is not supported in this release !
--=======================================================================

--        vsmISDNL2StatsTable OBJECT-TYPE
--                 SYNTAX  SEQUENCE OF VsmISDNL2StatsEntry
--                 ACCESS  not-accessible
--                 STATUS  mandatory
--                 DESCRIPTION
--                         "ISDN statistics for channel by slot/port/channel.
-- 
--                         For more information, please see the following CLI command:
--                        voice channel slot/port/channel isdn level 2 stat[istic]s view
--                         "
--                 ::= { vsmStatsGroup 8 }

--         vsmISDNL2StatsEntry OBJECT-TYPE
--                 SYNTAX  VsmISDNL2StatsEntry
--                 ACCESS  not-accessible
--                 STATUS  mandatory
--                 DESCRIPTION
--                         "Individual ISDN statistics entry.

--                   For more information, please see the following CLI command:
--                     [Note: There is NO equivalent command in the CLI.]
--                         "
--                 INDEX {
--                         vsmChanSlotIndex,
--                         vsmChanPortIndex,
--                         vsmChanIndex
--                         }
--                 ::= { vsmISDNL2StatsTable 1 }
-- 
--         VsmISDNL2StatsEntry ::=
--                 SEQUENCE {
--                         vsmISDNL2StatsIFramesSent               INTEGER,
--                         vsmISDNL2StatsIBytesSent                INTEGER,
--                         vsmISDNL2StatsIFramesResent             INTEGER,
--                         vsmISDNL2StatsIBytesResent              INTEGER,
--                         vsmISDNL2StatsUIFramesSent              INTEGER,
--                         vsmISDNL2StatsUIBytesSent               INTEGER,
--                         vsmISDNL2StatsIFramesRecvd              INTEGER,
--                         vsmISDNL2StatsIBytesRecvd               INTEGER,
--                         vsmISDNL2StatsUIFramesRecvd             INTEGER,
--                         vsmISDNL2StatsUIBytesRecvd              INTEGER,
--                         vsmResetISDNl2Stats                     INTEGER 
--                    }
-- 
--         vsmISDNL2StatsIFramesSent OBJECT-TYPE
--                SYNTAX  INTEGER
--                 ACCESS  read-only
--                 STATUS  mandatory
--                 DESCRIPTION
--                         "The number of information frames sent on the D-channel.
-- 
--                         For more information, please see the following CLI command:
--                           [Note: This object is not supported in this Release]
--                         "
--                 ::= { vsmISDNL2StatsEntry 1 }
-- 
--         vsmISDNL2StatsIBytesSent OBJECT-TYPE
--                 SYNTAX  INTEGER
--                 ACCESS  read-only
--                 STATUS  mandatory
--                 DESCRIPTION
--                         "The number of information bytes sent on the D-channel.
-- 
--                         For more information, please see the following CLI command:
--                           [Note: This object is not supported in this Release]
--                         "
--                 ::= { vsmISDNL2StatsEntry 2 }
-- 
--         vsmISDNL2StatsIFramesResent OBJECT-TYPE
--                 SYNTAX  INTEGER
--                 ACCESS  read-only
--                 STATUS  mandatory
--                 DESCRIPTION
--                         "The number of inforamtion frames resent on the D-channel.
-- 
--                         For more information, please see the following CLI command:
--                           [Note: This object is not supported in this Release]
--                         "
--                 ::= { vsmISDNL2StatsEntry 3 }
-- 
--         vsmISDNL2StatsIBytesResent OBJECT-TYPE
--                 SYNTAX  INTEGER
--                 ACCESS  read-only
--                 STATUS  mandatory
--                 DESCRIPTION
--                         "The number of information bytes resent on the D-channel
--                         through an information frame.
-- 
--                         For more information, please see the following CLI command:
--                           [Note: This object is not supported in this Release]
--                         "
--                 ::= { vsmISDNL2StatsEntry 4 }
-- 
--         vsmISDNL2StatsUIFramesSent OBJECT-TYPE
--                 SYNTAX  INTEGER
--                 ACCESS  read-only
--                 STATUS  mandatory
--                 DESCRIPTION
--                         "The number of unnumbered information frames sent on the
--                         D-channel.
-- 
--                         For more information, please see the following CLI command:
--                           [Note: This object is not supported in this Release]
--                         "
--                 ::= { vsmISDNL2StatsEntry 5 }
-- 
--         vsmISDNL2StatsUIBytesSent OBJECT-TYPE
--                 SYNTAX  INTEGER
--                 ACCESS  read-only
--                 STATUS  mandatory
--                 DESCRIPTION
--                         "The number of unnumbered information bytes sent
--                         on the D-channel through an unnumbered information frame.
-- 
--                         For more information, please see the following CLI command:
--                           [Note: This object is not supported in this Release]
--                         "
--                 ::= { vsmISDNL2StatsEntry 6 }
-- 
--         vsmISDNL2StatsIFramesRecvd OBJECT-TYPE
--                 SYNTAX  INTEGER
-- 
--                 ACCESS  read-only
--                 STATUS  mandatory
--                 DESCRIPTION
--                         "The number of information frames received on the
--                         D-channel.
-- 
--                         For more information, please see the following CLI command:
--                           [Note: This object is not supported in this Release]
--                         "
--                 ::= { vsmISDNL2StatsEntry 7 }
-- 
--         vsmISDNL2StatsIBytesRecvd OBJECT-TYPE
--                 SYNTAX  INTEGER
--                 ACCESS  read-only
--                 STATUS  mandatory
--                 DESCRIPTION
--                         "The number of information bytes received on the
--                         D-channel via an information frame.
-- 
--                         For more information, please see the following CLI command:
--                           [Note: This object is not supported in this Release]
--                         "
--                 ::= { vsmISDNL2StatsEntry 8 }
-- 
--         vsmISDNL2StatsUIFramesRecvd OBJECT-TYPE
--                SYNTAX  INTEGER
--                 ACCESS  read-only
--                 STATUS  mandatory
--                 DESCRIPTION
--                         "The number of unnumbered information frames received
--                         on the D-channel.
-- 
--                         For more information, please see the following CLI command:
--                           [Note: This object is not supported in this Release]
--                         "
--                 ::= { vsmISDNL2StatsEntry 9 }
-- 
--         vsmISDNL2StatsUIBytesRecvd OBJECT-TYPE
--                 SYNTAX  INTEGER
--                 ACCESS  read-only
--                 STATUS  mandatory
--                 DESCRIPTION
--                         "The number of unnumbered information bytes received
--                         on the D-channel via information frames.
-- 
--                         For more information, please see the following CLI command:
--                           [Note: This object is not supported in this Release]
--                         "
--                 ::= { vsmISDNL2StatsEntry 10 }
-- 
--        vsmResetISDNl2Stats OBJECT-TYPE
--                SYNTAX  INTEGER
--                ACCESS  write-only
--		STATUS  mandatory
--                DESCRIPTION
--                        "Any write operation on this field will 
--                         reset Isdn l2 statistics for the specified slot/port/channel"
--                ::= { vsmISDNL2StatsEntry 11 }	
--
 --=======================================================================
--
-- ISDN Channel stats Table
--
--=======================================================================

        vsmISDNTeleStatsTable OBJECT-TYPE
                SYNTAX  SEQUENCE OF VsmISDNTeleStatsEntry
                ACCESS  not-accessible
                STATUS  mandatory
                DESCRIPTION
                        "channel statistics for ISDN channel by slot/port/channel."
                ::= { vsmStatsGroup 9 }

        vsmISDNTeleStatsEntry OBJECT-TYPE
                SYNTAX  VsmISDNTeleStatsEntry
                ACCESS  not-accessible
                STATUS  mandatory
                DESCRIPTION
                        "Channel statistics for ISDN channel"
                INDEX {
                        vsmChanSlotIndex,
                        vsmChanPortIndex,
                        vsmChanIndex
                        }
                ::= { vsmISDNTeleStatsTable 1 }


        VsmISDNTeleStatsEntry ::=
                SEQUENCE {
                        vsmNbCalls                      INTEGER,
                        vsmNbLocalSetup                 INTEGER,
                        vsmNbRemoteSetup                INTEGER,
                        vsmNbDropCalls                  INTEGER,
			vsmNbFaxSwitch                  INTEGER,
			vsmNbModemSwitch                INTEGER,
			vsmResetISDNTeleStats           INTEGER
                        }

        vsmNbCalls OBJECT-TYPE
                SYNTAX  INTEGER
                ACCESS  read-only
                STATUS  mandatory
                DESCRIPTION
                        "Number of calls."
                ::= { vsmISDNTeleStatsEntry 1 }

        vsmNbLocalSetup OBJECT-TYPE
                SYNTAX  INTEGER
                ACCESS  read-only
                STATUS  mandatory
                DESCRIPTION
                        "Number of local setups"
                ::= { vsmISDNTeleStatsEntry 2 }

        vsmNbRemoteSetup OBJECT-TYPE
                SYNTAX  INTEGER
                ACCESS  read-only
                STATUS  mandatory
                DESCRIPTION
                        "Number of remote setups"
                ::= { vsmISDNTeleStatsEntry 3 }

        vsmNbDropCalls OBJECT-TYPE
                SYNTAX  INTEGER
                ACCESS  read-only
                STATUS  mandatory
                DESCRIPTION
                        "Number of dropped calls"
		::= { vsmISDNTeleStatsEntry 4 }


        vsmNbFaxSwitch OBJECT-TYPE
                SYNTAX  INTEGER
                ACCESS  read-only
                STATUS  mandatory
                DESCRIPTION
                        "Number of fax switch"
                ::= { vsmISDNTeleStatsEntry 5 }


        vsmNbModemSwitch OBJECT-TYPE
                SYNTAX  INTEGER
                ACCESS  read-only
                STATUS  mandatory
                DESCRIPTION
                        "Number of modem switch"
                ::= { vsmISDNTeleStatsEntry 6 }

        vsmResetISDNTeleStats OBJECT-TYPE
                SYNTAX  INTEGER
                ACCESS  write-only
		STATUS  mandatory
                DESCRIPTION
                        "Any write operation on this field will 
			 Reset DSP fax statistics for the specified slot/port/channel"
                ::= { vsmISDNTeleStatsEntry 7 }	


END

-- ======================================================
-- These commands are not supported by the mib:
--
--    voice coding profile 'codingProfName' view
--    voice network template 'vsmNetworkTemplateName' view
--    voice destination 'destinationName' view
--    voice phone group 'PhoneGroupName' view
--    voice numbering plan 'NumberingPlanName' view
--    voice clear configuration
--    voice echo ON
--    voice echo OFF
--    voice debug level (0x00000000 ... 0xFFFFFFFF)
--    voice debug tunnel 'String'
--    voice daughter card slot/daughter_card_number view
--    voice port slot/port view
--    voice channel slot/port/channel view
--
--    voice view all
--    voice view daughter card slot/daughter_card_number
--    voice view port slot/port
--    voice view channel slot/port/channel
--    voice view phone group 'PhoneGroupName'
--    voice view network template 'vsmNetworkTemplateName'
--    voice view coding profile 'codingProfName'
--    voice view signaling template 'signalingTemplateName'
--    voice view destination 'destinationName'
--    voice view numbering plan 'NumberingPlanName'
--        voice coding profile all reset
-- ======================================================
